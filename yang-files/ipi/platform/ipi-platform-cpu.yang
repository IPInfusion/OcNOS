/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-cpu.yang
*
*/

submodule ipi-platform-cpu {

    yang-version 1.1;

    belongs-to  ipi-platform { prefix ipi-platform; }

    import feature-list {
        prefix feature-list;
        revision-date 2026-09-15;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for CPU components in platform datamodel";


    revision "2023-06-12" {
        description "Inclusion of streaming telemetry yaml file";
        reference " 0.5.1.";
    }

    revision "2022-06-01" {
        description "Updated the yang file with feature";
        reference " 0.5.0.";
    }

    revision "2021-09-03" {
        description "Update descriptions of attribute";
        reference " 0.4.0.";
    }

    revision "2021-04-28" {
        description "Some threshold attribute names changed as notifications related to them";
        reference " 0.3.0.";
    }

    revision "2021-03-18" {
        description "Added notification for cpu load alarms";
        reference " 0.2.0.";
    }

    revision "2021-01-15" {
        description "Initial version for CPU utilization runtime attributes";
        reference " 0.1.0.";
    }

    grouping component-cpu-utilization {
        description
            "Per-component CPU statistics";
        leaf processor-count  {
            type  uint32;
            description "Number of processors currently available in the system";
        } // END of processor-count definition.

        leaf cpu-1min-load-percentage  {
            type  decimal64 {
                 fraction-digits 2;            }
            units "%";
            description "The arithmetic mean value of the percentage measure of the CPU load
                        over 1 minute interval";
        } // END of cpu-1min-load-percentage definition.

        leaf cpu-5min-load-percentage  {
            type  decimal64 {
                 fraction-digits 2;            }
            units "%";
            description "The arithmetic mean value of the percentage measure of the CPU load
                        over 5 minutes interval";
        } // END of cpu-5min-load-percentage definition.

        leaf cpu-15min-load-percentage  {
            type  decimal64 {
                 fraction-digits 2;            }
            units "%";
            description "The arithmetic mean value of the percentage measure of the CPU load
                        over 15 minutes interval";
        } // END of cpu-15min-load-percentage definition.

        leaf cpu-1min-alert-threshold  {
            type  uint8;
            units "%";
            description "CPU load threshold during 1 minute interval for alert level";
        } // END of cpu-1min-alert-threshold definition.

        leaf cpu-1min-critical-threshold  {
            type  uint8;
            units "%";
            description "CPU load threshold during 1 minute interval for critical level";
        } // END of cpu-1min-critical-threshold definition.

        leaf cpu-5min-alert-threshold  {
            type  uint8;
            units "%";
            description "CPU load threshold during 5 minutes interval for alert level";
        } // END of cpu-5min-alert-threshold definition.

        leaf cpu-15min-alert-threshold  {
            type  uint8;
            units "%";
            description "CPU load threshold during 15 minutes interval for alert level";
        } // END of cpu-15min-alert-threshold definition.

        leaf cpu-utilization  {
            type  decimal64 {
                 fraction-digits 2;            }
            units "%";
            description "Instantaneous CPU load";
        } // END of cpu-utilization definition.

        leaf cpu-utilization-alert  {
            type  uint8;
            units "%";
            description "Instantaneous CPU load threshold for alert level";
        } // END of cpu-utilization-alert definition.

        leaf cpu-utilization-critical  {
            type  uint8;
            units "%";
            description "Instantaneous CPU load threshold for critical level";
        } // END of cpu-utilization-critical definition.

    } // END of component-cpu-utilization definition.

    grouping  cpu-grouping {
    description
        "Container for CPU component";
    container cpu {
        if-feature feature-list:HAVE_CMMD;
        config false;
        description
            "Container for CPU component";
        container state {
            config false;
            description
                "Operational state data for CPU components";
            uses component-cpu-utilization;
        } // END of state-container definition.
    } // END of cpu-container definition.
    } // END of cpu-grouping definition.


}
