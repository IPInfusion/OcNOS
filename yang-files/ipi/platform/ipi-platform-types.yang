/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-types.yang
*
*/

module ipi-platform-types {

    yang-version 1.1;

    namespace   "http://www.ipinfusion.com/yang/ocnos/ipi-platform-types";

    prefix "ipi-platform-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-platform-types";


    revision "2026-04-16" {
        description "Added cpu-queue mgmt under ltsw platform";
        reference " 0.33.7.";
    }

    revision "2026-03-23" {
        description "Making l3-slowpath/rsvd mc cpu queue configurable ";
        reference " 0.33.6.";
    }

    revision "2025-09-04" {
        description "Modification of CPU queues(PLATFORM_CPU_QUEUE_NAME_T) for XGS platform ";
        reference " 0.33.5.";
    }

    revision "2025-04-28" {
        description "Revert transceiver CLI migration changes";
        reference " 0.33.4.";
    }

    revision "2025-04-04" {
        description "Added mode2/mode3 for hardware-profile port mode for S9600-28dx/64x/56dx/32x";
        reference " 0.33.3.";
    }

    revision "2025-02-22" {
        description "CLI migration from qsfp-dd references to xcvr references";
        reference " 0.33.2.";
    }

    revision "2025-02-21" {
        description "removed mode2/mode3 for hardware-profile port mode for S9600-28dx/64x/56dx/32x";
        reference " 0.33.1.";
    }

    revision "2025-02-14" {
        description "Added support for hardware-profile port mode for S9610-46DX and 48DX";
        reference " 0.33.0.";
    }

    revision "2025-01-30" {
        description "Removed support for hardware-profile port mode for UFIS9510_28DC ";
        reference " 0.32.14.";
    }

    revision "2024-11-06" {
        description "Removed support for hardware-profile port mode for TH5";
        reference " 0.32.13.";
    }

    revision "2024-09-25" {
        description "Removed the datatypes related to libhwconf";
        reference " 0.32.12.";
    }

    revision "2024-09-16" {
        description "Added the cpu-queues msdp and ptp to the existing lists";
        reference " 0.32.11.";
    }

    revision "2024-09-05" {
        description "Added support for hardware-profile port mode for S9321-64E";
        reference " 0.33.7.";
    }

    revision "2024-08-29" {
        description "Removed ecmp/lag parameter types from parser enable";
        reference " 0.32.10.";
    }

    revision "2024-08-28" {
        description "Added support for hardware-profile port mode for AS9817-64D";
        reference " 0.33.6.";
    }

    revision "2024-08-09" {
        description "OLS-9132: User configuration for Temperature threshold";
        reference " 0.33.4.";
    }

    revision "2024-07-31" {
        description "Added support for load-balance flb CLI";
        reference " 0.33.5.";
    }

    revision "2024-07-24" {
        description "User configuration for Temperature threshold - update to resolve DB sync issue";
        reference " 0.33.3.";
    }

    revision "2024-07-22" {
        description "User configuration for Temperature threshold";
        reference " 0.33.2.";
    }

    revision "2024-07-15" {
        description "Updated helpstring for mgmt-route-leak cpu rate config";
        reference " 0.33.1.";
    }

    revision "2024-07-01" {
        description "Include GPS GNSS and DPLL status";
        reference " 0.33.0.";
    }

    revision "2024-06-17" {
        description "Added support for hardware-profile port mode for AS9947-36XKB mode";
        reference " 0.32.5.";
    }

    revision "2024-04-29" {
        description "Cli implementation for gps satellite-system";
        reference " 0.32.4.";
    }

    revision "2024-04-27" {
        description "Removed unsupported Queues from PLATFORM_CPU_QUEUE_NAME_T for Marvell";
        reference " 0.32.3.";
    }

    revision "2024-03-20" {
        description "Reduced route-mode support for TD4 ";
        reference " 0.32.2.";
    }

    revision "2024-02-28" {
        description "Removed the Hardware-profile port-config mode3 4 5 6 for UFI_S9610-36D ";
        reference " 0.32.1.";
    }

    revision "2024-02-27" {
        description "Added Marvell cpu_queue names";
        reference " 0.32.0.";
    }

    revision "2024-02-09" {
        description "Added td-4/th-4 cml types for PLATFORM_SOC_TYPE_T ";
        reference " 0.31.0.";
    }

    revision "2023-12-20" {
        description "Moved Raon datatype";
        reference " 0.30.0.";
    }

    revision "2023-11-27" {
        description "Added support for hardware-profile port mode for S9600-28DX ";
        reference " 0.29.2.";
    }

    revision "2023-11-13" {
        description "Added support for hardware-profile port mode for S9500-30XS ";
        reference " 0.29.1.";
    }

    revision "2023-11-08" {
        description "Added support for hardware-profile port mode for AS7316-26xb mode";
        reference " 0.29.0.";
    }

    revision "2023-10-31" {
        description "Added AS7315-27X mode3 option";
        reference " 0.28.0.";
    }

    revision "2023-08-23" {
        description "Added datatype PLATFORM_ACLIF_TYPE_T";
        reference " 0.27.0.";
    }

    revision "2023-08-21" {
        description "support bgp-flowspec-mode attribute";
        reference " 0.27.0.";
    }

    revision "2023-08-08" {
        description "Moved platform ceragon types";
        reference " 0.26.0.";
    }

    revision "2023-07-20" {
        description "Fixed missing 'port-channel load-balance rtag7' from show command";
        reference " 0.25.0.";
    }

    revision "2023-07-17" {
        description "Changed help string for AS5916-54X and AS5912-54x ";
        reference " 0.24.0.";
    }

    revision "2023-06-22" {
        description "Only supported on broadcom";
        reference " 0.23.0.";
    }

    revision "2023-06-16" {
        description "Removed port mode support on AS9716-32D XGS TOMAHAWK3 ";
        reference " 0.22.0.";
    }

    revision "2023-06-06" {
        description "Added port mode 3 adn 4 for 4X100G support on UFIS9610-36d";
        reference " 0.21.0.";
    }

    revision "2023-05-19" {
        description "Added support for dune port mode and port-group";
        reference " 0.20.0.";
    }

    revision "2023-05-08" {
        description "Added support for dune port mode";
        reference " 0.19.0.";
    }

    revision "2023-05-05" {
        description "Added support for hardware-profile port mode for as9716-32d board";
        reference " 0.18.0.";
    }

    revision "2023-05-02" {
        description "Added support for hardware-profile port mode for UFIS9610-36d mode";
        reference " 0.17.0.";
    }

    revision "2023-02-11" {
        description "Added support for EDFA Operating mode type";
        reference " 0.16.0.";
    }

    revision "2022-12-14" {
        description "Added support for hardware-profile port mode for UFIS9600-56dx mode";
        reference " 0.10.11.";
    }

    revision "2022-12-08" {
        description "Added if-feature HAVE_BROADCOM AND HAVE_DUNE to the datatype PLATFORM_VOQ_SCALE_TYPE_T";
        reference " 0.10.10.";
    }

    revision "2022-12-01" {
        description "implementation of hardware profile statistics egress-policer|voq-scale CLI";
        reference " 0.10.9.";
    }

    revision "2022-11-28" {
        description "New SOC type Hurriane 4 added";
        reference " 0.10.8.";
    }

    revision "2022-10-17" {
        description "Fixed olt compilation err for voq stats";
        reference " 0.10.7.";
    }

    revision "2022-10-12" {
        description "Updated datatype for VOQ stats";
        reference " 0.10.6.";
    }

    revision "2022-07-29" {
        description "Updated datatype for RAON ODU state";
        reference " 0.10.5.";
    }

    revision "2022-06-01" {
        description "Updated the yang file with feature";
        reference " 0.10.5.";
    }

    revision "2022-05-02" {
        description "Added new datatype port mode config types for UFIS9600-64X / UFIS9600-32X mode";
        reference " 0.10.4.";
    }

    revision "2022-03-08" {
        description "Replace 'poe' by 'vendor-specific' in CMM_COMPONENT_TYPE_T datatype";
        reference " 0.10.3.";
    }

    revision "2022-02-17" {
        description "Removed invalid options from PLATFORM_FORWARDING_PROFILE_T";
        reference " 0.10.2.";
    }

    revision "2022-02-01" {
        description "Fixed PLATFORM_CPU_QUEUE_NAME_T mpls helpstring";
        reference " 0.10.1.";
    }

    revision "2022-01-06" {
        description "Added new datatype PLATFORM_PORT_CONFIG_TYPE_T";
        reference " 0.10.0.";
    }

    revision "2021-12-20" {
        description "Add 'poe' element to CMM_COMPONENT_TYPE_T datatype. Added CMM_POE_PORT_STATUS_T datatype.";
        reference " 0.9.0.";
    }

    revision "2021-12-10" {
        description "Add PLATFORM_SYSTEM_STATUS_TYPE_T datatype";
        reference " 0.8.0.";
    }

    revision "2021-11-22" {
        description "Added new datatypes for platform restructuring phase 2";
        reference " 0.7.0.";
    }

    revision "2021-09-03" {
        description "Update descriptions of attribute";
        reference " 0.6.0.";
    }

    revision "2021-07-19" {
        description "Added new datatypes for platform forwarding profiles and CPU queues.";
        reference " 0.5.0.";
    }

    revision "2021-06-24" {
        description "Added optical-channel to component type.";
        reference " 0.4.0.";
    }

    revision "2021-01-25" {
        description "Added new datatype for power-rail status. Fixed CMM_COMPONENT_TYPE_T:chassis typo and added fru, linecard, and port types.";
        reference " 0.3.0.";
    }

    revision "2020-12-15" {
        description "Change to have data-types in lower case instead of camel case";
        reference " 0.2.0.";
    }

    revision "2018-06-21" {
        description "Initial Version";
        reference " 0.1.0.";
    }



    typedef  cmm_component_type_t {
        type enumeration {
            enum NA {
                value 0;
                description "Not applicable";
            }
            enum software {
                value 1;
                description "software-related components in a managed device";
            }
            enum chassis {
                value 2;
                description "Chassis component typically with multiple slots / shelves";
            }
            enum backplane {
                value 3;
                description "Backplane component for aggregating traffic typically contained in a chassis component";
            }
            enum fabric {
                value 4;
                description "Interconnect between ingress and egress ports on the device (e.g. a crossbar switch).";
            }
            enum power-supply {
                value 5;
                description "Component that is supplying power to the device";
            }
            enum power-rail {
                value 6;
                description "Power rail component";
            }
            enum fan {
                value 7;
                description "Cooling fan or could be some other heat-reduction component";
            }
            enum sensor {
                value 8;
                description "Physical sensor e.g. a temperature sensor in a chassis";
            }
            enum fan-tray {
                value 9;
                description "Fan tray";
            }
            enum transceiver {
                value 10;
                description "Pluggable module present in a port";
            }
            enum cpu {
                value 11;
                description "Processing unit e.g. a management processor";
            }
            enum storage {
                value 12;
                description "A storage subsystem on the device (disk or SSD or etc.)";
            }
            enum integrated-circuit {
                value 13;
                description "A special purpose processing unit typically for traffic           switching/forwarding (e.g. switching ASIC or NPU or forwarding chip etc.)";
            }
            enum ram {
                value 14;
                description "RAM unit";
            }
            enum ptp-clock {
                value 15;
                description "Ptp-clock unit";
            }
            enum fru {
                value 16;
                description "Field Replaceable Unit";
            }
            enum linecard {
                value 17;
                description "Linecard component typically inserted into a chassis slot";
            }
            enum port {
                value 18;
                description "Physical port e.g. for attaching pluggables and networking cables";
            }
            enum optical-channel {
                value 19;
                description "Optical channels act as carriers for transport traffic           directed over a line system.  They are represented as           physical components in the physical inventory model";
            }
            enum vendor-specific {
                value 20;
                description "Vendor Specific components";
            }
            enum cmis-module {
                value 21;
                description "CMIS transceiver component";
            }
        }
        description "type definition for CMM_COMPONENT_TYPE_T";
    }

    typedef  cmm_bmc_event_type_t {
        type enumeration {
            enum Deasserted {
                value 1;
                description "Deasserted event";
            }
            enum Asserted {
                value 2;
                description "Asserted event";
            }
        }
        description "type definition for CMM_BMC_EVENT_TYPE_T";
    }

    typedef  cmm_component_oper_status_t {
        type enumeration {
            enum NA {
                value 0;
                description "Not Applicable";
            }
            enum active {
                value 1;
                description "Component is enabled and active (i.e. up)";
            }
            enum inactive {
                value 2;
                description "Component is enabled but inactive (i.e. down)";
            }
            enum disabled {
                value 3;
                description "Component is administratively disabled.";
            }
        }
        description "type definition for CMM_COMPONENT_OPER_STATUS_T";
    }

    typedef  cmm_bmc_value_t {
        type union {
            type decimal64 {

             fraction-digits 6;
            }
            type string {

            }
        }
        description "type definition for CMM_BMC_VALUE_T";
    }

    typedef  cmm_monitor_state {
        type enumeration {
            enum disable {
                value 1;
                description "Disable";
            }
            enum enable {
                value 2;
                description "Enable";
            }
        }
        description "type definition for CMM_MONITOR_STATE";
    }

    typedef  cmm_videopiu_state {
        type enumeration {
            enum disable {
                value 0;
                description "Disable";
            }
            enum enable {
                value 1;
                description "Enable";
            }
        }
        description "type definition for CMM_VIDEOPIU_STATE";
    }

    typedef  cmm_gps_monitor_type_t {
        type enumeration {
            enum stop {
                value 0;
                description "stop monitoring";
            }
            enum start {
                value 1;
                description "start monitoring";
            }
        }
        description "type definition for CMM_GPS_MONITOR_TYPE_T";
    }

    typedef  cml_wavelength_t {
        type union {
            type cml_wavelength_channel_t {

            }
            type cml_wavelength_update_t {

            }
        }
        description "type definition for CML_WAVELENGTH_T";
    }

    typedef  cml_wavelength_channel_t {
        type uint32 {
             range 1..96;
        }
        description "type definition for CML_WAVELENGTH_CHANNEL_T";
    }

    typedef  cml_wavelength_update_t {
        type uint32 {
             range 1528773..1566723;
        }
        description "type definition for CML_WAVELENGTH_UPDATE_T";
    }

    typedef  cml_cmm_power_rail_t {
        type enumeration {
            enum unknown {
                value 0;
                description "Power rail status unknown";
            }
            enum good {
                value 1;
                description "Power rail good";
            }
            enum fail {
                value 2;
                description "Power rail fail";
            }
        }
        description "type definition for CML_CMM_POWER_RAIL_T";
    }

    typedef  platform_ufis9600_64x_port_mode_type_t {
        type enumeration {
            enum mode1 {
                value 1;
                description "64X100G (Default)";
            }
            enum mode2 {
                value 2;
                description "4X1G  + 63X100G (ce0 breakout to 4X1G)";
            }
            enum mode3 {
                value 3;
                description "4X10G + 63X100G (ce0 breakout to 4X10G)";
            }
            enum mode4 {
                value 4;
                description "4X25G + 63X100G (ce0 breakout to 4X25G)";
            }
        }
        description "type definition for PLATFORM_UFIS9600_64X_PORT_MODE_TYPE_T";
    }

    typedef  platform_as7315_27x_port_mode_type_t {
        type enumeration {
            enum mode1 {
                value 1;
                description "20X10G + 4X25G + 3X100G (default)";
            }
            enum mode2 {
                value 2;
                description "20X10G + 4X25G + 12X25G";
            }
            enum mode3 {
                value 3;
                description "20X10G + 4X25G + 2X100G + 4X25G(ce2 breakout to 4X25G)";
            }
        }
        description "type definition for PLATFORM_AS7315_27X_PORT_MODE_TYPE_T";
    }

    typedef  platform_as5916_as5912_54x_port_mode_type_t {
        type enumeration {
            enum mode1 {
                value 1;
                description "48X10G + 6X100G (default)";
            }
            enum mode2 {
                value 2;
                description "48X10G + 24X25G";
            }
        }
        description "type definition for PLATFORM_AS5916_AS5912_54X_PORT_MODE_TYPE_T";
    }

    typedef  platform_as7316_26xb_port_mode_type_t {
        type enumeration {
            enum mode1 {
                value 1;
                description "16X10G + 8X25G + 2X100G (default)";
            }
            enum mode2 {
                value 2;
                description "16X10G + 8X25G + 8X25G";
            }
            enum mode3 {
                value 3;
                description "16X10G + 8X25G + 1X100G + 4X25G (ce0 breakout to 4X25G)";
            }
            enum mode4 {
                value 4;
                description "16X10G + 8X25G + 1X100G + 4X25G (ce1 breakout to 4X25G)";
            }
        }
        description "type definition for PLATFORM_AS7316_26XB_PORT_MODE_TYPE_T";
    }

    typedef  platform_s9500_30xs_port_mode_type_t {
        type enumeration {
            enum mode1 {
                value 1;
                description "20X10G + 8X25G + 2X100G (default)";
            }
            enum mode2 {
                value 2;
                description "20X10G + 8X25G + 8X25G";
            }
            enum mode3 {
                value 3;
                description "20X10G + 8X25G + 1X100G + 4X25G(ce0 breakout to 4X25G)";
            }
            enum mode4 {
                value 4;
                description "20X10G + 8X25G + 1X100G + 4X25G(ce1 breakout to 4X25G)";
            }
        }
        description "type definition for PLATFORM_S9500_30XS_PORT_MODE_TYPE_T";
    }

    typedef  platform_ufis9600_32x_port_mode_type_t {
        type enumeration {
            enum mode1 {
                value 1;
                description "32X100G (Default)";
            }
            enum mode2 {
                value 2;
                description "4X1G  + 31X100G (ce0 breakout to 4X1G)";
            }
            enum mode3 {
                value 3;
                description "4X10G + 31X100G (ce0 breakout to 4X10G)";
            }
            enum mode4 {
                value 4;
                description "4X25G + 31X100G (ce0 breakout to 4X25G)";
            }
        }
        description "type definition for PLATFORM_UFIS9600_32X_PORT_MODE_TYPE_T";
    }

    typedef  platform_ufis9600_56dx_port_mode_type_t {
        type enumeration {
            enum mode1 {
                value 1;
                description "8X400Gb + 48X100G (Default)";
            }
            enum mode2 {
                value 2;
                description "8X400Gb + 4X1G  + 47X100G (ce0 breakout to 4X1G)";
            }
            enum mode3 {
                value 3;
                description "8X400Gb + 4X10G + 47X100G (ce0 breakout to 4X10G)";
            }
            enum mode4 {
                value 4;
                description "8X400Gb + 4X25G + 47X100G (ce0 breakout to 4X25G)";
            }
        }
        description "type definition for PLATFORM_UFIS9600_56DX_PORT_MODE_TYPE_T";
    }

    typedef  platform_ufis9600_28dx_port_mode_type_t {
        type enumeration {
            enum mode1 {
                value 1;
                description "4X400Gb + 24X100G (Default)";
            }
            enum mode2 {
                value 2;
                description "4X400Gb + 4X1G  + 23X100G (ce0 breakout to 4X1G)";
            }
            enum mode3 {
                value 3;
                description "4X400Gb + 4X10G + 23X100G (ce0 breakout to 4X10G)";
            }
            enum mode4 {
                value 4;
                description "4X400Gb + 4X25G + 23X100G (ce0 breakout to 4X25G)";
            }
        }
        description "type definition for PLATFORM_UFIS9600_28DX_PORT_MODE_TYPE_T";
    }

    typedef  platform_ufis9610_36d_port_mode_type_t {
        type enumeration {
            enum mode1 {
                value 1;
                description "36X400G (Default : Without KBP)";
            }
            enum mode2 {
                value 2;
                description "32X400G With KBP Support";
            }
        }
        description "type definition for PLATFORM_UFIS9610_36D_PORT_MODE_TYPE_T";
    }

    typedef  platform_ufis9610_46dx_port_mode_type_t {
        type enumeration {
            enum mode1 {
                value 1;
                description "6X400G + 40X100G (Default)";
            }
            enum mode2 {
                value 2;
                description "6X400G  + 38X100G + 4x25G";
            }
        }
        description "type definition for PLATFORM_UFIS9610_46DX_PORT_MODE_TYPE_T";
    }

    typedef  platform_ufis9610_48dx_port_mode_type_t {
        type enumeration {
            enum mode1 {
                value 1;
                description "8X400G + 40X100G (Default)";
            }
            enum mode2 {
                value 2;
                description "8X400G  + 38X100G + 4x25G";
            }
        }
        description "type definition for PLATFORM_UFIS9610_48DX_PORT_MODE_TYPE_T";
    }

    typedef  platform_qos_queue_profile_type_t {
        type enumeration {
            enum profile1 {
                value 1;
                description "supported new 4 queue-bundle per service (default)";
            }
            enum profile2 {
                value 2;
                description "supported new 8 queue-bundle per service";
            }
        }
        description "type definition for PLATFORM_QOS_QUEUE_PROFILE_TYPE_T";
    }

    typedef  platform_kaps_profile_type_t {
        type enumeration {
            enum profile-one {
                value 1;
                description "select kaps profile one";
            }
            enum profile-two {
                value 2;
                description "select kaps profile two";
            }
        }
        description "type definition for PLATFORM_KAPS_PROFILE_TYPE_T";
    }

    typedef  platform_ext_tcam_profile_type_t {
        type enumeration {
            enum profile-one {
                value 3;
                description "select elk-tcam profile one";
            }
            enum profile-two {
                value 4;
                description "select elk-tcam profile two";
            }
            enum profile-three {
                value 5;
                description "select elk-tcam profile three";
            }
        }
        description "type definition for PLATFORM_EXT_TCAM_PROFILE_TYPE_T";
    }

    typedef  platform_aclif_type_t {
        type enumeration {
            enum failover {
                value 1;
                description "Configure failover";
            }
            enum no-failover {
                value 2;
                description "Configiure no failover";
            }
        }
        description "type definition for PLATFORM_ACLIF_TYPE_T";
    }

    typedef  platform_tcam_custom_profile_t {
        type enumeration {
            enum custom-profile {
                value 6;
                description "define elk-tcam custom profile";
            }
        }
        description "type definition for PLATFORM_TCAM_CUSTOM_PROFILE_T";
    }

    typedef  platform_kaps_forwading_profile_t {
        type enumeration {
            enum kaps-profile-one {
                value 9;
                description "kaps,profile one";
            }
            enum kaps-profile-two {
                value 10;
                description "kaps,profile two";
            }
        }
        description "type definition for PLATFORM_KAPS_FORWADING_PROFILE_T";
    }

    typedef  platform_elk_tcam_forwading_profile_t {
        type enumeration {
            enum elk-tcam-profile-one {
                value 11;
                description "elk-tcam,profile one";
            }
            enum elk-tcam-profile-two {
                value 12;
                description "elk-tcam,profile two";
            }
            enum elk-tcam-profile-three {
                value 13;
                description "elk-tcam,profile three";
            }
        }
        description "type definition for PLATFORM_ELK_TCAM_FORWADING_PROFILE_T";
    }

    typedef  platform_cpu_queue_name_t {
        type enumeration {
            enum mgmt-route-leak {
                value 33;
                if-feature feature-list:HAVE_DUNE;
                description "mgmt-route-leak queue parameters";
            }
            enum icmp-redirect {
                value 34;
                if-feature feature-list:HAVE_DUNE;
                description "ICMP-redirect queue parameters";
            }
            enum cfm {
                value 36;
                if-feature feature-list:HAVE_DUNE;
                description "CFM Error queue parameters";
            }
            enum msdp {
                value 39;
                if-feature feature-list:HAVE_DUNE;
                description "msdp queue parameters";
            }
            enum cpu.q0 {
                if-feature feature-list:HAVE_DUNE;
                description "cpu.q0";
            }
            enum best-effort {
                if-feature feature-list:HAVE_CUSTOM5_QOS;
                description "Best-effort queue parameters";
            }
            enum cpu-queue-0 {
                if-feature feature-list:NOT_HAVE_DUNE;
                if-feature feature-list:NOT_HAVE_MARVELL;
                if-feature feature-list:NOT_HAVE_CUSTOM5_QOS;
                description "Best-effort queue(cpu.q0) parameters";
            }
            enum cpu.q1 {
                if-feature feature-list:HAVE_DUNE;
                description "cpu.q1";
            }
            enum cpu-queue-1 {
                if-feature feature-list:NOT_HAVE_DUNE;
                if-feature feature-list:NOT_HAVE_MARVELL;
                if-feature feature-list:NOT_HAVE_CUSTOM5_QOS;
                description "cpu.q1 parameters";
            }
            enum cpu.q2 {
                if-feature feature-list:HAVE_DUNE;
                description "cpu.q2";
            }
            enum cpu-queue-2 {
                if-feature feature-list:NOT_HAVE_DUNE;
                if-feature feature-list:NOT_HAVE_MARVELL;
                if-feature feature-list:NOT_HAVE_CUSTOM5_QOS;
                description "cpu.q2 parameters";
            }
            enum cpu.q3 {
                if-feature feature-list:HAVE_DUNE;
                description "cpu.q3";
            }
            enum cpu-queue-3 {
                if-feature feature-list:NOT_HAVE_DUNE;
                if-feature feature-list:NOT_HAVE_MARVELL;
                if-feature feature-list:NOT_HAVE_CUSTOM5_QOS;
                description "cpu.q3 parameters";
            }
            enum cpu.q4 {
                if-feature feature-list:HAVE_DUNE;
                description "cpu.q4";
            }
            enum ipmc-miss {
                if-feature feature-list:HAVE_CUSTOM5_QOS;
                description "IPMC-Miss  queue parameters";
            }
            enum cpu-queue-4 {
                if-feature feature-list:NOT_HAVE_DUNE;
                if-feature feature-list:NOT_HAVE_MARVELL;
                if-feature feature-list:NOT_HAVE_CUSTOM5_QOS;
                description "cpu.q4 parameters";
            }
            enum cpu.q5 {
                if-feature feature-list:HAVE_DUNE;
                description "cpu.q5";
            }
            enum l3-miss {
                if-feature feature-list:HAVE_CUSTOM5_QOS;
                description "L3-Miss queue parameters";
            }
            enum cpu-queue-5 {
                if-feature feature-list:NOT_HAVE_DUNE;
                if-feature feature-list:NOT_HAVE_MARVELL;
                if-feature feature-list:NOT_HAVE_CUSTOM5_LTSW;
                description "MPLS queue parameters (For GAL label mpls oam packets) or cpu.q5 parameters";
            }
            enum cpu.q6 {
                if-feature feature-list:HAVE_DUNE;
                description "cpu.q6";
            }
            enum cpu-queue-6 {
                if-feature feature-list:NOT_HAVE_DUNE;
                if-feature feature-list:NOT_HAVE_MARVELL;
                if-feature feature-list:NOT_HAVE_CUSTOM5_QOS;
                description "cpu.q6 parameters";
            }
            enum cpu.q7 {
                if-feature feature-list:HAVE_DUNE;
                description "cpu.q7";
            }
            enum ipmc-reserved {
                if-feature feature-list:HAVE_CUSTOM5_QOS;
                description "ipmc-reserved parameters";
            }
            enum cpu-queue-7 {
                if-feature feature-list:NOT_HAVE_DUNE;
                if-feature feature-list:NOT_HAVE_MARVELL;
                if-feature feature-list:NOT_HAVE_CUSTOM5_QOS;
                description "cpu.q7 parameters";
            }
            enum igmp {
                if-feature feature-list:HAVE_MARVELL;
                description "IGMP queue parameters";
            }
            enum l3-slowpath {
                if-feature feature-list:HAVE_CUSTOM5_QOS;
                description "l3-slowpath parameters";
            }
            enum isis {
                if-feature feature-list:HAVE_MARVELL;
                if-feature feature-list:HAVE_ISISD;
                description "ISIS queue parameters";
            }
            enum sflow {
                if-feature feature-list:HAVE_SFLOW;
                if-feature feature-list:HAVE_CUSTOM5_QOS;
                description "SFLOW queue parameters";
            }
            enum reserved-mc {
                if-feature feature-list:HAVE_MARVELL;
                description "reserved-mc queue parameters";
            }
            enum bgp {
                if-feature feature-list:HAVE_BGPD;
                if-feature feature-list:HAVE_CUSTOM5_QOS;
                description "BGP queue parameters";
            }
            enum link-local {
                if-feature feature-list:HAVE_MARVELL;
                description "Link-local  queue parameters";
            }
            enum vrrp {
                if-feature feature-list:HAVE_VRRPD;
                if-feature feature-list:HAVE_CUSTOM5_QOS;
                description "VRRP queue parameters";
            }
            enum ospf {
                if-feature feature-list:HAVE_MARVELL;
                if-feature feature-list:HAVE_OSPFD;
                description "OSPF queue parameters";
            }
            enum ldp-rsvp {
                if-feature feature-list:HAVE_MPLS;
                if-feature feature-list:HAVE_CUSTOM5_QOS;
                description "LDP-RSVP queue parameters";
            }
            enum rip {
                if-feature feature-list:HAVE_RIPD;
                if-feature feature-list:HAVE_CUSTOM5_QOS;
                description "RIP queue parameters";
            }
            enum rsvp-ldp {
                if-feature feature-list:HAVE_MARVELL;
                if-feature feature-list:HAVE_MPLS;
                description "RSVP/LDP queue parameters";
            }
            enum vrrp-rip-dhcp {
                if-feature feature-list:HAVE_MARVELL;
                description "VRRP/RIP/DHCP queue parameters";
            }
            enum dhcp {
                if-feature feature-list:HAVE_CUSTOM5_QOS;
                description "DHCP queue parameters";
            }
            enum pim {
                if-feature feature-list:HAVE_MARVELL;
                if-feature feature-list:HAVE_PIMD;
                description "PIM queue parameters";
            }
            enum nd {
                if-feature feature-list:HAVE_IPV6;
                if-feature feature-list:HAVE_CUSTOM5_QOS;
                description "ND queue parameters";
            }
            enum icmp {
                if-feature feature-list:HAVE_MARVELL;
                description "ICMP queue parameters";
            }
            enum mpls {
                if-feature feature-list:HAVE_MPLS;
                if-feature feature-list:HAVE_CUSTOM5_QOS;
                description "MPLS queue parameters (For GAL label mpls oam packets)";
            }
            enum arp {
                if-feature feature-list:HAVE_MARVELL;
                description "ARP queue parameters";
            }
            enum bpdu {
                if-feature feature-list:HAVE_MARVELL;
                description "BPDU queue parameters";
            }
            enum oamp {
                if-feature feature-list:HAVE_MARVELL;
                description "OAMP queue parameters";
            }
            enum ccm {
                if-feature feature-list:HAVE_CFM;
                if-feature feature-list:HAVE_CUSTOM5_QOS;
                description "CCM queue parameters";
            }
            enum bfd {
                if-feature feature-list:HAVE_BFD;
                if-feature feature-list:HAVE_CUSTOM5_QOS;
                description "BFD queue parameters";
            }
            enum ptp {
                if-feature feature-list:HAVE_PTPD;
                if-feature feature-list:HAVE_CUSTOM5_QOS;
                description "PTP queue parameters";
            }
            enum trill-isis {
                if-feature feature-list:HAVE_TRILLD;
                if-feature feature-list:HAVE_CUSTOM5_QOS;
                description "TRILL queue parameters";
            }
            enum acl {
                if-feature feature-list:NOT_HAVE_DUNE;
                if-feature feature-list:NOT_HAVE_MARVELL;
                if-feature feature-list:NOT_HAVE_CUSTOM5_QOS;
                description "ACL queue parameters (for acl logging)";
            }
            enum vxlan {
                if-feature feature-list:HAVE_VXLAN;
                if-feature feature-list:NOT_HAVE_DUNE;
                if-feature feature-list:NOT_HAVE_MARVELL;
                if-feature feature-list:NOT_HAVE_CUSTOM5_QOS;
                description "VXLAN queue parameters";
            }
            enum dsp {
                if-feature feature-list:HAVE_DUNE;
                description "DSP queue parameters";
            }
            enum evpn {
                if-feature feature-list:HAVE_DUNE;
                if-feature feature-list:HAVE_BGP_EVPN;
                description "EVPN queue parameters";
            }
            enum nhop {
                if-feature feature-list:HAVE_DUNE;
                description "nhop queue parameters";
            }
            enum guest {
                if-feature feature-list:HAVE_DUNE;
                if-feature feature-list:HAVE_GUEST_VM;
                description "Guest queue parameters";
            }
            enum mgmt {
                if-feature feature-list:HAVE_CUSTOM5_QOS;
                description "Mgmt traffic parameters(eg. ssh/telnet/snmp/netconf ssh and tls)";
            }
        }
        description "type definition for PLATFORM_CPU_QUEUE_NAME_T";
    }

    typedef  platform_cpu_queue_monitor_t {
        type enumeration {
            enum no-monitor {
                value 0;
                description "do not monitor cpu queue usage";
            }
            enum monitor {
                value 1;
                description "monitor cpu queue usage";
            }
        }
        description "type definition for PLATFORM_CPU_QUEUE_MONITOR_T";
    }

    typedef  platform_system_status_type_t {
        type enumeration {
            enum Normal {
                value 1;
                description "Status is normal";
            }
            enum Minor-Fault {
                value 2;
                description "Status is Minor Fault,Fault";
            }
            enum Major-Fault {
                value 3;
                description "Status is Major Fault,Fault";
            }
        }
        description "type definition for PLATFORM_SYSTEM_STATUS_TYPE_T";
    }

    typedef  cml_cmm_storage_status_t {
        type enumeration {
            enum normal {
                value 1;
                description "Storage consumption <80% of reserved blocks";
            }
            enum critical {
                value 2;
                description "Storage consumption is  80% of reserved blocks";
            }
            enum alert {
                value 3;
                description "Storage consumption is an Alert leve";
            }
            enum undefined {
                value 4;
                description "Storage consumption state is unknown";
            }
        }
        description "type definition for CML_CMM_STORAGE_STATUS_T";
    }

    typedef  edfa_operating_mode_t {
        type enumeration {
            enum agc {
                value 1;
                description "Automatic Gain Control";
            }
            enum apc {
                value 2;
                description "Automatic Power Control";
            }
        }
        description "type definition for EDFA_OPERATING_MODE_T";
    }

    typedef  cml_temp_policy_t {
        type enumeration {
            enum sys-halt {
                value 1;
                description "System halt";
            }
            enum sys-reboot {
                value 2;
                description "System reboot";
            }
            enum none {
                value 3;
                description "None";
            }
        }
        description "type definition for CML_TEMP_POLICY_T";
    }

    typedef  cml_temp_threshold_t {
        type enumeration {
            enum emer-max {
                value 1;
                description "Emergency threshold maximum value";
            }
            enum alrt-max {
                value 2;
                description "Alert threshold maximum value";
            }
            enum crit-max {
                value 3;
                description "Critical threshold maximum value";
            }
            enum crit-min {
                value 4;
                description "Critical threshold minimum value";
            }
            enum alrt-min {
                value 5;
                description "Alert threshold minimum value";
            }
            enum emer-min {
                value 6;
                description "Emergency threshold minimum value";
            }
        }
        description "type definition for CML_TEMP_THRESHOLD_T";
    }

    typedef  platform_bgp_flowspec_mode_t {
        type enumeration {
            enum install-all {
                value 1;
                description "FLOWSPEC rules are prioritized. The all rules already installed are reinstalled when a new rule is tried to add.";
            }
            enum install-partial {
                value 2;
                description "FLOWSPEC rules are prioritized. Install not all rules already installed if possible to avoid unnecessarily reinstalling rules.";
            }
            enum no-prioritizing {
                value 3;
                description "FLOWSPEC rules are not prioritized. Install only rules requested to add but not reinstall any other rules when a new rule is tried to add.";
            }
        }
        description "type definition for PLATFORM_BGP_FLOWSPEC_MODE_T";
    }

    typedef  gps_satellite_system_t {
        type bits {
            bit gps {
                position 0;
                description "Global Position System";
            }
            bit galileo {
                position 1;
                description "Galileo System";
            }
            bit glonass {
                position 2;
                description "GLONASS System";
            }
            bit beidou {
                position 3;
                description "BEIDOU System";
            }
        }
        description "type definition for GPS_SATELLITE_SYSTEM_T";
    }

    typedef  cml_gps_gnss_status_t {
        type enumeration {
            enum OK {
                value 1;
                description "GPS GNSS status OK";
            }
            enum -- {
                value 2;
                description "GPS GNSS status --";
            }
        }
        description "type definition for CML_GPS_GNSS_STATUS_T";
    }

    typedef  cml_dpll_output_t {
        type enumeration {
            enum Enabled {
                value 1;
                description "DPLL output enabled";
            }
            enum Disabled {
                value 2;
                description "DPLL output disabled";
            }
        }
        description "type definition for CML_DPLL_OUTPUT_T";
    }

}
