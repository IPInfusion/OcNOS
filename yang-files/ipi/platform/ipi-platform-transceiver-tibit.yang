/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-transceiver-tibit.yang
*
*/

submodule ipi-platform-transceiver-tibit {

    yang-version 1.1;

    belongs-to  ipi-platform { prefix ipi-platform; }

    import feature-list {
        prefix feature-list;
        revision-date 2026-09-15;
    }

    import ipi-platform-transceiver-tibit-types {
        prefix ipi-platform-transceiver-tibit-types;
        revision-date 2022-07-14;
    }

    import ietf-yang-types {
        prefix yang;
        revision-date 2013-07-15;
    }

    import ipi-interface {
        prefix ipi-interface;
        revision-date 2026-03-10;
    }

    organization
        "IP Infusion Inc.";

    contact
        "Address: 3965 Freedom Circle, Suite 200, Santa Clara, CA 95054
         Phone: +1 408-4001900
         E-mail: support@ipinfusio.com
         Web: http://www.ipinfusion.com/";

    description
        "This module defines a schema for Tibit transceiver specific access in
                the platform datamodel";


    revision "2022-07-14" {
        description "Initial version for adding Tibit specific data and control for Tibit OLT MicroPlug transceiver";
        reference " 0.1.0.";
    }

    grouping olt-hardware-state {
        description
            "olt-hardware-state";
        leaf warranty-seal  {
            type  ipi-platform-transceiver-tibit-types:trans_tibit_cmm_warranty_seal_t;
            description "Indicate warranty seal cases.";
        } // END of warranty-seal definition.

        leaf operational-management  {
            type  ipi-platform-transceiver-tibit-types:trans_tibit_cmm_oper_mode_t;
            description "Indicate operational management mode. Only managed-mode is really
                        available regardless of this value in R2.3.0 and later.";
        } // END of operational-management definition.

        leaf pon-mode  {
            type  ipi-platform-transceiver-tibit-types:trans_tibit_cmm_pon_mode_t;
            description "Indicate PON mode.";
        } // END of pon-mode definition.

        leaf active-firmware-bank-id  {
            type  uint8;
            description "Indicate current active firmware bank identity.";
        } // END of active-firmware-bank-id definition.

        leaf next-active-firmware-bank-id  {
            type  uint8;
            description "Indicate next active firmware bank identity after rebooting.";
        } // END of next-active-firmware-bank-id definition.

        leaf management-vlan-tpid  {
            type  string {
                length "1..1965";
                pattern "[^?' =,>|]+";
            }
            description "Indicate the management VLAN TPID.";
        } // END of management-vlan-tpid definition.

        leaf management-vlan-id  {
            type  uint16 {
                 range "1..4094"  {
                    description "1..4094: Supported range 1 - 4094";
                 }
            }
            description "Indicate the management VLAN ID setting.";
        } // END of management-vlan-id definition.

        leaf pon-mac-address  {
            type  string {
                length "1..1965";
                pattern "[^?' =,>|]+";
            }
            description "Indicate the PON side MAC address.";
        } // END of pon-mac-address definition.

        leaf ethernet-mac-address  {
            type  string {
                length "1..1965";
                pattern "[^?' =,>|]+";
            }
            description "Indicate the ethernet side MAC address.";
        } // END of ethernet-mac-address definition.

        leaf pon-port-administrative-state  {
            type  ipi-platform-transceiver-tibit-types:trans_tibit_cmm_pon_status_t;
            description "Indicate the PON port administrative state.";
        } // END of pon-port-administrative-state definition.

        leaf pon-port-operational-status  {
            type  ipi-platform-transceiver-tibit-types:trans_tibit_cmm_pon_status_t;
            description "Indicate the PON port operational state.";
        } // END of pon-port-operational-status definition.

        leaf pon-link-count  {
            type  uint16;
            description "Indicate the PON link count.";
        } // END of pon-link-count definition.

    } // END of olt-hardware-state definition.
    grouping olt-firmware-state {
        description
            "olt-firmware-state";
        leaf bank-id  {
            type  uint8;
            description "Indicate the unique firmware bank value.";
        } // END of bank-id definition.

        leaf release-type  {
            type  string {
                length "1..1965";
                pattern "[^?' =,>|]+";
            }
            description "Indicate the firmware release type.";
        } // END of release-type definition.

        leaf major-version  {
            type  uint8;
            description "Indicate the firmware major version.";
        } // END of major-version definition.

        leaf minor-version  {
            type  uint8;
            description "Indicate the firmware minor version.";
        } // END of minor-version definition.

        leaf maintenance-version  {
            type  uint8;
            description "Indicate the firmware maintenance or patch version.";
        } // END of maintenance-version definition.

        leaf suffix-build-tag  {
            type  ipi-platform-transceiver-tibit-types:trans_tibit_cmm_string_t {
                length "0..2";
            }
            description "Indicate the suffix build tag.";
        } // END of suffix-build-tag definition.

        leaf suffix-build-number  {
            type  uint16;
            description "Indicate the suffix build number.";
        } // END of suffix-build-number definition.

        leaf build-sha  {
            type  ipi-platform-transceiver-tibit-types:trans_tibit_cmm_string_t {
                length "0..8";
            }
            description "Indicate the SHA checksum of the release build.";
        } // END of build-sha definition.

        leaf application-type  {
            type  ipi-platform-transceiver-tibit-types:trans_tibit_cmm_application_type_t;
            description "Indicate the application type of the release build.";
        } // END of application-type definition.

        leaf created-timestamp  {
            type  yang:date-and-time {
                pattern "\\d{4}-\\d{2}-\\d{2}T\\d{2}:\\d{2}:\\d{2}(\\.\\d+)?(Z|[\\+\\-]\\d{2}:\\d{2})";
                }
                description "Indicate the release created timestamp.";
            } // END of created-timestamp definition.

            leaf updated-timestamp  {
                type  yang:date-and-time {
                    pattern "\\d{4}-\\d{2}-\\d{2}T\\d{2}:\\d{2}:\\d{2}(\\.\\d+)?(Z|[\\+\\-]\\d{2}:\\d{2})";
                    }
                    description "Indicate the release updated timestamp.";
                } // END of updated-timestamp definition.

    } // END of olt-firmware-state definition.
    grouping olt-firmware-bank-top {
        description
            "olt-firmware-bank-top";

        list bank {
            key "bank-id";
            config false;
            description
                "List firmware info in the bank";
            leaf bank-id  {
                type  leafref {
                    path  "../state/bank-id";
                }
                description "A unique value of the firmware bank";
            } // END of bank-id definition.

            container state {
                config false;
                description
                    "Firmware info in the bank";
                uses olt-firmware-state;
            } // END of state-container definition.
        } // End of bank-list
    } // END of olt-firmware-bank-top definition.

    grouping  tibit-olt-microplug-grouping {
    description
        "Container for Tibit specific info of Tibit OLT MicroPlug transceiver";
    container tibit-olt-microplug {
        if-feature feature-list:HAVE_CMMD;
        if-feature feature-list:NOT_HAVE_TIBIT;
        config false;
        description
            "Container for Tibit specific info of Tibit OLT MicroPlug transceiver";
        container state {
            config false;
            description
                "Tibit OLT hardware state data";
            leaf interface-name  {
                type  leafref {
                    path  "/ipi-interface:interfaces/ipi-interface:interface/ipi-interface:name";
                }
                config false;
                description "Indicate the interface name for the Tibit OLT Microplug.";
            } // END of interface-name definition.

            uses olt-hardware-state;
        } // END of state-container definition.
        container firmware-banks {
            config false;
            description
                "Container for Tibit OLT firmware state";
            uses olt-firmware-bank-top;
        } // END of firmware-banks-container definition.
    } // END of tibit-olt-microplug-container definition.
    } // END of tibit-olt-microplug-grouping definition.


}
