/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-terminal-device-types.yang
*
*/

module ipi-platform-terminal-device-types {

    yang-version 1.1;

    namespace   "http://www.ipinfusion.com/yang/ocnos/ipi-platform-terminal-device-types";

    prefix "ipi-platform-terminal-device-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-platform-terminal-device-types";


    revision "2024-02-27" {
        description "Updated modulation-format 8qam-200g-ofec";
        reference " 0.3.4.";
    }

    revision "2024-02-22" {
        description "Updated modulation-format dp-qpsk-ofec";
        reference " 0.3.3.";
    }

    revision "2023-01-13" {
        description "Updated modulation-formate dp-qpsk-200g";
        reference " 0.3.2.";
    }

    revision "2022-08-10" {
        description "Debug hierarchy change";
        reference " 0.3.1.";
    }

    revision "2022-07-20" {
        description "Added new type to represent scientific notation";
        reference " 0.3.0.";
    }

    revision "2022-06-01" {
        description "Updated the yang file with feature";
        reference " 0.2.0.";
    }

    revision "2021-09-13" {
        description "Changed TERMINAL_DEVICE_TAI_DEBUG_FLAG_T bits position to start from 0";
        reference " 0.1.1.";
    }

    revision "2021-09-03" {
        description "Update descriptions of attribute";
        reference " 0.1.0.";
    }

    revision "2021-03-08" {
        description "Restructured module as per open-config style";
        reference "Initial Version";
    }



    typedef  terminal_device_scientific_notation_string {
        type string {
            pattern "[0-9]\\.?[0-9]?[0-9]?e-[0-9][0-9]?";
        }
        description "type definition for TERMINAL_DEVICE_SCIENTIFIC_NOTATION_STRING";
    }

    typedef  terminal_device_cmm_device_presence_t {
        type enumeration {
            enum present {
                value 1;
                description "transceiver present";
            }
            enum not-present {
                value 2;
                description "transceiver not present";
            }
            enum unknown {
                value 3;
                description "unknown";
            }
        }
        description "type definition for TERMINAL_DEVICE_CMM_DEVICE_PRESENCE_T";
    }

    typedef  terminal_device_cmm_card_type_t {
        type enumeration {
            enum UNKNOWN {
                value 0;
                description "unknown";
            }
            enum DCO {
                value 1;
                description "DCO";
            }
            enum ACO {
                value 2;
                description "ACO";
            }
            enum NON_COHERENT {
                value 3;
                description "non coherent card";
            }
        }
        description "type definition for TERMINAL_DEVICE_CMM_CARD_TYPE_T";
    }

    typedef  terminal_device_cmm_cfp_presence_t {
        type enumeration {
            enum present {
                value 1;
                description "present";
            }
            enum not-present {
                value 2;
                description "not present";
            }
            enum unknown {
                value 3;
                description "unknown";
            }
            enum not-applicable {
                value 4;
                description "not applicable";
            }
        }
        description "type definition for TERMINAL_DEVICE_CMM_CFP_PRESENCE_T";
    }

    typedef  terminal_device_cmm_mod_oper_status_t {
        type enumeration {
            enum initialize {
                value 1;
                description "initialize";
            }
            enum ready {
                value 2;
                description "ready";
            }
        }
        description "type definition for TERMINAL_DEVICE_CMM_MOD_OPER_STATUS_T";
    }

    typedef  terminal_device_cmm_netif_oper_status_t {
        type enumeration {
            enum unknown {
                value 0;
                description "unknown";
            }
            enum reset {
                value 1;
                description "reset";
            }
            enum initialize {
                value 2;
                description "initialize";
            }
            enum low-power {
                value 3;
                description "low-power";
            }
            enum high-power-up {
                value 4;
                description "high-power-up";
            }
            enum tx-off {
                value 5;
                description "tx-off";
            }
            enum tx-turn-on {
                value 6;
                description "tx-turn-on";
            }
            enum ready {
                value 7;
                description "ready";
            }
            enum tx-turn-off {
                value 8;
                description "tx-turn-off";
            }
            enum high-power-down {
                value 9;
                description "high-power-down";
            }
            enum fault {
                value 10;
                description "fault";
            }
        }
        description "type definition for TERMINAL_DEVICE_CMM_NETIF_OPER_STATUS_T";
    }

    typedef  terminal_device_cmm_dsp_oper_status_t {
        type enumeration {
            enum no-module {
                value 1;
                description "no-module";
            }
            enum waiting-configuration {
                value 2;
                description "waiting-configuration";
            }
            enum booting-first-half {
                value 3;
                description "booting-first-half";
            }
            enum waiting-aco-module {
                value 4;
                description "waiting-aco-module";
            }
            enum booting-aco-module {
                value 5;
                description "booting-aco-module";
            }
            enum waiting-rx-signal {
                value 6;
                description "waiting-rx-signal";
            }
            enum booting-second-half {
                value 7;
                description "booting-second-half";
            }
            enum ready {
                value 8;
                description "ready";
            }
            enum misc-config {
                value 9;
                description "misc-config";
            }
        }
        description "type definition for TERMINAL_DEVICE_CMM_DSP_OPER_STATUS_T";
    }

    typedef  terminal_device_cmm_prbs_type_t {
        type enumeration {
            enum none {
                value 0;
                description "none";
            }
            enum prbs7 {
                value 1;
                description "generates prbs 7 sequence";
            }
            enum prbs9 {
                value 2;
                description "generates prbs 9 sequence";
            }
            enum prbs11 {
                value 3;
                description "generates prbs 11 sequence";
            }
            enum prbs15 {
                value 4;
                description "generates prbs 15 sequence";
            }
            enum prbs20 {
                value 5;
                description "generates prbs 20 sequence";
            }
            enum prbs23 {
                value 6;
                description "generates prbs 23 sequence";
            }
            enum prbs31 {
                value 7;
                description "generates prbs 31 sequence";
            }
        }
        description "type definition for TERMINAL_DEVICE_CMM_PRBS_TYPE_T";
    }

    typedef  terminal_device_cmm_modulation_format_t {
        type enumeration {
            enum bpsk {
                value 1;
                description "Binary phase shift keying modulation scheme";
            }
            enum dp-bpsk {
                value 2;
                description "Dual polarization binary phase-shift keying";
            }
            enum qpsk {
                value 3;
                description "Quadrature phase shift keying";
            }
            enum dp-qpsk {
                value 4;
                description "Dual polarization quadrature phase shift keying";
            }
            enum 8-qam {
                value 5;
                description "8-quadrature amplitude modulation format";
            }
            enum dp-8-qam {
                value 6;
                description "Dual polarization 8-ary quadrature amplitude modulation format";
            }
            enum 16-qam {
                value 7;
                description "16-quadrature amplitude modulation format";
            }
            enum dp-16-qam {
                value 8;
                description "Dual polarization 16-ary quadrature amplitude modulation format";
            }
            enum 32-qam {
                value 9;
                description "32-quadrature amplitude modulation format";
            }
            enum dp-32-qam {
                value 10;
                description "Dual polarization 32-ary quadrature amplitude modulation format";
            }
            enum 64-qam {
                value 11;
                description "64-quadrature amplitude modulation format";
            }
            enum dp-64-qam {
                value 12;
                description "Dual polarization 64-ary quadrature amplitude modulation format";
            }
            enum dp-qpsk-200g {
                value 13;
                description "Dual polarization quadrature phase shift keying for speed 200G";
            }
            enum dp-qpsk-ofec {
                value 14;
                description "Dual polarization quadrature phase shift keying with OFEC";
            }
            enum 8qam-200g-ofec {
                value 15;
                description "8-quadrature amplitude modulation format for 200G with OFEC";
            }
        }
        description "type definition for TERMINAL_DEVICE_CMM_MODULATION_FORMAT_T";
    }

    typedef  terminal_device_cmm_fec_mode_t {
        type enumeration {
            enum 15per-everest {
                value 1;
                description "15percent Everest Compatible";
            }
            enum 15per-denali {
                value 2;
                description "15percent Denali Compatible";
            }
            enum otu4-g709 {
                value 3;
                description "OTU-4 G.709";
            }
            enum otu4-7per-staircase {
                value 5;
                description "OTU-4 7percent Staircase";
            }
            enum 25per-hc-sd2 {
                value 6;
                description "25percent HC SD2";
            }
        }
        description "type definition for TERMINAL_DEVICE_CMM_FEC_MODE_T";
    }

    typedef  terminal_device_cmm_optical_loopback_t {
        type enumeration {
            enum none {
                value 0;
                description "Set to default value";
            }
            enum shallow {
                value 1;
                description "Set line loopback to shallow";
            }
            enum deep {
                value 2;
                description "Set line loopback to deep";
            }
        }
        description "type definition for TERMINAL_DEVICE_CMM_OPTICAL_LOOPBACK_T";
    }

    typedef  terminal_device_cmm_optical_fec_t {
        type enumeration {
            enum none {
                value 0;
                description "none";
            }
            enum rs {
                value 1;
                description "Set FEC to Reed Solomon FEC type";
            }
            enum fc {
                value 2;
                description "Set FEC to Fire Code FEC type";
            }
        }
        description "type definition for TERMINAL_DEVICE_CMM_OPTICAL_FEC_T";
    }

    typedef  terminal_device_cmm_grid_spacing_t {
        type enumeration {
            enum 6.25-ghz {
                value 0;
                description "6.25-ghz";
            }
            enum 12.5-ghz {
                value 1;
                description "12.5-ghz";
            }
            enum 25-ghz {
                value 2;
                description "25-ghz";
            }
            enum 33-ghz {
                value 3;
                description "33-ghz";
            }
            enum 50-ghz {
                value 4;
                description "50-ghz";
            }
            enum 100-ghz {
                value 5;
                description "100-ghz";
            }
        }
        description "type definition for TERMINAL_DEVICE_CMM_GRID_SPACING_T";
    }

    typedef  terminal_device_cmm_netif_rx_otu_alarm_t {
        type bits {
            bit loss-of-frame {
                position 0;
                description "loss of frame";
            }
            bit loss-of-multiframe {
                position 1;
                description "loss-of-multiframe";
            }
            bit backward-defect-detection {
                position 2;
                description "backward-defect-detection";
            }
            bit alarm-indication-signal {
                position 3;
                description "alarm-indication-signal";
            }
        }
        description "type definition for TERMINAL_DEVICE_CMM_NETIF_RX_OTU_ALARM_T";
    }

    typedef  terminal_device_cmm_netif_rx_odu_alarm_t {
        type bits {
            bit backward-defect-indication {
                position 0;
                description "backward-defect-indication";
            }
            bit alarm-indication-signal {
                position 1;
                description "alarm-indication-signal";
            }
            bit open-connection-indication {
                position 2;
                description "open-connection-indication";
            }
            bit locked-defect {
                position 3;
                description "locked-defect";
            }
        }
        description "type definition for TERMINAL_DEVICE_CMM_NETIF_RX_ODU_ALARM_T";
    }

    typedef  terminal_device_cmm_netif_rx_opu_alarm_t {
        type bits {
            bit payload-Mismatch {
                position 0;
                description "payload-Mismatch";
            }
            bit client-signal-fail {
                position 1;
                description "client-signal-fail";
            }
        }
        description "type definition for TERMINAL_DEVICE_CMM_NETIF_RX_OPU_ALARM_T";
    }

    typedef  terminal_device_cmm_netif_rx_ts_alarm_t {
        type bits {
            bit loss-of-lock {
                position 0;
                description "loss-of-lock";
            }
        }
        description "type definition for TERMINAL_DEVICE_CMM_NETIF_RX_TS_ALARM_T";
    }

    typedef  terminal_device_cmm_netif_pre_fec_ber_signal_alarm_t {
        type enumeration {
            enum pre-fec-ber-signal-degrade {
                value 1;
                description "pre-fec-ber-signal-degrade";
            }
            enum pre-fec-ber-signal-failure {
                value 2;
                description "pre-fec-ber-signal-failure";
            }
        }
        description "type definition for TERMINAL_DEVICE_CMM_NETIF_PRE_FEC_BER_SIGNAL_ALARM_T";
    }

    typedef  terminal_device_cmm_netif_input_power_alarm_t {
        type enumeration {
            enum input-power-low-alarm {
                value 1;
                description "input-power-low-alarm";
            }
            enum input-power-low-warning {
                value 2;
                description "input-power-low-warning";
            }
            enum input-power-high-warning {
                value 3;
                description "input-power-high-warning";
            }
            enum input-power-high-alarm {
                value 4;
                description "input-power-high-alarm";
            }
        }
        description "type definition for TERMINAL_DEVICE_CMM_NETIF_INPUT_POWER_ALARM_T";
    }

    typedef  terminal_device_cmm_netif_output_power_alarm_t {
        type enumeration {
            enum output-power-low-alarm {
                value 1;
                description "output-power-low-alarm";
            }
            enum output-power-low-warning {
                value 2;
                description "output-power-low-warning";
            }
            enum output-power-high-warning {
                value 3;
                description "output-power-high-warning";
            }
            enum output-power-high-alarm {
                value 4;
                description "output-power-high-alarm";
            }
        }
        description "type definition for TERMINAL_DEVICE_CMM_NETIF_OUTPUT_POWER_ALARM_T";
    }

    typedef  terminal_device_cmm_hostif_pcs_alarm_t {
        type bits {
            bit loss-of-signal {
                position 0;
                description "loss-of-signal";
            }
            bit loss-of-frame {
                position 1;
                description "loss-of-frame";
            }
            bit illegal-alignment-marker {
                position 2;
                description "illegal-alignment-marker";
            }
            bit remote-fault {
                position 3;
                description "remote-fault";
            }
            bit local-fault {
                position 4;
                description "local-fault";
            }
            bit high-BER {
                position 5;
                description "high-BER";
            }
            bit BIP-error {
                position 6;
                description "BIP-error";
            }
            bit deskew-error {
                position 7;
                description "deskew-error";
            }
            bit loss-of-block-lock {
                position 8;
                description "loss-of-block-lock";
            }
            bit loss-of-alignment-marker-lock {
                position 9;
                description "loss-of-alignment-marker-lock";
            }
            bit loss-of-alignment {
                position 10;
                description "loss-of-alignment";
            }
            bit OPU-client-signal-fail {
                position 11;
                description "OPU-client-signal-fail";
            }
            bit error-blocks-detected {
                position 12;
                description "error-blocks-detected";
            }
        }
        description "type definition for TERMINAL_DEVICE_CMM_HOSTIF_PCS_ALARM_T";
    }

    typedef  terminal_device_cmm_hostif_fault_status_alarm_t {
        type bits {
            bit tx-host-lol-l0 {
                position 0;
                description "tx-host-lol-l0";
            }
            bit tx-host-lol-l1 {
                position 1;
                description "tx-host-lol-l1";
            }
            bit tx-host-lol-l2 {
                position 2;
                description "tx-host-lol-l2";
            }
            bit tx-host-lol-l3 {
                position 3;
                description "tx-host-lol-l3";
            }
            bit ingress-aps-msg-rcvd {
                position 4;
                description "ingress-aps-msg-rcvd";
            }
            bit deskew-lock-fault {
                position 5;
                description "deskew-lock-fault";
            }
            bit out-of-align {
                position 6;
                description "out-of-align";
            }
            bit loss-of-align {
                position 7;
                description "loss-of-align";
            }
        }
        description "type definition for TERMINAL_DEVICE_CMM_HOSTIF_FAULT_STATUS_ALARM_T";
    }

    typedef  terminal_device_cmm_mod_temp_alarm_t {
        type enumeration {
            enum temperature-low-alarm {
                value 1;
                description "temperature-low-alarm";
            }
            enum temperature-low-waring {
                value 2;
                description "temperature-low-waring";
            }
            enum temperature-high-warning {
                value 3;
                description "temperature-high-warning";
            }
            enum temperature-high-alarm {
                value 4;
                description "temperature-high-alarm";
            }
        }
        description "type definition for TERMINAL_DEVICE_CMM_MOD_TEMP_ALARM_T";
    }

    typedef  terminal_device_cmm_mod_volt_alarm_t {
        type enumeration {
            enum power-low-alarm {
                value 1;
                description "power-low-alarm";
            }
            enum power-low-waring {
                value 2;
                description "power-low-waring";
            }
            enum power-high-warning {
                value 3;
                description "power-high-warning";
            }
            enum power-high-alarm {
                value 4;
                description "power-high-alarm";
            }
        }
        description "type definition for TERMINAL_DEVICE_CMM_MOD_VOLT_ALARM_T";
    }

    typedef  terminal_device_cmm_mod_general_status_alarm_t {
        type bits {
            bit hw-interlock {
                position 0;
                description "hw-interlock";
            }
            bit tx-loss-of-signal-functionality {
                position 1;
                description "tx-loss-of-signal-functionality";
            }
            bit rx-loss-of-signal {
                position 2;
                description "rx-loss-of-signal";
            }
            bit rx-network-loss-of-lock {
                position 3;
                description "rx-network-loss-of-lock";
            }
            bit tx-host-loss-of-lock {
                position 4;
                description "tx-host-loss-of-lock";
            }
            bit hostlane-out-of-alignment {
                position 5;
                description "hostlane-out-of-alignment";
            }
        }
        description "type definition for TERMINAL_DEVICE_CMM_MOD_GENERAL_STATUS_ALARM_T";
    }

    typedef  terminal_device_cmm_mod_fault_status_alarm_t {
        type bits {
            bit over-temperature-fault {
                position 0;
                description "over-temperature-fault";
            }
            bit hardware-fault {
                position 1;
                description "hardware-fault";
            }
            bit initialization-fault {
                position 2;
                description "initialization-fault";
            }
            bit power-supply-fault {
                position 3;
                description "power-supply-fault";
            }
            bit checksum-fault {
                position 4;
                description "checksum-fault";
            }
        }
        description "type definition for TERMINAL_DEVICE_CMM_MOD_FAULT_STATUS_ALARM_T";
    }

    typedef  terminal_device_tai_debug_t {
        type bits {
            bit module {
                position 0;
                description "TAI module-level";
            }
            bit netif {
                position 1;
                description "TAI netif-level";
            }
            bit hostif {
                position 2;
                description "TAI hostif-level";
            }
        }
        description "type definition for TERMINAL_DEVICE_TAI_DEBUG_T";
    }

    typedef  terminal_device_cmm_grid_support_t {
        type bits {
            bit grid-6.25-ghz {
                position 0;
                description "grid-6.25-ghz";
            }
            bit grid-12.5-ghz {
                position 1;
                description "grid-12.5-ghz";
            }
            bit grid-25-ghz {
                position 2;
                description "grid-25-ghz";
            }
            bit grid-33-ghz {
                position 3;
                description "grid-33-ghz";
            }
            bit grid-50-ghz {
                position 4;
                description "grid-50-ghz";
            }
            bit grid-100-ghz {
                position 5;
                description "grid-100-ghz";
            }
        }
        description "type definition for TERMINAL_DEVICE_CMM_GRID_SUPPORT_T";
    }

    typedef  terminal_device_cmm_tx_frequency_t {
        type string {
            pattern "[0-9]{1,15}(\\.[0-9]{1,12})?([MmGgTt])?[Hh][Zz]";
        }
        description "type definition for TERMINAL_DEVICE_CMM_TX_FREQUENCY_T";
    }

    typedef  cml_cmm_link_down_t {
        type bits {
            bit pre-fec-ber {
                position 0;
                description "link down policy for pre-fec-ber";
            }
            bit q-margin {
                position 1;
                description "link down policy for q-margin";
            }
            bit snr {
                position 2;
                description "link down policy for snr";
            }
            bit chromatic-dispersion {
                position 3;
                description "link down policy for chromatic-dispersion";
            }
            bit rx-power {
                position 4;
                description "link down policy for rx-power";
            }
        }
        description "type definition for CML_CMM_LINK_DOWN_T";
    }

}
