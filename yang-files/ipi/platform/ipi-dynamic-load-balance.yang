/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dynamic-load-balance.yang
*
*/

module ipi-dynamic-load-balance {

    yang-version 1.1;

    namespace   "http://www.ipinfusion.com/yang/ocnos/ipi-dynamic-load-balance";

    prefix "ipi-dynamic-load-balance";

    import ipi-dynamic-load-balance-types {
        prefix ipi-dynamic-load-balance-types;
        revision-date 2025-06-02;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Dynamic load balance";


    revision "2025-07-07" {
        description "Enabling port-quality-load and rate-weigtage configuration in TH4, TD4, TH3, TD3.";
        reference " 0.1.7.";
    }

    revision "2025-05-23" {
        description "Adding feature flag HAVE_DLB to port-quality-load/config container.";
        reference " 0.1.6.";
    }

    revision "2025-05-20" {
        description "Added support for configuring port-quality-load and rate-weightage for dynamic load balance.";
        reference " 0.1.5.";
    }

    revision "2025-04-21" {
        description "Modified Inactivity-Timer value";
        reference " 0.1.4.";
    }

    revision "2025-04-17" {
        description "Added Flow Monitoring attributes monitor and sampling-rate";
        reference " 0.1.3.";
    }

    revision "2025-04-04" {
        description "Adding cli-commands for dynamic-laod-balance mode";
        reference " 0.1.2.";
    }

    revision "2025-04-02" {
        description "Removing dynamic-load-balance-top container at top";
        reference " 0.1.1.";
    }

    revision "2025-02-28" {
        description "Initial Version";
        reference " 0.1.0.";
    }

    grouping dynamic-load-balance-config {
        description
            "Top level grouping of dynamic load balance config";
        leaf enable  {
            if-feature feature-list:HAVE_DLB;
            type  empty;
            description "Use this attribute to enable or disable dynamic load balance.";
        } // END of enable definition.

        leaf inactivity-timer  {
            if-feature feature-list:HAVE_DLB;
            type  uint32 {
                 range "16..32767"  {
                    description "16..32767: Supported range 16 - 32767";
                 }
            }
            description "inactivity timer for dynamic load balance";
        } // END of inactivity-timer definition.

        leaf-list ethertype  {
            if-feature feature-list:HAVE_AI_ML;
            type  string {
                length "1..1965";
                pattern "0x(8100|88a8|0800|0806|86dd)";
            }
            description "ether type for dynamic load balance";
        } // END of ethertype definition.

        leaf flowset-size  {
            if-feature feature-list:HAVE_DLB;
            type  ipi-dynamic-load-balance-types:dlb_flowset_size_t;
            description "Flowset Size for dynamic load balance";
        } // END of flowset-size definition.

        leaf mode  {
            if-feature feature-list:HAVE_DLB;
            type  ipi-dynamic-load-balance-types:dlb_mode_t;
            description "mode of dynamic load balance";
        } // END of mode definition.

        leaf threshold  {
            if-feature feature-list:HAVE_DLB;
            type  uint8 {
                 range "1..100"  {
                    description "1..100: Supported range 1 - 100";
                 }
            }
            description "attribute to set dynamic load balance to threshold.";
        } // END of threshold definition.

        leaf quality-delta  {
            if-feature feature-list:HAVE_DLB;
            type  uint8 {
                 range "0..7"  {
                    description "0..7: Supported range 0 - 7";
                 }
            }
            description "attribute to set dynamic load balance to quality-delta.";
        } // END of quality-delta definition.

        leaf monitor  {
            if-feature feature-list:HAVE_AI_ML;
            type  empty;
            description "Enable flow monitoring for dynamic load balance";
        } // END of monitor definition.

        leaf sampling-rate  {
            if-feature feature-list:HAVE_AI_ML;
            type  uint32 {
                 range "1..4294967295"  {
                    description "1..4294967295: Supported range 1 - 4294967295";
                 }
            }
            description "attribute to set sampling-rate for Flow monitoring.";
        } // END of sampling-rate definition.

        leaf rate-weightage  {
            if-feature feature-list:HAVE_DLB;
            type  uint8 {
                 range "1..100"  {
                    description "1..100: Supported range 1 - 100";
                 }
            }
            description "attribute to set dynamic load balance to rate-weightage.";
        } // END of rate-weightage definition.

    } // END of dynamic-load-balance-config definition.
    grouping port-quality-load-config {
        description
            "Grouping of port quality";
        leaf min-value  {
            type  uint8 {
                 range "1..100"  {
                    description "1..100: Supported range 1 - 100";
                 }
            }
            mandatory true;
            description "attribute to set dynamic load balance port quality load min value.";
        } // END of min-value definition.

        leaf max-value  {
            type  uint8 {
                 range "1..100"  {
                    description "1..100: Supported range 1 - 100";
                 }
            }
            mandatory true;
            description "attribute to set dynamic load balance port quality load max value.";
        } // END of max-value definition.

    } // END of port-quality-load-config definition.

    grouping  dynamic-load-balance-grouping {
    description
        "Dynamic Load Balance";
    container dynamic-load-balance {
        if-feature feature-list:HAVE_BROADCOM;
        if-feature feature-list:NOT_HAVE_DUNE;
        description
            "Dynamic Load Balance";
        container config {
            description
                "Config container";
            uses dynamic-load-balance-config;
        } // END of config-container definition.
        container state {
            config false;
            description
                "container for runtime state of dlb";
            uses dynamic-load-balance-config;
        } // END of state-container definition.
        container port-quality-load {
            if-feature feature-list:HAVE_DLB;
            description
                "Top level port-quality-load container";
            container config {
                presence "yes";
                description
                    "Config container for port-quality-load";
                uses port-quality-load-config;
            } // END of config-container definition.
            container state {
                config false;
                description
                    "State container for port-quality-load";
                uses port-quality-load-config;
            } // END of state-container definition.
        } // END of port-quality-load-container definition.
    } // END of dynamic-load-balance-container definition.
    } // END of dynamic-load-balance-grouping definition.

    uses dynamic-load-balance-grouping;

}
