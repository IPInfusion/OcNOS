/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-terminal-device.yang
*
*/

module ipi-platform-terminal-device {

    yang-version 1.1;

    namespace   "http://www.ipinfusion.com/yang/ocnos/ipi-platform-terminal-device";

    prefix "ipi-platform-terminal-device";

    import ietf-yang-types {
        prefix yang;
        revision-date 2013-07-15;
    }

    import cml-data-types {
        prefix cml-data-types;
        revision-date 2026-05-15;
    }

    import ipi-platform {
        prefix ipi-platform;
        revision-date 2026-08-14;
    }

    import ipi-platform-terminal-device-types {
        prefix ipi-platform-terminal-device-types;
        revision-date 2024-02-27;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Coherent Optics Terminal Device";


    revision "2024-02-27" {
        description "Updated modulation-format 8qam-200g-ofec";
        reference " 0.7.10.";
    }

    revision "2024-02-22" {
        description "Updated modulation-format dp-qpsk-ofec";
        reference " 0.7.9.";
    }

    revision "2024-02-20" {
        description "Added a utils_func normalize_freq_to_hz on the output laser frequency for the optical network interface";
        reference " 0.7.8.";
    }

    revision "2024-01-22" {
        description "Removed if-feature DNX check for hardware-profile seamless-bfd (enable|disable)";
        reference " 0.7.7.";
    }

    revision "2023-01-13" {
        description "updated terminal_device_cmm_modulation_format_t type";
        reference " 0.7.3.";
    }

    revision "2022-12-02" {
        description "Added implicit-delete tag for optical-port/config container";
        reference " 0.7.2.";
    }

    revision "2022-11-29" {
        description "Addressed make cmlgen warnings";
        reference " 0.7.1.";
    }

    revision "2022-11-22" {
        description "Changed vendor-name attribute type to accept white spaces";
        reference " 0.7.0.";
    }

    revision "2022-08-10" {
        description "Debug hierarchy change";
        reference " 0.6.3.";
    }

    revision "2022-07-25" {
        description "Update if-feature for Notification";
        reference " 0.6.2.";
    }

    revision "2022-07-22" {
        description "Updated ipi-platform-profile submodule";
        reference " 0.6.1.";
    }

    revision "2022-07-20" {
        description "Added scientific notation pattern for pre-fec threshold configuration attributes";
        reference " 0.6.0.";
    }

    revision "2022-07-14" {
        description "Add Tibit specific data and control for Tibit OLT MicroPlug transceiver";
        reference " 0.5.5.";
    }

    revision "2022-07-12" {
        description "New notifications added for FAN rpm changes";
        reference " 0.5.4.";
    }

    revision "2022-07-07" {
        description "Added datamodel file for SFF-8024 type definitions";
        reference " 0.5.3.";
    }

    revision "2022-06-28" {
        description "Initial version for CMIS transceivers attributes";
        reference " 0.5.2.";
    }

    revision "2022-06-27" {
        description "Added new attribute for hardware-profile seamless-bfd (enable|disable)";
        reference " 0.5.1.";
    }

    revision "2022-06-01" {
        description "Updated the yang file with feature";
        reference " 0.5.0.";
    }

    revision "2022-03-03" {
        description "Enclosed the objectlist with container";
        reference " 0.7.6.";
    }

    revision "2022-01-23" {
        description "Changed operational-mode max value from 6 to 9";
        reference " 0.7.5.";
    }

    revision "2022-01-19" {
        description "Added implicit-delete tag for monitor-thresholds for config container";
        reference " 0.7.4.";
    }

    revision "2021-09-17" {
        description "Added when tag check not allow the config when module is disabled";
        reference "Initial Version";
    }

    revision "2021-09-03" {
        description "Update descriptions of attribute";
        reference "Initial Version";
    }

    revision "2021-03-08" {
        description "Initial Version";
        reference "Initial Version";
    }

    grouping terminal-host-interface-alarms-state {
        description
            "terminal-host-interface-alarms-state";
        leaf egress-pcs  {
            type  ipi-platform-terminal-device-types:terminal_device_cmm_hostif_pcs_alarm_t;
            description "Specifies current Host interface Egress PhysicalCodingSublayer Status.";
        } // END of egress-pcs definition.

        leaf interface-fault  {
            type  ipi-platform-terminal-device-types:terminal_device_cmm_hostif_fault_status_alarm_t;
            description "Specifies current Host interface Fault Status.";
        } // END of interface-fault definition.

        leaf ingress-pcs  {
            type  ipi-platform-terminal-device-types:terminal_device_cmm_hostif_pcs_alarm_t;
            description "Specifies current Host interface Ingress PhysicalCodingSublayer
                        Status.";
        } // END of ingress-pcs definition.

    } // END of terminal-host-interface-alarms-state definition.
    grouping terminal-host-interface-alarms {
        description
            "terminal-host-interface-alarms";
        container host-interface-alarms {
            description
                "Host-interface status data";
            container state {
                config false;
                description
                    "Host-interface status data";
                uses terminal-host-interface-alarms-state;
            } // END of state-container definition.
        } // END of host-interface-alarms-container definition.
    } // END of terminal-host-interface-alarms definition.
    grouping terminal-host-interface-event-counters-tx-lol {
        description
            "terminal-host-interface-event-counters-tx-lol";
        leaf lane0  {
            type  yang:counter32;
            description "Specifies tx host loss of lock lane 0 event count value.";
        } // END of lane0 definition.

        leaf lane1  {
            type  yang:counter32;
            description "Specifies tx host loss of lock lane 1 event count value.";
        } // END of lane1 definition.

        leaf lane2  {
            type  yang:counter32;
            description "Specifies tx host loss of lock lane 2 event count value.";
        } // END of lane2 definition.

        leaf lane3  {
            type  yang:counter32;
            description "Specifies tx host loss of lock lane 3 event count value.";
        } // END of lane3 definition.

    } // END of terminal-host-interface-event-counters-tx-lol definition.
    grouping terminal-host-interface-event-counters-ingress-pcs {
        description
            "terminal-host-interface-event-counters-ingress-pcs";
        leaf bip-error  {
            type  yang:counter32;
            description "Specifies ingress PCS BIP error event count value.";
        } // END of bip-error definition.

        leaf deskew-error  {
            type  yang:counter32;
            description "Specifies ingress PCS deskew error event count value.";
        } // END of deskew-error definition.

        leaf error-blocks-detected  {
            type  yang:counter32;
            description "Specifies ingress PCS error blocks detected event count value.";
        } // END of error-blocks-detected definition.

        leaf high-ber  {
            type  yang:counter32;
            description "Specifies ingress PCS high BER event count value.";
        } // END of high-ber definition.

        leaf illegal-alignment-marker  {
            type  yang:counter32;
            description "Specifies ingress PCS illegal alignment marker event count value.";
        } // END of illegal-alignment-marker definition.

        leaf local-fault  {
            type  yang:counter32;
            description "Specifies ingress PCS local fault event count value.";
        } // END of local-fault definition.

        leaf loss-of-alignment  {
            type  yang:counter32;
            description "Specifies ingress PCS loss of alignment event count value.";
        } // END of loss-of-alignment definition.

        leaf loss-of-alignment-marker-lock  {
            type  yang:counter32;
            description "Specifies ingress PCS loss of alignment marker lock event count value.";
        } // END of loss-of-alignment-marker-lock definition.

        leaf loss-of-block-lock  {
            type  yang:counter32;
            description "Specifies ingress PCS loss of block lock event count value.";
        } // END of loss-of-block-lock definition.

        leaf loss-of-frame  {
            type  yang:counter32;
            description "Specifies ingress PCS loss of frame event count value.";
        } // END of loss-of-frame definition.

        leaf loss-of-signal  {
            type  yang:counter32;
            description "Specifies ingress PCS loss of signal event count value.";
        } // END of loss-of-signal definition.

        leaf opu-client-signal-fail  {
            type  yang:counter32;
            description "Specifies ingress PCS OPU client signal fail event count value.";
        } // END of opu-client-signal-fail definition.

        leaf remote-fault  {
            type  yang:counter32;
            description "Specifies ingress PCS remote fault event count value.";
        } // END of remote-fault definition.

    } // END of terminal-host-interface-event-counters-ingress-pcs definition.
    grouping terminal-host-interface-event-counters-ingress-aps {
        description
            "terminal-host-interface-event-counters-ingress-aps";
        leaf msg-received  {
            type  yang:counter32;
            description "Specifies ingress APS message received event count value.";
        } // END of msg-received definition.

    } // END of terminal-host-interface-event-counters-ingress-aps definition.
    grouping terminal-host-interface-event-counters-egress-pcs {
        description
            "terminal-host-interface-event-counters-egress-pcs";
        leaf bip-error  {
            type  uint32;
            description "Specifies egress PCS BIP error event count value.";
        } // END of bip-error definition.

        leaf deskew-error  {
            type  uint32;
            description "Specifies egress PCS deskew error event count value.";
        } // END of deskew-error definition.

        leaf error-blocks-detected  {
            type  uint32;
            description "Specifies egress PCS error blocks detected event count value.";
        } // END of error-blocks-detected definition.

        leaf high-ber  {
            type  uint32;
            description "Specifies egress PCS high BER event count value.";
        } // END of high-ber definition.

        leaf illegal-alignment-marker  {
            type  uint32;
            description "Specifies egress PCS illegal alignment event count value.";
        } // END of illegal-alignment-marker definition.

        leaf local-fault  {
            type  uint32;
            description "Specifies egress PCS local fault event count value.";
        } // END of local-fault definition.

        leaf loss-of-alignment  {
            type  uint32;
            description "Specifies egress PCS loss of alignment event count value.";
        } // END of loss-of-alignment definition.

        leaf loss-of-alignment-marker-lock  {
            type  uint32;
            description "Specifies egress PCS loss of alignment marker lock event count value.";
        } // END of loss-of-alignment-marker-lock definition.

        leaf loss-of-block-lock  {
            type  uint32;
            description "Specifies egress PCS loss of block lock event count value.";
        } // END of loss-of-block-lock definition.

        leaf loss-of-frame  {
            type  uint32;
            description "Specifies egress PCS loss of frame event count value.";
        } // END of loss-of-frame definition.

        leaf loss-of-signal  {
            type  uint32;
            description "Specifies egress PCS loss of signal event count value.";
        } // END of loss-of-signal definition.

        leaf opu-client-signal-fail  {
            type  uint32;
            description "Specifies egress PCS OPU client signal fail event count value.";
        } // END of opu-client-signal-fail definition.

        leaf remote-fault  {
            type  uint32;
            description "Specifies egress PCS remote fault event count value.";
        } // END of remote-fault definition.

    } // END of terminal-host-interface-event-counters-egress-pcs definition.
    grouping terminal-host-interface-event-counters {
        description
            "terminal-host-interface-event-counters";
        leaf deskew-lock-fault  {
            type  yang:counter32;
            description "Specifies deskew lock fault event count value.";
        } // END of deskew-lock-fault definition.

        leaf loss-of-align  {
            type  yang:counter32;
            description "Specifies loss of alignment event count value.";
        } // END of loss-of-align definition.

        leaf out-of-align  {
            type  yang:counter32;
            description "Specifies out of alignment event count value.";
        } // END of out-of-align definition.

    } // END of terminal-host-interface-event-counters definition.
    grouping terminal-host-interface-error-counters {
        description
            "terminal-host-interface-error-counters";
        leaf fec-uncorrected-blocks  {
            type  uint64;
            description "Specifies the Host Interface Uncorrected Fec Block count value.";
        } // END of fec-uncorrected-blocks definition.

    } // END of terminal-host-interface-error-counters definition.
    grouping terminal-host-interface-state {
        description
            "terminal-host-interface-state";
        leaf current-pre-fec-ber  {
            type  uint64;
            units "1e-18";
            description "Specifies the Host Interface current PRE FEC Bit Error Rate per 1e-18
                        BER Period.";
        } // END of current-pre-fec-ber definition.

    } // END of terminal-host-interface-state definition.
    grouping terminal-host-interface-config {
        description
            "terminal-host-interface-config";
        leaf host-index  {
            type  uint8 {
                 range "0..15"  {
                    description "0..15: Supported range 0 - 15";
                 }
            }
            description "Index of host interface in a coherent optical module.";
        } // END of host-index definition.

        leaf fec-type  {
            type  ipi-platform-terminal-device-types:terminal_device_cmm_optical_fec_t;
            default "none";
            description "Fec type for host-interface. The default value is none.";
        } // END of fec-type definition.

        leaf loopback-type  {
            type  ipi-platform-terminal-device-types:terminal_device_cmm_optical_loopback_t;
            default "none";
            description "Loopback type for host-interface. The default value is none.";
        } // END of loopback-type definition.

    } // END of terminal-host-interface-config definition.
    grouping terminal-host-interface-top {
        description
            "terminal-host-interface-top";
        container host-interfaces {
            when " /ipi-platform-terminal-device:terminal-device/ipi-platform-terminal-device:coherent-modules/ipi-platform-terminal-device:coherent-module/ipi-platform-terminal-device:config/ipi-platform-terminal-device:service-enable ";
            description
                "host-interfaces configuration data";

            list interface {
                key "host-index";
                description
                    "A list to store all host-interfaces";
                leaf host-index  {
                    type  leafref {
                        path  "../config/host-index";
                    }
                    description "Index of host interface in a coherent optical module.";
                } // END of host-index definition.

                container config {
                    description
                        "host-interface configuration data";
                    uses terminal-host-interface-config;
                } // END of config-container definition.
                container state {
                    config false;
                    description
                        "host-interface state data";
                    container counters {
                        config false;
                        description
                            "host-interface counters";
                        container errors {
                            config false;
                            description
                                "host-interface error counters";
                            uses terminal-host-interface-error-counters;
                        } // END of errors-container definition.
                        container events {
                            config false;
                            description
                                "Event counters for host-interface";
                            uses terminal-host-interface-event-counters;
                        } // END of events-container definition.
                        container egress-pcs-events {
                            config false;
                            description
                                "Egress PCS host-interface event counters";
                            uses terminal-host-interface-event-counters-egress-pcs;
                        } // END of egress-pcs-events-container definition.
                        container ingress-aps-events {
                            config false;
                            description
                                "Ingress APS host-interface event counters";
                            uses terminal-host-interface-event-counters-ingress-aps;
                        } // END of ingress-aps-events-container definition.
                        container ingress-pcs-events {
                            config false;
                            description
                                "Ingress PCS host-interface event counters";
                            uses terminal-host-interface-event-counters-ingress-pcs;
                        } // END of ingress-pcs-events-container definition.
                        container tx-loss-of-lock-events {
                            config false;
                            description
                                "TX loss-of-lock host-interface event counters";
                            uses terminal-host-interface-event-counters-tx-lol;
                        } // END of tx-loss-of-lock-events-container definition.
                    } // END of counters-container definition.
                    uses terminal-host-interface-config;
                    uses terminal-host-interface-state;
                } // END of state-container definition.
                uses terminal-host-interface-alarms;
                uses terminal-host-interface-assignments-top;
            } // End of interface-list
        } // END of host-interfaces-container definition.
    } // END of terminal-host-interface-top definition.
    grouping terminal-device-optical-port-state {
        description
            "terminal-device-optical-port-state";
        leaf oper-status  {
            type  ipi-platform-terminal-device-types:terminal_device_cmm_mod_oper_status_t;
            description "Operational status of the coherent optical module.";
        } // END of oper-status definition.

    } // END of terminal-device-optical-port-state definition.
    grouping terminal-device-optical-port-config {
        description
            "terminal-device-optical-port-config";
        leaf shutdown  {
            when " /ipi-platform-terminal-device:terminal-device/ipi-platform-terminal-device:coherent-modules/ipi-platform-terminal-device:coherent-module/ipi-platform-terminal-device:config/ipi-platform-terminal-device:service-enable ";
            type  empty;
            description "Indicates if coherent optical module is shutdown or not.";
        } // END of shutdown definition.

    } // END of terminal-device-optical-port-config definition.
    grouping terminal-device-optical-port-top {
        description
            "terminal-device-optical-port-top";
        container optical-port {
            description
                "optical port configuration data";
            container config {
                description
                    "Configuration data for optical-port";
                uses terminal-device-optical-port-config;
            } // END of config-container definition.
            container state {
                config false;
                description
                    "Operational state data for optical-port";
                uses terminal-device-optical-port-config;
                uses terminal-device-optical-port-state;
            } // END of state-container definition.
        } // END of optical-port-container definition.
    } // END of terminal-device-optical-port-top definition.
    grouping terminal-device-network-interface-config {
        description
            "terminal-device-network-interface-config";
        leaf net-index  {
            type  uint8 {
                 range "0..15"  {
                    description "0..15: Supported range 0 - 15";
                 }
            }
            description "Index of network interface in a coherent optical module.";
        } // END of net-index definition.

        leaf differential-encoding  {
            type  empty;
            description "Enable differential encoding on a optical network interface.";
        } // END of differential-encoding definition.

        leaf fec-mode  {
            // when " !ipi-platform-terminal-device:terminal-device/coherent-modules/coherent-module/network-interfaces/interface/config/operational-mode ";
            type  ipi-platform-terminal-device-types:terminal_device_cmm_fec_mode_t;
            default "15per-denali";
            description "FEC mode for network interface. Default is 15per-denali.";
        } // END of fec-mode definition.

        leaf frequency  {
            type  ipi-platform-terminal-device-types:terminal_device_cmm_tx_frequency_t {
                length "1..1965";
            }
            description "Specifies the output laser frequency for the optical network interface
                        in terms of Hz, MHz, GHz or THz.";
        } // END of frequency definition.

        leaf loopback-type  {
            type  ipi-platform-terminal-device-types:terminal_device_cmm_optical_loopback_t;
            default "none";
            description "Specifies the loopback type of the optical network interface. Default
                        is none.";
        } // END of loopback-type definition.

        leaf losi-enabled  {
            type  empty;
            description "Enable loss of signal alarm on a network interface.";
        } // END of losi-enabled definition.

        leaf modulation-format  {
            // when " !ipi-platform-terminal-device:terminal-device/coherent-modules/coherent-module/network-interfaces/interface/config/operational-mode ";
            type  ipi-platform-terminal-device-types:terminal_device_cmm_modulation_format_t;
            default "dp-16-qam";
            description "Specifies the modulation format of the optical signal. Default is
                        dp-16-qam.";
        } // END of modulation-format definition.

        leaf operational-mode  {
            // when " !ipi-platform-terminal-device:terminal-device/coherent-modules/coherent-module/network-interfaces/interface/config/fec-mode + !ipi-platform-terminal-device:terminal-device/coherent-modules/coherent-module/network-interfaces/interface/config/modulation-format ";
            type  uint16 {
                 range "1..11"  {
                    description "1..11: Supported range 1 - 11";
                 }
            }
            description "Specifies the operational mode. The specified operational mode must
                        exist in the list of supported operational modes supplied by the
                        device";
        } // END of operational-mode definition.

        leaf prbs-type  {
            type  ipi-platform-terminal-device-types:terminal_device_cmm_prbs_type_t;
            default "none";
            description "Simulate random data for transmission across the network interface if
                        set. Default is none.";
        } // END of prbs-type definition.

        leaf pulse-shaping-rx  {
            type  empty;
            description "Enable or disable rx pulse shaping of the signal.";
        } // END of pulse-shaping-rx definition.

        leaf pulse-shaping-tx  {
            type  empty;
            description "Use this attribute to to enable or disable pulse shaping";
        } // END of pulse-shaping-tx definition.

        leaf soft-tx-disable  {
            type  empty;
            description "Disable transmission of data on a network interface.";
        } // END of soft-tx-disable definition.

        leaf target-output-power  {
            type  decimal64 {
                 fraction-digits 2;            }
            units "dBm";
            description "Specifies the output power of the optical network interface.";
        } // END of target-output-power definition.

        leaf link-down  {
            type  ipi-platform-terminal-device-types:cml_cmm_link_down_t;
            description "Configure the link to go down when it exceeds threshold values.";
        } // END of link-down definition.

    } // END of terminal-device-network-interface-config definition.
    grouping terminal-device-network-interface-state {
        description
            "terminal-device-network-interface-state";
        leaf line-port  {
            type  leafref {
                path  "/ipi-platform:components/ipi-platform:component/ipi-platform:name";
            }
            description "Reference to the line-side physical port that carries this optical
                        channel.";
        } // END of line-port definition.

        leaf provisioned-channel-power  {
            type  decimal64 {
                 fraction-digits 2;            }
            units "dBm";
            description "Specifies the current Provisioned Channel Power.";
        } // END of provisioned-channel-power definition.

        leaf differential-group-delay  {
            type  uint32;
            units "ps";
            description "Specifies the current Differential Group Delay in pico second.";
        } // END of differential-group-delay definition.

        leaf dsp-oper-status  {
            type  ipi-platform-terminal-device-types:terminal_device_cmm_dsp_oper_status_t;
            description "Specifies the operational status of the Digital Signal Processor of
                        the network interface in a coherent optical module.";
        } // END of dsp-oper-status definition.

        leaf osnr  {
            type  decimal64 {
                 fraction-digits 2;            }
            units "dB";
            description "Specifies the optical signal noise ratio.";
        } // END of osnr definition.

        leaf current-q-margin  {
            type  decimal64 {
                 fraction-digits 2;            }
            units "dB";
            description "Specifies Network RX Q margin.";
        } // END of current-q-margin definition.

        leaf current-tx-laser-frequency  {
            type  uint64;
            units "Hz";
            description "Specifies the current Tx-Laser Frequency.";
        } // END of current-tx-laser-frequency definition.

        leaf prbs-in-sync  {
            type  empty;
            description "Specifies the PRBS in SYNC.";
        } // END of prbs-in-sync definition.

        leaf oper-status  {
            type  ipi-platform-terminal-device-types:terminal_device_cmm_netif_oper_status_t;
            description "Specifies the operational status of the network interface in a
                        coherent optical module.";
        } // END of oper-status definition.

    } // END of terminal-device-network-interface-state definition.
    grouping terminal-device-network-interface-error-counters {
        description
            "terminal-device-network-interface-error-counters";
        leaf current-uncorrected-blocks  {
            type  yang:counter32;
            description "Specifies the Current Uncorrected Block-Count Value.";
        } // END of current-uncorrected-blocks definition.

        leaf fec-uncorrected-blocks  {
            type  yang:counter64;
            description "Specifies the Uncorrected Fec Block Count value.";
        } // END of fec-uncorrected-blocks definition.

        leaf otn-sm-bip8-error  {
            type  yang:counter64;
            description "Specifies the OTN Section Monitoring BIP-8 Count Value.";
        } // END of otn-sm-bip8-error definition.

    } // END of terminal-device-network-interface-error-counters definition.
    grouping terminal-device-network-interface-chromatic-disp-state {
        description
            "terminal-device-network-interface-chromatic-disp-state";
        leaf instant  {
            type  int32;
            units "ps/nm";
            description "Specifies the current Chromatic Dispersion in pico second/nano meter.";
        } // END of instant definition.

    } // END of terminal-device-network-interface-chromatic-disp-state definition.
    grouping terminal-device-network-interface-chromatic-disp-top {
        description
            "terminal-device-network-interface-chromatic-disp-top";
        container chromatic-dispersion {
            description
                "Container for network-interface chromatic dispersion";
            container state {
                config false;
                description
                    "Operational state data";
                uses terminal-device-network-interface-chromatic-disp-state;
            } // END of state-container definition.
        } // END of chromatic-dispersion-container definition.
    } // END of terminal-device-network-interface-chromatic-disp-top definition.
    grouping terminal-device-network-interface-input-power-state {
        description
            "terminal-device-network-interface-input-power-state";
        leaf instant  {
            type  decimal64 {
                 fraction-digits 2;            }
            units "dBm";
            description "Specifies the current Input Power.";
        } // END of instant definition.

    } // END of terminal-device-network-interface-input-power-state definition.
    grouping terminal-device-network-interface-input-power-top {
        description
            "terminal-device-network-interface-input-power-top";
        container input-power {
            description
                "Container for network-interface input power";
            container state {
                config false;
                description
                    "Operational state data";
                uses terminal-device-network-interface-input-power-state;
            } // END of state-container definition.
        } // END of input-power-container definition.
    } // END of terminal-device-network-interface-input-power-top definition.
    grouping terminal-device-network-interface-output-power-state {
        description
            "terminal-device-network-interface-output-power-state";
        leaf instant  {
            type  decimal64 {
                 fraction-digits 2;            }
            units "dBm";
            description "Specifies the current Output Power.";
        } // END of instant definition.

    } // END of terminal-device-network-interface-output-power-state definition.
    grouping terminal-device-network-interface-output-power-top {
        description
            "terminal-device-network-interface-output-power-top";
        container output-power {
            description
                "Container for network-interface output power";
            container state {
                config false;
                description
                    "Operational state data";
                uses terminal-device-network-interface-output-power-state;
            } // END of state-container definition.
        } // END of output-power-container definition.
    } // END of terminal-device-network-interface-output-power-top definition.
    grouping terminal-device-network-interface-post-voa-power-state {
        description
            "terminal-device-network-interface-post-voa-power-state";
        leaf instant  {
            type  decimal64 {
                 fraction-digits 2;            }
            units "dBm";
            description "Specifies the current POST VOA Power.";
        } // END of instant definition.

        leaf instant-provisioned-channel  {
            type  decimal64 {
                 fraction-digits 2;            }
            units "dBm";
            description "Specifies the current Post VOA Provisioned Channel Power.";
        } // END of instant-provisioned-channel definition.

    } // END of terminal-device-network-interface-post-voa-power-state definition.
    grouping terminal-device-network-interface-post-voa-power-top {
        description
            "terminal-device-network-interface-post-voa-power-top";
        container post-voa-power {
            description
                "Container for network-interface POST VOA power";
            container state {
                config false;
                description
                    "Operational state data";
                uses terminal-device-network-interface-post-voa-power-state;
            } // END of state-container definition.
        } // END of post-voa-power-container definition.
    } // END of terminal-device-network-interface-post-voa-power-top definition.
    grouping terminal-device-network-interface-laser-grid-state {
        description
            "terminal-device-network-interface-laser-grid-state";
        leaf slot-width  {
            type  ipi-platform-terminal-device-types:terminal_device_cmm_grid_spacing_t;
            description "Specifies the Grid Spacing.";
        } // END of slot-width definition.

        leaf laser-grid  {
            type  ipi-platform-terminal-device-types:terminal_device_cmm_grid_support_t;
            description "Specifies the supported Laser Grid.";
        } // END of laser-grid definition.

    } // END of terminal-device-network-interface-laser-grid-state definition.
    grouping terminal-device-network-interface-laser-grid-top {
        description
            "terminal-device-network-interface-laser-grid-top";
        container laser-grid {
            description
                "Container for network-interface laser grid";
            container state {
                config false;
                description
                    "Operational state data";
                uses terminal-device-network-interface-laser-grid-state;
            } // END of state-container definition.
        } // END of laser-grid-container definition.
    } // END of terminal-device-network-interface-laser-grid-top definition.
    grouping terminal-device-network-interface-laser-info-state {
        description
            "terminal-device-network-interface-laser-info-state";
        leaf laser-age  {
            type  uint16;
            units "%";
            description "Specifies the Tx Laser Age in Percentage.";
        } // END of laser-age definition.

        leaf min-laser-freq  {
            type  uint64;
            units "Hz";
            description "Specifies the Min Laser Frequency.";
        } // END of min-laser-freq definition.

        leaf max-laser-freq  {
            type  uint64;
            units "Hz";
            description "Specifies Max Laser Frequency.";
        } // END of max-laser-freq definition.

    } // END of terminal-device-network-interface-laser-info-state definition.
    grouping terminal-device-network-interface-laser-info-top {
        description
            "terminal-device-network-interface-laser-info-top";
        container laser-info {
            description
                "Container for network-interface laser info";
            container state {
                config false;
                description
                    "Operational state data";
                uses terminal-device-network-interface-laser-info-state;
            } // END of state-container definition.
        } // END of laser-info-container definition.
    } // END of terminal-device-network-interface-laser-info-top definition.
    grouping terminal-device-network-interface-monitor-threshold-config {
        description
            "terminal-device-network-interface-monitor-threshold-config";
        leaf rx-chromatic-dispersion  {
            type  string {
                length "1..1965";
                pattern "[^?' =,>|]+";
            }
            description "Set rx chromatic-dispersion threshold.";
        } // END of rx-chromatic-dispersion definition.

        leaf rx-q-margin  {
            type  decimal64 {
                 fraction-digits 2;            }
            description "Set rx q-margin threshold.";
        } // END of rx-q-margin definition.

        leaf rx-snr  {
            type  decimal64 {
                 fraction-digits 2;            }
            description "Set rx snr threshold.";
        } // END of rx-snr definition.

    } // END of terminal-device-network-interface-monitor-threshold-config definition.
    grouping terminal-device-network-interface-event-counters {
        description
            "terminal-device-network-interface-event-counters";
        leaf chromatic-dispersion-threshold  {
            type  yang:counter32;
            description "Specifies chromatic dispersion threshold event count value.";
        } // END of chromatic-dispersion-threshold definition.

        leaf osnr-threshold  {
            type  yang:counter32;
            description "Specifies osnr threshold event count value.";
        } // END of osnr-threshold definition.

        leaf q-margin-threshold  {
            type  yang:counter32;
            description "Specifies Q margin threshold event count value.";
        } // END of q-margin-threshold definition.

        leaf rx-los  {
            type  yang:counter32;
            description "Specifies rx los event count value.";
        } // END of rx-los definition.

    } // END of terminal-device-network-interface-event-counters definition.
    grouping terminal-device-network-interface-event-counters-rx-power {
        description
            "terminal-device-network-interface-event-counters-rx-power";
        leaf high-alarm  {
            type  yang:counter32;
            description "Specifies input power high alarm threshold event count value.";
        } // END of high-alarm definition.

        leaf high-warning  {
            type  yang:counter32;
            description "Specifies input power high warning threshold event count value.";
        } // END of high-warning definition.

        leaf low-warning  {
            type  yang:counter32;
            description "Specifies input power low warning threshold event count value.";
        } // END of low-warning definition.

        leaf low-alarm  {
            type  yang:counter32;
            description "Specifies input power low alarm threshold event count value.";
        } // END of low-alarm definition.

    } // END of terminal-device-network-interface-event-counters-rx-power definition.
    grouping terminal-device-network-interface-event-counters-pre-fec-ber {
        description
            "terminal-device-network-interface-event-counters-pre-fec-ber";
        leaf signal-degrade  {
            type  yang:counter32;
            description "Specifies pre fec ber signal degrade threshold event count value.";
        } // END of signal-degrade definition.

        leaf signal-fail  {
            type  yang:counter32;
            description "Specifies pre fec ber signal fail threshold event count value.";
        } // END of signal-fail definition.

    } // END of terminal-device-network-interface-event-counters-pre-fec-ber definition.
    grouping terminal-device-network-interface-event-counters-tx-power {
        description
            "terminal-device-network-interface-event-counters-tx-power";
        leaf high-alarm  {
            type  yang:counter32;
            description "Specifies output power high alarm threshold event count value.";
        } // END of high-alarm definition.

        leaf high-warning  {
            type  yang:counter32;
            description "Specifies output power high warning threshold event count value.";
        } // END of high-warning definition.

        leaf low-warning  {
            type  yang:counter32;
            description "Specifies output power low warning threshold event count value.";
        } // END of low-warning definition.

        leaf low-alarm  {
            type  yang:counter32;
            description "Specifies output power low alarm threshold event count value.";
        } // END of low-alarm definition.

    } // END of terminal-device-network-interface-event-counters-tx-power definition.
    grouping terminal-device-network-interface-ber-state {
        description
            "terminal-device-network-interface-ber-state";
        leaf current-ber-period  {
            type  uint32;
            units "ms";
            description "Specifies the current Bit Error Rate Period in milliseconds.";
        } // END of current-ber-period definition.

        leaf current-post-fec-ber  {
            type  uint64;
            units "1e-18";
            description "Specifies current POST FEC Bit Error Rate per 1e-18 BER Period.";
        } // END of current-post-fec-ber definition.

        leaf current-prbs-ber  {
            type  uint64;
            units "1e-18";
            description "Specifies Current PRBS Bit Error Rate value divided by 1e-18.";
        } // END of current-prbs-ber definition.

        leaf current-pre-fec-ber  {
            type  uint64;
            units "1e-18";
            description "Specifies the current PRE FEC Bit Error Rate per 1e-18 BER Period.";
        } // END of current-pre-fec-ber definition.

    } // END of terminal-device-network-interface-ber-state definition.
    grouping terminal-device-network-interface-ber-top {
        description
            "terminal-device-network-interface-ber-top";
        container ber {
            description
                "Container for network-interface BER";
            container state {
                config false;
                description
                    "Operational state data";
                uses terminal-device-network-interface-ber-state;
            } // END of state-container definition.
        } // END of ber-container definition.
    } // END of terminal-device-network-interface-ber-top definition.
    grouping terminal-device-network-interface-monitor-pre-fec-ber-config {
        description
            "terminal-device-network-interface-monitor-pre-fec-ber-config";
        leaf signal-failure  {
            type  ipi-platform-terminal-device-types:terminal_device_scientific_notation_string {
                length "1..1965";
            }
            description "Set pre fec ber threshold value for signal failure.";
        } // END of signal-failure definition.

        leaf signal-degrade  {
            type  ipi-platform-terminal-device-types:terminal_device_scientific_notation_string {
                length "1..1965";
            }
            description "Set pre fec ber threshold value for signal degrade.";
        } // END of signal-degrade definition.

        leaf clear  {
            type  ipi-platform-terminal-device-types:terminal_device_scientific_notation_string {
                length "1..1965";
            }
            description "Set pre fec ber threshold value for clear.";
        } // END of clear definition.

    } // END of terminal-device-network-interface-monitor-pre-fec-ber-config definition.
    grouping terminal-device-network-interface-monitor-pre-fec-ber-top {
        description
            "terminal-device-network-interface-monitor-pre-fec-ber-top";
        container pre-fec-ber-thresholds {
            description
                "network-interface PRE FEC BER thresholds";

            list pre-fec-ber-threshold {
                key "signal-failure signal-degrade clear";
                max-elements 1;
                description
                    "network-interface PRE FEC BER thresholds";
                leaf signal-failure  {
                    type  leafref {
                        path  "../config/signal-failure";
                    }
                    description "Set pre fec ber threshold value for signal failure.";
                } // END of signal-failure definition.

                leaf signal-degrade  {
                    type  leafref {
                        path  "../config/signal-degrade";
                    }
                    description "Set pre fec ber threshold value for signal degrade.";
                } // END of signal-degrade definition.

                leaf clear  {
                    type  leafref {
                        path  "../config/clear";
                    }
                    description "Set pre fec ber threshold value for clear.";
                } // END of clear definition.

                container config {
                    description
                        "Configuration data";
                    uses terminal-device-network-interface-monitor-pre-fec-ber-config;
                } // END of config-container definition.
                container state {
                    config false;
                    description
                        "Operational state data";
                    uses terminal-device-network-interface-monitor-pre-fec-ber-config;
                } // END of state-container definition.
            } // End of pre-fec-ber-threshold-list
        } // END of pre-fec-ber-thresholds-container definition.
    } // END of terminal-device-network-interface-monitor-pre-fec-ber-top definition.
    grouping terminal-device-network-interface-monitor-rx-power-config {
        description
            "terminal-device-network-interface-monitor-rx-power-config";
        leaf high-alarm  {
            type  decimal64 {
                 fraction-digits 2;            }
            description "Set input power threshold value for high alarm.";
        } // END of high-alarm definition.

        leaf high-warning  {
            type  decimal64 {
                 fraction-digits 2;            }
            description "Set input power threshold value for high warning.";
        } // END of high-warning definition.

        leaf low-warning  {
            type  decimal64 {
                 fraction-digits 2;            }
            description "Set input power threshold value for low warning.";
        } // END of low-warning definition.

        leaf low-alarm  {
            type  decimal64 {
                 fraction-digits 2;            }
            description "Set input power threshold value for low alarm.";
        } // END of low-alarm definition.

    } // END of terminal-device-network-interface-monitor-rx-power-config definition.
    grouping terminal-device-network-interface-monitor-rx-power-top {
        description
            "terminal-device-network-interface-monitor-rx-power-top";
        container rx-power-thresholds {
            description
                "network-interface input power thresholds";

            list rx-power-threshold {
                key "high-alarm high-warning low-warning low-alarm";
                max-elements 1;
                description
                    "network-interface input power thresholds";
                leaf high-alarm  {
                    type  leafref {
                        path  "../config/high-alarm";
                    }
                    description "Set input power threshold value for high alarm.";
                } // END of high-alarm definition.

                leaf high-warning  {
                    type  leafref {
                        path  "../config/high-warning";
                    }
                    description "Set input power threshold value for high warning.";
                } // END of high-warning definition.

                leaf low-warning  {
                    type  leafref {
                        path  "../config/low-warning";
                    }
                    description "Set input power threshold value for low warning.";
                } // END of low-warning definition.

                leaf low-alarm  {
                    type  leafref {
                        path  "../config/low-alarm";
                    }
                    description "Set input power threshold value for low alarm.";
                } // END of low-alarm definition.

                container config {
                    description
                        "Configuration data";
                    uses terminal-device-network-interface-monitor-rx-power-config;
                } // END of config-container definition.
                container state {
                    config false;
                    description
                        "Operational state data";
                    uses terminal-device-network-interface-monitor-rx-power-config;
                } // END of state-container definition.
            } // End of rx-power-threshold-list
        } // END of rx-power-thresholds-container definition.
    } // END of terminal-device-network-interface-monitor-rx-power-top definition.
    grouping terminal-device-network-interface-monitor-tx-power-state {
        description
            "terminal-device-network-interface-monitor-tx-power-state";
        leaf high-alarm  {
            type  decimal64 {
                 fraction-digits 2;            }
            units "dBm";
            description "Specifies current network interface tx output power high alarm
                        threshold.";
        } // END of high-alarm definition.

        leaf high-warning  {
            type  decimal64 {
                 fraction-digits 2;            }
            units "dBm";
            description "Specifies current network interface tx output power high warning
                        threshold.";
        } // END of high-warning definition.

        leaf low-alarm  {
            type  decimal64 {
                 fraction-digits 2;            }
            units "dBm";
            description "Specifies current network interface tx output power low warning
                        threshold.";
        } // END of low-alarm definition.

        leaf low-warning  {
            type  decimal64 {
                 fraction-digits 2;            }
            units "dBm";
            description "Specifies current network interface tx output power low alarm
                        threshold.";
        } // END of low-warning definition.

    } // END of terminal-device-network-interface-monitor-tx-power-state definition.
    grouping terminal-device-network-interface-monitor-tx-power-top {
        description
            "terminal-device-network-interface-monitor-tx-power-top";
        container tx-power-threshold {
            description
                "Container for network-interface output power threshold";
            container state {
                config false;
                description
                    "Operational state data";
                uses terminal-device-network-interface-monitor-tx-power-state;
            } // END of state-container definition.
        } // END of tx-power-threshold-container definition.
    } // END of terminal-device-network-interface-monitor-tx-power-top definition.
    grouping terminal-device-network-interface-monitor-perm-rx-power-state {
        description
            "terminal-device-network-interface-monitor-perm-rx-power-state";
        leaf high-alarm-max  {
            type  decimal64 {
                 fraction-digits 2;            }
            units "dBm";
            description "Specifies current network interface rx input power maximum permissible
                        high alarm threshold.";
        } // END of high-alarm-max definition.

        leaf high-alarm-min  {
            type  decimal64 {
                 fraction-digits 2;            }
            units "dBm";
            description "Specifies current network interface rx input power minimum permissible
                        high alarm threshold.";
        } // END of high-alarm-min definition.

        leaf high-warning-max  {
            type  decimal64 {
                 fraction-digits 2;            }
            units "dBm";
            description "Specifies current network interface rx input power maximum permissible
                        high warning threshold.";
        } // END of high-warning-max definition.

        leaf high-warning-min  {
            type  decimal64 {
                 fraction-digits 2;            }
            units "dBm";
            description "Specifies current network interface rx input power minimum permissible
                        high warning threshold.";
        } // END of high-warning-min definition.

        leaf low-alarm-max  {
            type  decimal64 {
                 fraction-digits 2;            }
            units "dBm";
            description "Specifies current network interface rx input power maximum permissible
                        low alarm threshold.";
        } // END of low-alarm-max definition.

        leaf low-alarm-min  {
            type  decimal64 {
                 fraction-digits 2;            }
            units "dBm";
            description "Specifies current network interface rx input power minimum permissible
                        low alarm threshold.";
        } // END of low-alarm-min definition.

        leaf low-warning-max  {
            type  decimal64 {
                 fraction-digits 2;            }
            units "dBm";
            description "Specifies current network interface rx input power maximum permissible
                        low warning threshold.";
        } // END of low-warning-max definition.

        leaf low-warning-min  {
            type  decimal64 {
                 fraction-digits 2;            }
            units "dBm";
            description "Specifies current network interface rx input power minimum permissible
                        low warning threshold.";
        } // END of low-warning-min definition.

    } // END of terminal-device-network-interface-monitor-perm-rx-power-state definition.
    grouping terminal-device-network-interface-monitor-perm-rx-power-top {
        description
            "terminal-device-network-interface-monitor-perm-rx-power-top";
        container permissible-rx-power-threshold {
            description
                "Container for network-interface permissible input power threshold";
            container state {
                config false;
                description
                    "Operational state data";
                uses terminal-device-network-interface-monitor-perm-rx-power-state;
            } // END of state-container definition.
        } // END of permissible-rx-power-threshold-container definition.
    } // END of terminal-device-network-interface-monitor-perm-rx-power-top definition.
    grouping terminal-device-network-interface-monitor-threshold-top {
        description
            "terminal-device-network-interface-monitor-threshold-top";
        container monitor-thresholds {
            description
                "Container for network-interface monitor thresholds";
            container config {
                description
                    "Configuration data for network-interface monitor thresholds";
                uses terminal-device-network-interface-monitor-threshold-config;
            } // END of config-container definition.
            container state {
                config false;
                description
                    "Operational state data";
                container counters {
                    config false;
                    description
                        "Container for network-interface counters";
                    container events {
                        config false;
                        description
                            "Container for network-interface event counters";
                        uses terminal-device-network-interface-event-counters;
                    } // END of events-container definition.
                    container rx-power-threshold-events {
                        config false;
                        description
                            "Container for network-interface rx power threshold count";
                        uses terminal-device-network-interface-event-counters-rx-power;
                    } // END of rx-power-threshold-events-container definition.
                    container pre-fec-ber-threshold-events {
                        config false;
                        description
                            "Container for network-interface PRE FEC BER threshold count";
                        uses terminal-device-network-interface-event-counters-pre-fec-ber;
                    } // END of pre-fec-ber-threshold-events-container definition.
                    container tx-power-threshold-events {
                        config false;
                        description
                            "Container for network-interface tx power threshold count";
                        uses terminal-device-network-interface-event-counters-tx-power;
                    } // END of tx-power-threshold-events-container definition.
                } // END of counters-container definition.
                uses terminal-device-network-interface-monitor-threshold-config;
            } // END of state-container definition.
            uses terminal-device-network-interface-monitor-pre-fec-ber-top;
            uses terminal-device-network-interface-monitor-rx-power-top;
            uses terminal-device-network-interface-monitor-tx-power-top;
            uses terminal-device-network-interface-monitor-perm-rx-power-top;
        } // END of monitor-thresholds-container definition.
    } // END of terminal-device-network-interface-monitor-threshold-top definition.
    grouping terminal-device-network-interface-alarms-state {
        description
            "terminal-device-network-interface-alarms-state";
        leaf chromatic-dispersion  {
            type  empty;
            description "Specifies current netif chromatic dispersion alarm status.";
        } // END of chromatic-dispersion definition.

        leaf input-power  {
            type  ipi-platform-terminal-device-types:terminal_device_cmm_netif_input_power_alarm_t;
            description "Specifies current netif rx input power alarm/warning status.";
        } // END of input-power definition.

        leaf output-power  {
            type  ipi-platform-terminal-device-types:terminal_device_cmm_netif_output_power_alarm_t;
            description "Specifies current netif tx output power alarm/warning status.";
        } // END of output-power definition.

        leaf q-margin  {
            type  empty;
            description "Specifies current netif q-margin alarm status.";
        } // END of q-margin definition.

        leaf pre-fec-ber-signal  {
            type  ipi-platform-terminal-device-types:terminal_device_cmm_netif_pre_fec_ber_signal_alarm_t;
            description "Specifies the signal degrade/fail alarm  based on Pre-FEC BER.";
        } // END of pre-fec-ber-signal definition.

        leaf rx-los  {
            type  empty;
            description "Specifies current netif rx loss of signal status.";
        } // END of rx-los definition.

        leaf rx-odu  {
            type  ipi-platform-terminal-device-types:terminal_device_cmm_netif_rx_odu_alarm_t;
            description "Specifies current netif rx optical data unit frame status.";
        } // END of rx-odu definition.

        leaf rx-opu  {
            type  ipi-platform-terminal-device-types:terminal_device_cmm_netif_rx_opu_alarm_t;
            description "Specifies current netif rx optical payload unit frame status.";
        } // END of rx-opu definition.

        leaf rx-otu  {
            type  ipi-platform-terminal-device-types:terminal_device_cmm_netif_rx_otu_alarm_t;
            description "Specifies current netif rx optical transport unit frame status.";
        } // END of rx-otu definition.

        leaf rx-training-sequence  {
            type  ipi-platform-terminal-device-types:terminal_device_cmm_netif_rx_ts_alarm_t;
            description "Specifies current netif rx training sequence status.";
        } // END of rx-training-sequence definition.

        leaf osnr  {
            type  empty;
            description "Specifies current netif snr alarm status.";
        } // END of osnr definition.

    } // END of terminal-device-network-interface-alarms-state definition.
    grouping terminal-device-network-interface-alarms-top {
        description
            "terminal-device-network-interface-alarms-top";
        container channel-alarms {
            description
                "Container for network-interface status";
            container state {
                config false;
                description
                    "Operational state data";
                uses terminal-device-network-interface-alarms-state;
            } // END of state-container definition.
        } // END of channel-alarms-container definition.
    } // END of terminal-device-network-interface-alarms-top definition.
    grouping terminal-device-network-interface-top {
        description
            "terminal-device-network-interface-top";
        container network-interfaces {
            when " /ipi-platform-terminal-device:terminal-device/ipi-platform-terminal-device:coherent-modules/ipi-platform-terminal-device:coherent-module/ipi-platform-terminal-device:config/ipi-platform-terminal-device:service-enable ";
            description
                "network-interface configuration data";

            list interface {
                key "net-index";
                description
                    "A list to store all network-interfaces";
                leaf net-index  {
                    type  leafref {
                        path  "../config/net-index";
                    }
                    description "Index of network interface in a coherent optical module.";
                } // END of net-index definition.

                container config {
                    description
                        "network-interface configuration data";
                    uses terminal-device-network-interface-config;
                } // END of config-container definition.
                container state {
                    config false;
                    description
                        "network-interface state data";
                    container counters {
                        config false;
                        description
                            "Container for network-interface error counters";
                        uses terminal-device-network-interface-error-counters;
                    } // END of counters-container definition.
                    uses terminal-device-network-interface-config;
                    uses terminal-device-network-interface-state;
                } // END of state-container definition.
                uses terminal-device-network-interface-chromatic-disp-top;
                uses terminal-device-network-interface-input-power-top;
                uses terminal-device-network-interface-output-power-top;
                uses terminal-device-network-interface-post-voa-power-top;
                uses terminal-device-network-interface-laser-grid-top;
                uses terminal-device-network-interface-laser-info-top;
                uses terminal-device-network-interface-ber-top;
                uses terminal-device-network-interface-monitor-threshold-top;
                uses terminal-device-network-interface-alarms-top;
            } // End of interface-list
        } // END of network-interfaces-container definition.
    } // END of terminal-device-network-interface-top definition.
    grouping terminal-device-transceiver-state {
        description
            "terminal-device-transceiver-state";
        leaf firmware-version  {
            type  string {
                length "1..1965";
                pattern "[^?' =,>|]+";
            }
            description "Specifies the CFP Vendor Firmware Version.";
        } // END of firmware-version definition.

        leaf vendor-name  {
            type  string {
                length "1..1965";
            }
            description "Specifies the CFP Vendor Name.";
        } // END of vendor-name definition.

        leaf part-no  {
            type  string {
                length "1..1965";
                pattern "[^?' =,>|]+";
            }
            description "Specifies the CFP Vendor Part Number.";
        } // END of part-no definition.

        leaf serial-no  {
            type  string {
                length "1..1965";
                pattern "[^?' =,>|]+";
            }
            description "Specifies the CFP Vendor Serial Number.";
        } // END of serial-no definition.

        leaf vendor-oui  {
            type  cml-data-types:cml_line_t {
                length "1..1965";
            }
            description "Specifies the CFP Vendor OUI.";
        } // END of vendor-oui definition.

        leaf temperature  {
            type  decimal64 {
                 fraction-digits 2;            }
            units "C";
            description "Specifies the CFP Module Temperature.";
        } // END of temperature definition.

        leaf power  {
            type  decimal64 {
                 fraction-digits 3;            }
            units "V";
            description "Specifies the CFP Module Power Supply.";
        } // END of power definition.

        leaf present  {
            type  ipi-platform-terminal-device-types:terminal_device_cmm_cfp_presence_t;
            description "Indicates Transceiver presence status.";
        } // END of present definition.

    } // END of terminal-device-transceiver-state definition.
    grouping terminal-device-transceiver-top {
        description
            "Terminal device transceiver state info";
        container transceiver {
            description
                "Terminal device transceiver container";
            container state {
                config false;
                description
                    "Operational state data for transceiver";
                uses terminal-device-transceiver-state;
            } // END of state-container definition.
        } // END of transceiver-container definition.
    } // END of terminal-device-transceiver-top definition.
    grouping terminal-device-module-event-counters-voltage {
        description
            "Terminal device module event voltage related counters";
        leaf high-alarm  {
            type  yang:counter32;
            description "Specifies power high alarm event count value.";
        } // END of high-alarm definition.

        leaf high-warning  {
            type  yang:counter32;
            description "Specifies power high warning event count value.";
        } // END of high-warning definition.

        leaf low-alarm  {
            type  yang:counter32;
            description "Specifies power low alarm event count value.";
        } // END of low-alarm definition.

        leaf low-warning  {
            type  yang:counter32;
            description "Specifies power low warning event count value.";
        } // END of low-warning definition.

    } // END of terminal-device-module-event-counters-voltage definition.
    grouping terminal-device-module-monitor-thresholds-voltage-state {
        description
            "terminal-device-module-monitor-thresholds-voltage-state";
        leaf high-alarm  {
            type  decimal64 {
                 fraction-digits 3;            }
            units "V";
            description "Specifies current module voltage high alarm threshold value.";
        } // END of high-alarm definition.

        leaf high-warning  {
            type  decimal64 {
                 fraction-digits 3;            }
            units "V";
            description "Specifies current module voltage high warning threshold value.";
        } // END of high-warning definition.

        leaf low-alarm  {
            type  decimal64 {
                 fraction-digits 3;            }
            units "V";
            description "Specifies current module voltage low alarm threshold value.";
        } // END of low-alarm definition.

        leaf low-warning  {
            type  decimal64 {
                 fraction-digits 3;            }
            units "V";
            description "Specifies current module voltage low warning threshold value.";
        } // END of low-warning definition.

    } // END of terminal-device-module-monitor-thresholds-voltage-state definition.
    grouping terminal-device-module-monitor-thresholds-voltage {
        description
            "Terminal device module monitor voltage thresholds state";
        container voltage {
            description
                "Terminal device module monitor voltage thresholds container";
            container state {
                config false;
                description
                    "Operational state data for module monitor voltage thresholds";
                container counters {
                    config false;
                    description
                        "Module event voltage related counters";
                    container events {
                        config false;
                        description
                            "Operational state data for module event voltage related counters";
                        uses terminal-device-module-event-counters-voltage;
                    } // END of events-container definition.
                } // END of counters-container definition.
                uses terminal-device-module-monitor-thresholds-voltage-state;
            } // END of state-container definition.
        } // END of voltage-container definition.
    } // END of terminal-device-module-monitor-thresholds-voltage definition.
    grouping terminal-device-module-event-counters-temperature {
        description
            "Terminal device module event temperature related counters";
        leaf high-alarm  {
            type  yang:counter32;
            description "Specifies temperature high alarm event count value.";
        } // END of high-alarm definition.

        leaf high-warning  {
            type  yang:counter32;
            description "Specifies temperature high warning event count value.";
        } // END of high-warning definition.

        leaf low-alarm  {
            type  yang:counter32;
            description "Specifies temperature low alarm event count value.";
        } // END of low-alarm definition.

        leaf low-warning  {
            type  yang:counter32;
            description "Specifies temperature low warning event count value.";
        } // END of low-warning definition.

    } // END of terminal-device-module-event-counters-temperature definition.
    grouping terminal-device-module-monitor-thresholds-temperature-state {
        description
            "Terminal device module monitor temperature thresholds state";
        leaf high-alarm  {
            type  decimal64 {
                 fraction-digits 2;            }
            units "C";
            description "Specifies current module temperature high alarm  threshold value.";
        } // END of high-alarm definition.

        leaf high-warning  {
            type  decimal64 {
                 fraction-digits 2;            }
            units "C";
            description "Specifies current module temperature high warning threshold value.";
        } // END of high-warning definition.

        leaf low-alarm  {
            type  decimal64 {
                 fraction-digits 2;            }
            units "C";
            description "Specifies current module temperature low alarm threshold value.";
        } // END of low-alarm definition.

        leaf low-warning  {
            type  decimal64 {
                 fraction-digits 2;            }
            units "C";
            description "Specifies current module temperature low warning threshold value.";
        } // END of low-warning definition.

    } // END of terminal-device-module-monitor-thresholds-temperature-state definition.
    grouping terminal-device-module-monitor-thresholds-temperature {
        description
            "Terminal device module monitor temperature thresholds state";
        container temperature {
            description
                "Terminal device module monitor temperature thresholds container";
            container state {
                config false;
                description
                    "Operational state data for module monitor temperature thresholds";
                container counters {
                    config false;
                    description
                        "Module event temperature related counters";
                    container events {
                        config false;
                        description
                            "Operational state data for module event temperature related counters";
                        uses terminal-device-module-event-counters-temperature;
                    } // END of events-container definition.
                } // END of counters-container definition.
                uses terminal-device-module-monitor-thresholds-temperature-state;
            } // END of state-container definition.
        } // END of temperature-container definition.
    } // END of terminal-device-module-monitor-thresholds-temperature definition.
    grouping terminal-device-module-monitor-thresholds {
        description
            "Terminal device module monitor thresholds state";
        container monitor-thresholds {
            description
                "Terminal device module status container";
            uses terminal-device-module-monitor-thresholds-temperature;
            uses terminal-device-module-monitor-thresholds-voltage;
        } // END of monitor-thresholds-container definition.
    } // END of terminal-device-module-monitor-thresholds definition.
    grouping terminal-device-module-alarms-state {
        description
            "Terminal device module alarms information state";
        leaf general-status  {
            type  ipi-platform-terminal-device-types:terminal_device_cmm_mod_general_status_alarm_t;
            description "Specifies the current module general status, if any fault/status is
                        present.";
        } // END of general-status definition.

        leaf module-fault-status  {
            type  ipi-platform-terminal-device-types:terminal_device_cmm_mod_fault_status_alarm_t;
            description "Specifies the current module fault status, if any fault/status is
                        present.";
        } // END of module-fault-status definition.

        leaf temperature  {
            type  ipi-platform-terminal-device-types:terminal_device_cmm_mod_temp_alarm_t;
            description "Specifies current module temperature alarm/warning status, according
                        to the threshold value.";
        } // END of temperature definition.

        leaf voltage  {
            type  ipi-platform-terminal-device-types:terminal_device_cmm_mod_volt_alarm_t;
            description "Specifies current module voltage alarm/warning status, according to
                        the threshold value.";
        } // END of voltage definition.

    } // END of terminal-device-module-alarms-state definition.
    grouping terminal-device-module-alarms {
        description
            "Terminal device module status";
        container module-alarms {
            description
                "Terminal device module alarms container";
            container state {
                config false;
                description
                    "Operational state data for module alarms";
                uses terminal-device-module-alarms-state;
            } // END of state-container definition.
        } // END of module-alarms-container definition.
    } // END of terminal-device-module-alarms definition.
    grouping terminal-device-module-event-counters {
        description
            "Terminal device module event counters";
        leaf checksum-fault  {
            type  yang:counter32;
            description "Specifies checksum fault event count value.";
        } // END of checksum-fault definition.

        leaf hardware-fault  {
            type  yang:counter32;
            description "Specifies hardware fault event count value.";
        } // END of hardware-fault definition.

        leaf host-lane-out-of-alignment  {
            type  yang:counter32;
            description "Specifies host lane out of alignment event count value.";
        } // END of host-lane-out-of-alignment definition.

        leaf hardware-interlock  {
            type  yang:counter32;
            description "Specifies hardware interlock event count value.";
        } // END of hardware-interlock definition.

        leaf initialization-fault  {
            type  yang:counter32;
            description "Specifies initialization fault event count value.";
        } // END of initialization-fault definition.

        leaf over-temperature-fault  {
            type  yang:counter32;
            description "Specifies over temperature fault event count value.";
        } // END of over-temperature-fault definition.

        leaf power-supply-fault  {
            type  yang:counter32;
            description "Specifies power supply fault event count value.";
        } // END of power-supply-fault definition.

        leaf rx-loss-of-signal  {
            type  yang:counter32;
            description "Specifies rx loss of signal event count value.";
        } // END of rx-loss-of-signal definition.

        leaf rx-network-loss-of-lock  {
            type  yang:counter32;
            description "Specifies rx network loss of lock event count value.";
        } // END of rx-network-loss-of-lock definition.

        leaf tx-host-loss-of-lock  {
            type  yang:counter32;
            description "Specifies tx host loss of lock event count value.";
        } // END of tx-host-loss-of-lock definition.

        leaf tx-los-functionality  {
            type  yang:counter32;
            description "Specifies tx loss of signal functionality event count value.";
        } // END of tx-los-functionality definition.

    } // END of terminal-device-module-event-counters definition.
    grouping terminal-device-module-info-state {
        description
            "Terminal device module info state grouping";
        leaf host-interface-count  {
            type  uint32;
            description "Specifies the number of ethernet non-optical ports supported for the
                        optical interface.";
        } // END of host-interface-count definition.

        leaf network-interface-count  {
            type  uint32;
            description "Number of optical channel interfaces.";
        } // END of network-interface-count definition.

        leaf coherent-module-type  {
            type  ipi-platform-terminal-device-types:terminal_device_cmm_card_type_t;
            description "Specifies the coherent optical module Type, currently supported module
                        types are ACO and DCO.";
        } // END of coherent-module-type definition.

        leaf presence  {
            type  ipi-platform-terminal-device-types:terminal_device_cmm_device_presence_t;
            description "Specifies whether coherent optical module is Present in the slot.";
        } // END of presence definition.

    } // END of terminal-device-module-info-state definition.
    grouping terminal-device-module-info {
        description
            "Terminal device module info grouping";
        container module-info {
            description
                "Terminal device module info container";
            container state {
                config false;
                description
                    "Operational state data for module info";
                uses terminal-device-module-info-state;
            } // END of state-container definition.
        } // END of module-info-container definition.
    } // END of terminal-device-module-info definition.
    grouping terminal-device-config {
        description
            "Terminal device config data grouping";
        leaf slot-index  {
            type  uint8 {
                 range "1..255"  {
                    description "1..255: Supported range 1 - 255";
                 }
            }
            description "Index to select a optical module slot.";
        } // END of slot-index definition.

        leaf service-enable  {
            type  empty;
            description "Use this attribute to enable or disable service for controller optical
                        module";
        } // END of service-enable definition.

        leaf description  {
            type  cml-data-types:cml_line_t {
                length "1..1965";
            }
            description "Use this attribute to describe a coherent optical slot.";
        } // END of description definition.

        leaf network-interface-loopback-type  {
            // when " ipi-platform-terminal-device:terminal-device/coherent-modules/coherent-module/config/service-enable ";
            type  ipi-platform-terminal-device-types:terminal_device_cmm_optical_loopback_t;
            default "none";
            description "Use this attribute to set all the network interfaces loopback type.";
        } // END of network-interface-loopback-type definition.

        leaf host-interface-loopback-type  {
            // when " ipi-platform-terminal-device:terminal-device/coherent-modules/coherent-module/config/service-enable ";
            type  ipi-platform-terminal-device-types:terminal_device_cmm_optical_loopback_t;
            default "none";
            description "Use this attribute to set all the host interfaces loopback type.";
        } // END of host-interface-loopback-type definition.

    } // END of terminal-device-config definition.
    grouping terminal-device-top {
        description
            "Terminal devices main container";
        container coherent-modules {
            description
                "Container for coherent modules";

            list coherent-module {
                key "slot-index";
                description
                    "A list to store all info about coherent-modules";
                leaf slot-index  {
                    type  leafref {
                        path  "../config/slot-index";
                    }
                    description "Index to select a optical module slot.";
                } // END of slot-index definition.

                container config {
                    description
                        "Configuration data for coherent module";
                    uses terminal-device-config;
                } // END of config-container definition.
                container state {
                    config false;
                    description
                        "Operational state data for coherent module";
                    container counters {
                        config false;
                        description
                            "Terminal device module event counters";
                        container events {
                            config false;
                            description
                                "Operational state data for module event counters";
                            uses terminal-device-module-event-counters;
                        } // END of events-container definition.
                    } // END of counters-container definition.
                    uses terminal-device-config;
                } // END of state-container definition.
                uses terminal-device-module-info;
                uses terminal-device-module-alarms;
                uses terminal-device-module-monitor-thresholds;
                uses terminal-device-transceiver-top;
                uses terminal-device-optical-port-top;
                uses terminal-device-network-interface-top;
                uses terminal-host-interface-top;
            } // End of coherent-module-list
        } // END of coherent-modules-container definition.
    } // END of terminal-device-top definition.
    grouping terminal-operational-mode-state {
        description
            "Operational state data for vendor-supported operational modes";
        leaf mode-id  {
            type  uint16;
            description "Vendor-defined operational mode id.";
        } // END of mode-id definition.

        leaf description  {
            type  string {
                length "1..1965";
            }
            description "Vendor-supplied textual description of the characteristics
                        of this operational mode to enable operators to select the
                        appropriate mode for the application.";
        } // END of description definition.

        leaf vendor-id  {
            type  string {
                length "1..1965";
            }
            description "Specifies the coherent optical module vendor name";
        } // END of vendor-id definition.

    } // END of terminal-operational-mode-state definition.
    grouping terminal-operational-mode-top {
        description
            "grouping for vendor-supported operational modes";
        container operational-modes {
            description
                "Container for a list of operational modes pre-defined by vendor";

            list mode {
                key "mode-id";
                config false;
                description
                    "List of operational modes supported by the platform. The operational
                                mode provides a platform-defined summary
                                of information such as symbol rate, modulation, pulse shaping, etc.";
                leaf mode-id  {
                    type  leafref {
                        path  "../state/mode-id";
                    }
                    description "Vendor-defined operational mode id.";
                } // END of mode-id definition.

                container state {
                    config false;
                    description
                        "Operational state data for terminal devices";
                    uses terminal-operational-mode-state;
                } // END of state-container definition.
            } // End of mode-list
        } // END of operational-modes-container definition.
    } // END of terminal-operational-mode-top definition.
    grouping terminal-host-interface-assignments-state {
        description
            "terminal-host-interface-assignments-state";
        leaf network-interface-index  {
            type  uint8;
            description "Specifies the mapped net-index.";
        } // END of network-interface-index definition.

        leaf ethernet-interface  {
            type  string {
                length "1..1965";
                pattern "[^?' =,>|]+";
            }
            description "Specifies the mapped ethernet interface name";
        } // END of ethernet-interface definition.

    } // END of terminal-host-interface-assignments-state definition.
    grouping terminal-host-interface-assignments-top {
        description
            "terminal-host-interface-assignments-top";
        container assignments {
            description
                "Store the network-interface and ethernet interface assigned to the
                        host-interface";
            container state {
                config false;
                description
                    "Operational state data";
                uses terminal-host-interface-assignments-state;
            } // END of state-container definition.
        } // END of assignments-container definition.
    } // END of terminal-host-interface-assignments-top definition.
    grouping terminal-device-debug-term-state {
        description
            "terminal-device-debug-term-state";
        leaf terminal-debug-status  {
            type  ipi-platform-terminal-device-types:terminal_device_tai_debug_t;
            description "Terminal debug TAI debug level";
        } // END of terminal-debug-status definition.

    } // END of terminal-device-debug-term-state definition.
    grouping terminal-device-debug-config {
        description
            "terminal-device-debug-config";
        leaf options  {
            type  ipi-platform-terminal-device-types:terminal_device_tai_debug_t;
            description "Set TAI debug for Module/Netif/Hostif in config mode.";
        } // END of options definition.

    } // END of terminal-device-debug-config definition.
    grouping terminal-device-debug-top {
        description
            "terminal-device-debug-top";
        container debug {
            description
                "Container for TAI debug";
            container config {
                description
                    "Container for TAI debug configuration";
                uses terminal-device-debug-config;
            } // END of config-container definition.
            container state {
                config false;
                description
                    "Operational state data";
                uses terminal-device-debug-config;
                uses terminal-device-debug-term-state;
            } // END of state-container definition.
        } // END of debug-container definition.
    } // END of terminal-device-debug-top definition.

    grouping  terminal-device-grouping {
    description
        "Container for the terminal devices";
    container terminal-device {
        if-feature feature-list:HAVE_COHERENT_OPTICS;
        if-feature feature-list:HAVE_CMMD;
        description
            "Container for the terminal devices";
        uses terminal-device-top;
        uses terminal-operational-mode-top;
        uses terminal-device-debug-top;
    } // END of terminal-device-container definition.
    } // END of terminal-device-grouping definition.

    uses terminal-device-grouping;

    rpc tai-terminal-debug-on {
        if-feature feature-list:HAVE_COHERENT_OPTICS;
        if-feature feature-list:HAVE_CMMD;
        description "Enable TAI debug options";
        input  {
            leaf terminal-debug-options  {
                type ipi-platform-terminal-device-types:terminal_device_tai_debug_t;
                mandatory true;
                description "Enable TAI debug for Module/Netif/Hostif in EXEC mode.";
            }
        }
    }

    rpc tai-terminal-debug-off {
        if-feature feature-list:HAVE_COHERENT_OPTICS;
        if-feature feature-list:HAVE_CMMD;
        description "Disable TAI debug options";
        input  {
            leaf terminal-debug-options  {
                type ipi-platform-terminal-device-types:terminal_device_tai_debug_t;
                mandatory true;
                description "Disable TAI debug for Module/Netif/Hostif in EXEC mode.";
            }
        }
    }

    rpc clear-coherent-module-event-counters {
        if-feature feature-list:HAVE_COHERENT_OPTICS;
        if-feature feature-list:HAVE_CMMD;
        description "Clear coherent module event counters";
        input  {
            leaf slot-index  {
                type uint8 {
                    range "1..255";
                }
                mandatory true;
                description "Coherent module index";
            }
        }
    }

    rpc clear-coherent-module-error-counters {
        if-feature feature-list:HAVE_COHERENT_OPTICS;
        if-feature feature-list:HAVE_CMMD;
        description "Clear coherent module error counters";
        input  {
            leaf slot-index  {
                type uint8 {
                    range "1..255";
                }
                mandatory true;
                description "Coherent module index";
            }
        }
    }

    notification coherent-module-inserted {
        if-feature feature-list:HAVE_CMMD;
        if-feature feature-list:HAVE_COHERENT_OPTICS;

        description "Notification sent when coherent optical module is inserted/detected..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }

        leaf coherent-module-type {
            type ipi-platform-terminal-device-types:terminal_device_cmm_card_type_t;
        description
            "Specifies the coherent optical module Type, currently supported module
                    types are ACO and DCO.";
        }
    }

    notification coherent-module-removed {
        if-feature feature-list:HAVE_CMMD;
        if-feature feature-list:HAVE_COHERENT_OPTICS;

        description "Notification sent when coherent coherent optical module is removed..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }

        leaf coherent-module-type {
            type ipi-platform-terminal-device-types:terminal_device_cmm_card_type_t;
        description
            "Specifies the coherent optical module Type, currently supported module
                    types are ACO and DCO.";
        }
    }

    notification cfp-transceiver-inserted {
        if-feature feature-list:HAVE_CMMD;
        if-feature feature-list:HAVE_COHERENT_OPTICS;

        description "Notification sent when CFP transceiver is inserted/detected..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }

        leaf coherent-module-type {
            type ipi-platform-terminal-device-types:terminal_device_cmm_card_type_t;
        description
            "Specifies the coherent optical module Type, currently supported module
                    types are ACO and DCO.";
        }

        leaf net-index {
            type  uint8;
        description
            "Index of network interface in a coherent optical module.";
        }
    }

    notification cfp-transceiver-removed {
        if-feature feature-list:HAVE_CMMD;
        if-feature feature-list:HAVE_COHERENT_OPTICS;

        description "Notification sent when CFP transceiver is removed..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }

        leaf coherent-module-type {
            type ipi-platform-terminal-device-types:terminal_device_cmm_card_type_t;
        description
            "Specifies the coherent optical module Type, currently supported module
                    types are ACO and DCO.";
        }

        leaf net-index {
            type  uint8;
        description
            "Index of network interface in a coherent optical module.";
        }
    }

    notification coherent-module-temperature-high-alarm {
        if-feature feature-list:HAVE_CMMD;
        if-feature feature-list:HAVE_COHERENT_OPTICS;

        description "Notification sent when coherent optical module temperature reaches high alarm value..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }
    }

    notification coherent-module-temperature-high-warning {
        if-feature feature-list:HAVE_CMMD;
        if-feature feature-list:HAVE_COHERENT_OPTICS;

        description "Notification sent when coherent optical module temperature reaches high warning value..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }
    }

    notification coherent-module-temperature-low-warning {
        if-feature feature-list:HAVE_CMMD;
        if-feature feature-list:HAVE_COHERENT_OPTICS;

        description "Notification sent when coherent optical module temperature reaches low warning value..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }
    }

    notification coherent-module-temperature-low-alarm {
        if-feature feature-list:HAVE_CMMD;
        if-feature feature-list:HAVE_COHERENT_OPTICS;

        description "Notification sent when coherent optical module temperature reaches low alarm value..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }
    }

    notification coherent-module-temperature-recovered {
        if-feature feature-list:HAVE_CMMD;
        if-feature feature-list:HAVE_COHERENT_OPTICS;

        description "Notification sent when coherent optical module Temperature alarm/warning is recovered..";

        leaf severity {
            type cml-data-types:cml_notif_severity_t;
            description "Notification severity level (value: MINOR)";
        }

        leaf eventClass {
            type cml-data-types:cml_notif_class_t;
            description "Notification event class (value: STATE)";
        }

        leaf slot-index {
            type  uint8;
        description
            "Index to select a optical module slot.";
        }
    }

    notification coherent-module-voltage-high-alarm {
        if-feature feature-list:HAVE_CMMD;
        if-feature feature-list:HAVE_COHERENT_OPTICS;

        description "Notification sent when coherent optical module voltage reaches high alarm value..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }
    }

    notification coherent-module-voltage-high-warning {
        if-feature feature-list:HAVE_CMMD;
        if-feature feature-list:HAVE_COHERENT_OPTICS;

        description "Notification sent when coherent optical module voltage reaches high warning value..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }
    }

    notification coherent-module-voltage-low-warning {
        if-feature feature-list:HAVE_CMMD;
        if-feature feature-list:HAVE_COHERENT_OPTICS;

        description "Notification sent when coherent optical module voltage reaches low warning value..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }
    }

    notification coherent-module-voltage-low-alarm {
        if-feature feature-list:HAVE_CMMD;
        if-feature feature-list:HAVE_COHERENT_OPTICS;

        description "Notification sent when coherent optical module power reaches low alarm value..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }
    }

    notification coherent-module-voltage-recovered {
        if-feature feature-list:HAVE_CMMD;
        if-feature feature-list:HAVE_COHERENT_OPTICS;

        description "Notification sent when coherent optical module power alarm/warning is recovered..";

        leaf severity {
            type cml-data-types:cml_notif_severity_t;
            description "Notification severity level (value: MINOR)";
        }

        leaf eventClass {
            type cml-data-types:cml_notif_class_t;
            description "Notification event class (value: STATE)";
        }

        leaf slot-index {
            type  uint8;
        description
            "Index to select a optical module slot.";
        }
    }

    notification coherent-module-general-status {
        if-feature feature-list:HAVE_CMMD;
        if-feature feature-list:HAVE_COHERENT_OPTICS;

        description "Notification sent when coherent optical module general status is changed..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }

        leaf general-status {
            type ipi-platform-terminal-device-types:terminal_device_cmm_mod_general_status_alarm_t;
        description
            "Specifies the current module general status, if any fault/status is
                    present.";
        }
    }

    notification coherent-module-fault-status {
        if-feature feature-list:HAVE_CMMD;
        if-feature feature-list:HAVE_COHERENT_OPTICS;

        description "Notification sent when coherent optical module fault status is changed..";

        leaf severity {
            type cml-data-types:cml_notif_severity_t;
            description "Notification severity level (value: CRITICAL)";
        }

        leaf eventClass {
            type cml-data-types:cml_notif_class_t;
            description "Notification event class (value: STATE)";
        }

        leaf slot-index {
            type  uint8;
        description
            "Index to select a optical module slot.";
        }

        leaf module-fault-status {
            type ipi-platform-terminal-device-types:terminal_device_cmm_mod_fault_status_alarm_t;
        description
            "Specifies the current module fault status, if any fault/status is
                    present.";
        }
    }

    notification network-interface-rx-los-alarm {
        if-feature feature-list:HAVE_CMMD;
        if-feature feature-list:HAVE_COHERENT_OPTICS;

        description "Notification sent when RX LOS Alarm is raised..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-rx-los-recovered {
        if-feature feature-list:HAVE_CMMD;
        if-feature feature-list:HAVE_COHERENT_OPTICS;

        description "Notification sent when RX LOS Alarm is cleared..";

        leaf severity {
            type cml-data-types:cml_notif_severity_t;
            description "Notification severity level (value: MINOR)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-input-power-high-alarm {
        if-feature feature-list:HAVE_CMMD;
        if-feature feature-list:HAVE_COHERENT_OPTICS;

        description "Notification sent when coherent network-interface input power reaches high alarm value..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-input-power-high-warning {
        if-feature feature-list:HAVE_CMMD;
        if-feature feature-list:HAVE_COHERENT_OPTICS;

        description "Notification sent when coherent network-interface input power reaches high warning value..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-input-power-low-warning {
        if-feature feature-list:HAVE_CMMD;
        if-feature feature-list:HAVE_COHERENT_OPTICS;

        description "Notification sent when coherent network-interface input power reaches low warning value..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-input-power-low-alarm {
        if-feature feature-list:HAVE_CMMD;
        if-feature feature-list:HAVE_COHERENT_OPTICS;

        description "Notification sent when coherent network-interface input power reaches low alarm value..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-input-power-recovered {
        if-feature feature-list:HAVE_CMMD;
        if-feature feature-list:HAVE_COHERENT_OPTICS;

        description "Notification sent when coherent network-interface input power recovered from alarm/warning value..";

        leaf severity {
            type cml-data-types:cml_notif_severity_t;
            description "Notification severity level (value: MINOR)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-output-power-high-alarm {
        if-feature feature-list:HAVE_CMMD;
        if-feature feature-list:HAVE_COHERENT_OPTICS;

        description "Notification sent when coherent network-interface output power reaches high alarm value..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-output-power-high-warning {
        if-feature feature-list:HAVE_CMMD;
        if-feature feature-list:HAVE_COHERENT_OPTICS;

        description "Notification sent when coherent network-interface output power reaches high warning value..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-output-power-low-warning {
        if-feature feature-list:HAVE_CMMD;
        if-feature feature-list:HAVE_COHERENT_OPTICS;

        description "Notification sent when coherent network-interface output power reaches low warning value..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-output-power-low-alarm {
        if-feature feature-list:HAVE_CMMD;
        if-feature feature-list:HAVE_COHERENT_OPTICS;

        description "Notification sent when coherent network-interface input power reaches low alarm value..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-output-power-recovered {
        if-feature feature-list:HAVE_CMMD;
        if-feature feature-list:HAVE_COHERENT_OPTICS;

        description "Notification sent when coherent network-interface output power recovered from alarm/warning value..";

        leaf severity {
            type cml-data-types:cml_notif_severity_t;
            description "Notification severity level (value: MINOR)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-pre-fec-ber-signal-fail {
        if-feature feature-list:HAVE_CMMD;
        if-feature feature-list:HAVE_COHERENT_OPTICS;

        description "Notification sent when coherent network-interface pre FEC BER Signal reaches Failure Threshold value..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-pre-fec-ber-signal-degrade {
        if-feature feature-list:HAVE_CMMD;
        if-feature feature-list:HAVE_COHERENT_OPTICS;

        description "Notification sent when coherent network-interface pre FEC BER Signal reaches Degrade Threshold value..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-pre-fec-ber-signal-clear {
        if-feature feature-list:HAVE_CMMD;
        if-feature feature-list:HAVE_COHERENT_OPTICS;

        description "Notification sent when coherent network-interface pre FEC BER Signal recovered to Clear Threshold value..";

        leaf severity {
            type cml-data-types:cml_notif_severity_t;
            description "Notification severity level (value: MINOR)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-rx-q-margin-pm-interval {
        if-feature feature-list:HAVE_CMMD;
        if-feature feature-list:HAVE_COHERENT_OPTICS;

        description "Notification sent when coherent network-interface Q-margin value reaches threshold limit..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-rx-q-margin-pm-recovered {
        if-feature feature-list:HAVE_CMMD;
        if-feature feature-list:HAVE_COHERENT_OPTICS;

        description "Notification sent when coherent network-interface Q-margin value recovers from threshold..";

        leaf severity {
            type cml-data-types:cml_notif_severity_t;
            description "Notification severity level (value: MINOR)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-current-osnr-threshold {
        if-feature feature-list:HAVE_CMMD;
        if-feature feature-list:HAVE_COHERENT_OPTICS;

        description "Notification sent when coherent network-interface OSNR value reaches threshold limit..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-current-osnr-threshold-recovered {
        if-feature feature-list:HAVE_CMMD;
        if-feature feature-list:HAVE_COHERENT_OPTICS;

        description "Notification sent when coherent network-interface OSNR value recovers from threshold..";

        leaf severity {
            type cml-data-types:cml_notif_severity_t;
            description "Notification severity level (value: MINOR)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-chromatic-dispersion {
        if-feature feature-list:HAVE_CMMD;
        if-feature feature-list:HAVE_COHERENT_OPTICS;

        description "Notification sent when coherent network-interface chromatic dispersion value reaches the threshold limit..";

        leaf severity {
            type cml-data-types:cml_notif_severity_t;
            description "Notification severity level (value: CRITICAL)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification network-interface-chromatic-dispersion-recovered {
        if-feature feature-list:HAVE_CMMD;
        if-feature feature-list:HAVE_COHERENT_OPTICS;

        description "Notification sent when coherent network-interface chromatic dispersion value recovers from threshold..";

        leaf severity {
            type cml-data-types:cml_notif_severity_t;
            description "Notification severity level (value: MINOR)";
        }

        leaf eventClass {
            type cml-data-types:cml_notif_class_t;
            description "Notification event class (value: STATE)";
        }

        leaf net-index {
            type  uint8;
        description
            "Index of network interface in a coherent optical module.";
        }

        leaf slot-index {
            type  uint8;
        description
            "Index to select a optical module slot.";
        }
    }

    notification host-interface-ingress-pcs {
        if-feature feature-list:HAVE_CMMD;
        if-feature feature-list:HAVE_COHERENT_OPTICS;

        description "Notification sent when coherent optical module Host-Interface Ingress PCS Alarm is set..";

        leaf severity {
            type cml-data-types:cml_notif_severity_t;
            description "Notification severity level (value: CRITICAL)";
        }

        leaf eventClass {
            type cml-data-types:cml_notif_class_t;
            description "Notification event class (value: STATE)";
        }

        leaf host-index {
            type  uint8;
        description
            "Index of host interface in a coherent optical module.";
        }

        leaf slot-index {
            type  uint8;
        description
            "Index to select a optical module slot.";
        }

        leaf ingress-pcs {
            type ipi-platform-terminal-device-types:terminal_device_cmm_hostif_pcs_alarm_t;
        description
            "Specifies current Host interface Ingress PhysicalCodingSublayer
                    Status.";
        }
    }

    notification host-interface-egress-pcs {
        if-feature feature-list:HAVE_CMMD;
        if-feature feature-list:HAVE_COHERENT_OPTICS;

        description "Notification sent when coherent optical module Host-Interface Egress PCS Alarm is set..";

        leaf severity {
            type cml-data-types:cml_notif_severity_t;
            description "Notification severity level (value: CRITICAL)";
        }

        leaf eventClass {
            type cml-data-types:cml_notif_class_t;
            description "Notification event class (value: STATE)";
        }

        leaf host-index {
            type  uint8;
        description
            "Index of host interface in a coherent optical module.";
        }

        leaf slot-index {
            type  uint8;
        description
            "Index to select a optical module slot.";
        }

        leaf egress-pcs {
            type ipi-platform-terminal-device-types:terminal_device_cmm_hostif_pcs_alarm_t;
        description
            "Specifies current Host interface Egress PhysicalCodingSublayer Status.";
        }
    }

    notification host-interface-interface-fault-status {
        if-feature feature-list:HAVE_CMMD;
        if-feature feature-list:HAVE_COHERENT_OPTICS;

        description "Notification sent when coherent optical module Host-Interface Fault Status is changed..";

        leaf severity {
            type cml-data-types:cml_notif_severity_t;
            description "Notification severity level (value: CRITICAL)";
        }

        leaf eventClass {
            type cml-data-types:cml_notif_class_t;
            description "Notification event class (value: STATE)";
        }

        leaf host-index {
            type  uint8;
        description
            "Index of host interface in a coherent optical module.";
        }

        leaf slot-index {
            type  uint8;
        description
            "Index to select a optical module slot.";
        }

        leaf interface-fault {
            type ipi-platform-terminal-device-types:terminal_device_cmm_hostif_fault_status_alarm_t;
        description
            "Specifies current Host interface Fault Status.";
        }
    }

}
