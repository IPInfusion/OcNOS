/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-profile-extended.yang
*
*/

submodule ipi-platform-profile-extended {

    yang-version 1.1;

    belongs-to  ipi-platform { prefix ipi-platform; }

    import feature-list {
        prefix feature-list;
        revision-date 2026-09-15;
    }

    import ipi-interface {
        prefix ipi-interface;
        revision-date 2026-03-10;
    }

    import ipi-platform-profile-types {
        prefix ipi-platform-profile-types;
        revision-date 2026-04-16;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Platform profile extended object";


    revision "2025-07-01" {
        description "Added unset notification for port channel load balance ";
        reference " 0.4.2.";
    }

    revision "2024-10-08" {
        description "added symmetric type for load balance l2 and ipv4 ";
        reference " 0.4.1.";
    }

    revision "2024-09-25" {
        description "Imported ipi-platform-profile-types";
        reference " 0.4.0.";
    }

    revision "2024-04-22" {
        description "added when condition for rtag7 ";
        reference " 0.3.5.";
    }

    revision "2024-03-20" {
        description "Reduced route-mode support for TD4 ";
        reference " 0.3.4.";
    }

    revision "2024-03-15" {
        description "Added CML_OBJ_READ_ONLY_CONFIG flag for platform container for soc configuration";
        reference " 0.3.3.";
    }

    revision "2023-10-02" {
        description "Add load-balance command for Marvell";
        reference " 0.3.1.";
    }

    revision "2023-09-25" {
        description "Added when condition for type attribute ";
        reference " 0.3.0.";
    }

    revision "2023-04-11" {
        description "Blocked load balance command for tomahaw3 ";
        reference " 0.2.3.";
    }

    revision "2023-03-17" {
        description "Enabling RTAG7 MPLS option in DC IP BASE";
        reference " 0.2.2.";
    }

    revision "2023-01-12" {
        description "Removed forwarding profile config support for HR4";
        reference " 0.2.1.";
    }

    revision "2022-11-29" {
        description "Addressed make cmlgen warnings";
        reference " 0.2.0.";
    }

    revision "2022-07-20" {
        description "Added implicit_delete on port-channel container";
        reference " 0.1.8.";
    }

    revision "2022-06-01" {
        description "Updated the yang file with feature";
        reference " 0.1.7.";
    }

    revision "2022-01-21" {
        description "Added when tag to all load-balance child containers";
        reference " 0.1.6.";
    }

    revision "2022-01-11" {
        description "Added when tag to inner-ipv4 non-symmetric";
        reference " 0.1.5.";
    }

    revision "2022-01-05" {
        description "Changed cpu-q-default from attribute to rpc";
        reference " 0.1.4.";
    }

    revision "2022-01-03" {
        description "Added implicit-delete to load-balance config groupping";
        reference " 0.1.3.";
    }

    revision "2021-12-30" {
        description "Removed autoPopulate tag from platform container";
        reference " 0.1.2.";
    }

    revision "2021-12-27" {
        description "Added when tag to mpls-ler container";
        reference " 0.1.1.";
    }

    revision "2021-11-22" {
        description "Initial Version";
        reference " 0.1.0.";
    }

    grouping platform-extended-forwarding-profile-config {
        description
            "Grouping for extended platform forwarding profile configuration data";
        leaf profile  {
            if-feature feature-list:HAVE_BCM_UFT;
            if-feature feature-list:NOT_HAVE_DUNE;
            type  ipi-platform-profile-types:platform_forwarding_profile_t;
            default "l2-profile-three";
            description "This Object is to check forwarding profile limit";
        } // END of profile definition.

    } // END of platform-extended-forwarding-profile-config definition.
    grouping platform-extended-forwarding-profile-route-modes-config {
        description
            "Grouping for extended platform forwarding profile route mode
                        configuration data";
        leaf route-mode  {
            if-feature feature-list:HAVE_BCM_UFT;
            if-feature feature-list:NOT_HAVE_DUNE;
            type  ipi-platform-profile-types:platform_forwarding_profile_route_mode_t;
            default "wide";
            description "This Object is to check forwarding profile limit";
        } // END of route-mode definition.

    } // END of platform-extended-forwarding-profile-route-modes-config definition.
    grouping platform-custom-profile-config {
        description
            "Grouping for extended platform custom-profile configuration data";
        leaf l2-banks  {
            type  uint8 {
                 range "1..24"  {
                    description "1..24: Supported range 1 - 24";
                 }
            }
            description "Use this attribute to set Sets memory allocation profile - Use `show
                        forwarding profile limit` to check size";
        } // END of l2-banks definition.

        leaf l3-banks  {
            type  uint8 {
                 range "1..23"  {
                    description "1..23: Supported range 1 - 23";
                 }
            }
            description "Use this attribute to set Sets memory allocation profile - Use `show
                        forwarding profile limit` to check size";
        } // END of l3-banks definition.

        leaf lpm-banks  {
            // when " ipi-platform-profile-extended:platform/config/soc == '4' + ipi-platform-profile-extended:platform/config/soc == '5' ";
            type  ipi-platform-profile-types:platform_lpm_custom_profile_t;
            description "Use this attribute to set Sets memory allocation profile - Use `show
                        forwarding profile limit` to check size";
        } // END of lpm-banks definition.

        leaf vlan-xlate-banks  {
            // when " ipi-platform-profile-extended:platform/config/soc == '11' ";
            type  uint8 {
                 range "1..23"  {
                    description "1..23: Supported range 1 - 23";
                 }
            }
            description "Use this attribute to set Sets memory allocation profile - Use `show
                        forwarding profile limit` to check size";
        } // END of vlan-xlate-banks definition.

        leaf ep-vlan-xlate-banks  {
            // when " ipi-platform-profile-extended:platform/config/soc == '11' ";
            type  uint8 {
                 range "1..23"  {
                    description "1..23: Supported range 1 - 23";
                 }
            }
            description "Use this attribute to set Sets memory allocation profile - Use `show
                        forwarding profile limit` to check size";
        } // END of ep-vlan-xlate-banks definition.

        leaf mpls-banks  {
            // when " ipi-platform-profile-extended:platform/config/soc == '11' ";
            if-feature feature-list:HAVE_MPLS;
            type  uint8 {
                 range "1..23"  {
                    description "1..23: Supported range 1 - 23";
                 }
            }
            description "Use this attribute to set Sets memory allocation profile - Use `show
                        forwarding profile limit` to check size";
        } // END of mpls-banks definition.

    } // END of platform-custom-profile-config definition.
    grouping platform-profile-mdb-config {
        description
            "Grouping for extended profile mdb configuration data";
        leaf type  {
            type  ipi-platform-profile-types:platform_mdb_profile_t;
            mandatory true;
            description "forwarding MDB profile";
        } // END of type definition.

        leaf kaps  {
            type  ipi-platform-profile-types:platform_mdb_kaps_type_t;
            mandatory true;
            description "forwarding MDB profile KAPS-CFG";
        } // END of kaps definition.

    } // END of platform-profile-mdb-config definition.
    grouping platform-profile-table-limit-state {
        description
            "Grouping for extended profile table-limit operational state data";
        leaf forwarding-profile  {
            if-feature feature-list:NOT_HAVE_DUNE;
            type  ipi-platform-profile-types:platform_forwarding_profile_t;
            description "Profile active in hardware";
        } // END of forwarding-profile definition.

    } // END of platform-profile-table-limit-state definition.
    grouping platform-profile-table-size-state {
        description
            "Grouping for extended profile table-size operational state data";
        leaf profile  {
            type  ipi-platform-profile-types:platform_forwarding_profile_t;
            description "Profile name";
        } // END of profile definition.

        leaf mac-address-entries  {
            type  uint32;
            description "MAC-Table size";
        } // END of mac-address-entries definition.

        leaf host-ipv4-entries  {
            type  uint32;
            description "Host-Table (UC) IPv4 size";
        } // END of host-ipv4-entries definition.

        leaf host-ipv6-entries  {
            type  uint32;
            description "Host-Table (UC) IPv6 size";
        } // END of host-ipv6-entries definition.

        leaf prefix-ipv4-entries  {
            type  uint32;
            description "Prefix-Table (UC) IPv4 size";
        } // END of prefix-ipv4-entries definition.

        leaf prefix-ipv6-entries  {
            type  uint32;
            description "Prefix-Table (UC) IPv6 size";
        } // END of prefix-ipv6-entries definition.

        leaf prefix-ipv6-128-entries  {
            if-feature feature-list:NOT_HAVE_HELIX4;
            type  uint32;
            description "Prefix-Table (UC) IPv6 (>=65) size";
        } // END of prefix-ipv6-128-entries definition.

        leaf mpls-entries  {
            if-feature feature-list:HAVE_HELIX4;
            if-feature feature-list:HAVE_MPLS;
            type  uint32;
            description "MPLS table size";
        } // END of mpls-entries definition.

        leaf vlan-xlate-entries  {
            if-feature feature-list:HAVE_HELIX4;
            type  uint32;
            description "VLAN xlate table size";
        } // END of vlan-xlate-entries definition.

        leaf egree-vlan-xlate-entries  {
            if-feature feature-list:HAVE_HELIX4;
            type  uint32;
            description "Egress VLAN xlate table size";
        } // END of egree-vlan-xlate-entries definition.

    } // END of platform-profile-table-size-state definition.
    grouping platform-extended-rate-limit-config {
        description
            "Grouping for extended profile rate-limit configuration data";
        leaf lossy  {
            if-feature feature-list:NOT_HAVE_DUNE;
            type  ipi-platform-profile-types:platform_cpu_queue_lossy_t;
            description "Configure CPU queue as lossy or lossless";
        } // END of lossy definition.

        leaf monitor  {
            if-feature feature-list:NOT_HAVE_DUNE;
            type  ipi-platform-profile-types:platform_cpu_queue_monitor_t;
            description "monitor CPU queue usage";
        } // END of monitor definition.

    } // END of platform-extended-rate-limit-config definition.
    grouping platform-cpu-control-packets-config {
        description
            "Grouping for extended profile cpu control packets configuration data";
        leaf disable-vxlan  {
            type  empty;
            description "This Object is to disable the control packets to CPU";
        } // END of disable-vxlan definition.

    } // END of platform-cpu-control-packets-config definition.
    grouping platform-load-balance-ipv4-inner-config {
        description
            "Grouping for extended profile load-balance ipv4 inner configuration
                        data";
        leaf src-dest-ipv4-address-based  {
            if-feature feature-list:HAVE_DNX;
            type  empty;
            description "Source Destination IPV4 based load balancing";
        } // END of src-dest-ipv4-address-based definition.

        leaf symmetric-type  {
            if-feature feature-list:HAVE_DNX;
            type  ipi-platform-profile-types:platform_loadbalance_type_t;
            description "Destination IPV4 based load balancing";
        } // END of symmetric-type definition.

        leaf protocol-id-based  {
            if-feature feature-list:HAVE_DNX;
            type  empty;
            description "Protocol Id based load balancing";
        } // END of protocol-id-based definition.

    } // END of platform-load-balance-ipv4-inner-config definition.
    grouping platform-load-balance-l3-tunnel-config {
        description
            "Grouping for extended profile load-balance l3 tunnel configuration
                        data";
        leaf outer-l3-header  {
            type  empty;
            description "Used to set Load balance tunneled packets based on outer header";
        } // END of outer-l3-header definition.

    } // END of platform-load-balance-l3-tunnel-config definition.
    grouping platform-load-balance-vxlan-inner-l2-config {
        description
            "Grouping for extended profile load-balance vxlan inner l2
                        configuration data";
        leaf dest-mac-based  {
            type  empty;
            description "VXLAN Destination MAC address based load balancing";
        } // END of dest-mac-based definition.

        leaf src-mac-based  {
            type  empty;
            description "VXLAN Source MAC address based load balancing";
        } // END of src-mac-based definition.

    } // END of platform-load-balance-vxlan-inner-l2-config definition.
    grouping platform-load-balance-vxlan-inner-l3-config {
        description
            "Grouping for extended profile load-balance vxlan inner l3
                        configuration data";
        leaf src-ip-based  {
            type  empty;
            description "VXLAN Source IP";
        } // END of src-ip-based definition.

        leaf dest-ip-based  {
            type  empty;
            description "VXLAN Destination IP";
        } // END of dest-ip-based definition.

        leaf src-l4-port-based  {
            type  empty;
            description "vxlan Source l4 port";
        } // END of src-l4-port-based definition.

        leaf dest-l4-port-based  {
            type  empty;
            description "vxlan Destination l4 port";
        } // END of dest-l4-port-based definition.

        leaf protocol-id-based  {
            type  empty;
            description "vxlan Protocol Id";
        } // END of protocol-id-based definition.

    } // END of platform-load-balance-vxlan-inner-l3-config definition.
    grouping platform-load-balance-mpls-ler-inner-l2-config {
        description
            "Grouping for extended profile load-balance mpls-ler inner l2
                        configuration data";
        leaf dest-mac-based  {
            type  empty;
            description "mpls destination Mac address based load balancing";
        } // END of dest-mac-based definition.

        leaf src-mac-based  {
            type  empty;
            description "mpls source Mac address based load balancing";
        } // END of src-mac-based definition.

        leaf ether-type-based  {
            type  empty;
            description "mpls Ether-type based load balancing";
        } // END of ether-type-based definition.

        leaf vlan-based  {
            type  empty;
            description "mpls Vlan based load balancing";
        } // END of vlan-based definition.

    } // END of platform-load-balance-mpls-ler-inner-l2-config definition.
    grouping platform-load-balance-mpls-ler-inner-l3-config {
        description
            "Grouping for extended profile load-balance mpls-ler inner l3
                        configuration data";
        leaf src-ip-address-based  {
            type  empty;
            description "Source IP";
        } // END of src-ip-address-based definition.

        leaf dest-ip-address-based  {
            type  empty;
            description "Destination IP";
        } // END of dest-ip-address-based definition.

        leaf src-l4-port-based  {
            type  empty;
            description "Source l4 port";
        } // END of src-l4-port-based definition.

        leaf dest-l4-port-based  {
            type  empty;
            description "Destination l4 port";
        } // END of dest-l4-port-based definition.

        leaf protocol-id-based  {
            type  empty;
            description "Load balance based on the protocol-id (IPv4) field";
        } // END of protocol-id-based definition.

    } // END of platform-load-balance-mpls-ler-inner-l3-config definition.
    grouping platform-load-balance-l4-port-config {
        description
            "Grouping for extended profile load-balance l4-port configuration data";
        leaf src-dest-based  {
            type  empty;
            description "Source Destination l4port based load balancing";
        } // END of src-dest-based definition.

        leaf symmetric-type  {
            type  ipi-platform-profile-types:platform_loadbalance_type_t;
            description "Non-symmetrical based load balancing";
        } // END of symmetric-type definition.

    } // END of platform-load-balance-l4-port-config definition.
    grouping platform-extended-load-balance-config {
        description
            "Grouping for load-balance config objects.";
        leaf mpls-ip-payload  {
            if-feature feature-list:NOT_HAVE_DUNE;
            type  empty;
            description "This Object is set for load balancing based on MPLS IP payload";
        } // END of mpls-ip-payload definition.

        leaf trill  {
            if-feature feature-list:HAVE_TRILLD;
            if-feature feature-list:NOT_HAVE_DUNE;
            type  ipi-platform-profile-types:platform_load_trill_t;
            description "This Object is used to set trill header";
        } // END of trill definition.

        leaf hash  {
            if-feature feature-list:NOT_HAVE_DUNE;
            type  ipi-platform-profile-types:platform_load_hash_t;
            description "This Object is used to set (hash values)CRC";
        } // END of hash definition.

        leaf macro-flow-based  {
            if-feature feature-list:NOT_HAVE_DUNE;
            type  empty;
            description "macro-flow based dynamic hash selection";
        } // END of macro-flow-based definition.

    } // END of platform-extended-load-balance-config definition.
    grouping platform-extended-load-balance-l2-config {
        description
            "Grouping for load-balance l2 config objects.";
        leaf src-dest-mac-based  {
            if-feature feature-list:HAVE_DNX;
            type  empty;
            description "Source Destination based load balancing";
        } // END of src-dest-mac-based definition.

        leaf symmetric-type  {
            if-feature feature-list:HAVE_DNX;
            type  ipi-platform-profile-types:platform_loadbalance_type_t;
            description "Choose Symmetrical or Non symmetrical based load balancing";
        } // END of symmetric-type definition.

    } // END of platform-extended-load-balance-l2-config definition.
    grouping platform-extended-load-balance-inner-l2-config {
        description
            "Grouping for load-balance inner l2 config objects.";
        leaf ether-type-based  {
            type  empty;
            description "This Object is set for Ether-type based load balancing";
        } // END of ether-type-based definition.

        leaf vlan-based  {
            type  empty;
            description "This Object is set for Vlan based load balancing";
        } // END of vlan-based definition.

        leaf src-dest-mac-based  {
            if-feature feature-list:HAVE_DNX;
            type  empty;
            description "Source Destination based load balancing";
        } // END of src-dest-mac-based definition.

        leaf symmetric-type  {
            if-feature feature-list:HAVE_DNX;
            type  ipi-platform-profile-types:platform_loadbalance_type_t;
            description "Non symmetrical based load balancing";
        } // END of symmetric-type definition.

    } // END of platform-extended-load-balance-inner-l2-config definition.
    grouping platform-extended-load-balance-ipv4-config {
        description
            "Grouping for load-balance ipv4 config objects.";
        leaf symmetric  {
            if-feature feature-list:NOT_HAVE_DUNE;
            if-feature feature-list:NOT_HAVE_DNX;
            type  empty;
            description "Symmetric load balancing";
        } // END of symmetric definition.

        leaf src-dest-ipv4-address-based  {
            if-feature feature-list:HAVE_DNX;
            type  empty;
            description "Source Destination IPV4 based load balancing";
        } // END of src-dest-ipv4-address-based definition.

        leaf symmetric-type  {
            if-feature feature-list:HAVE_DNX;
            type  ipi-platform-profile-types:platform_loadbalance_type_t;
            description "Choose Symmetrical or Non symmetrical based load balancing";
        } // END of symmetric-type definition.

    } // END of platform-extended-load-balance-ipv4-config definition.
    grouping platform-extended-load-balance-ipv6-config {
        description
            "Grouping for load-balance ipv6 config objects.";
        leaf symmetric  {
            if-feature feature-list:NOT_HAVE_DUNE;
            if-feature feature-list:NOT_HAVE_DNX;
            type  empty;
            description "Symmetric load balancing";
        } // END of symmetric definition.

        leaf src-dest-ipv6-address-based  {
            if-feature feature-list:HAVE_DNX;
            type  empty;
            description "Source Destination IPV6 based load balancing";
        } // END of src-dest-ipv6-address-based definition.

        leaf flow-label-based  {
            if-feature feature-list:HAVE_DNX;
            type  empty;
            description "Flowlabel based load balancing";
        } // END of flow-label-based definition.

    } // END of platform-extended-load-balance-ipv6-config definition.
    grouping platform-interface-config {
        description
            "Grouping for Platform profile interface configuration data";
        leaf name  {
            type  leafref {
                path  "/ipi-interface:interfaces/ipi-interface:interface/ipi-interface:name";
            }
            description "Interface name for which platform profile is being configured.";
        } // END of name definition.

    } // END of platform-interface-config definition.
    grouping platform-port-channel-config {
        description
            "Grouping for platform-port-channel-config configuration data";
        leaf type  {
            type  ipi-platform-profile-types:platform_lacp_psc_t;
            description "This Object is used to set LACP port-channel load-balancing and set
                        port selection criteria (PSC) on an interface";
        } // END of type definition.

    } // END of platform-port-channel-config definition.
    grouping platform-extended-soc-top {
        description
            "Grouping for Platform SoC information";
        leaf soc  {
            type  ipi-platform-profile-types:platform_soc_type_t;
            description "Attribute to indicate the SoC running on this platform. This attribute
                        cannot be configured.";
        } // END of soc definition.

    } // END of platform-extended-soc-top definition.
    grouping platform-extended-mac-ageing-top {
        description
            "Grouping for MAC ageing timer calculation";
        leaf enable-mac-ageing-timer  {
            if-feature feature-list:HAVE_L2_AGE_SHOW;
            type  empty;
            description "Use this command to enable or disable the MAC ageing timer calculation
                        in control plane";
        } // END of enable-mac-ageing-timer definition.

    } // END of platform-extended-mac-ageing-top definition.

    grouping  mac-ageing-grouping {
    description
        "MAC ageing container";
    container mac-ageing {
        if-feature feature-list:HAVE_CMMD;
        if-feature feature-list:NOT_HAVE_MARVELL;
        if-feature feature-list:NOT_HAVE_MARVELL;
        if-feature feature-list:HAVE_BROADCOM_OR_HAVE_MARVELL;
        description
            "MAC ageing container";
        container config {
            description
                "Config container for mac-ageing parameters";
            uses platform-extended-mac-ageing-top;
        } // END of config-container definition.
        container state {
            config false;
            description
                "State container for mac-ageing parameters";
            uses platform-extended-mac-ageing-top;
        } // END of state-container definition.
    } // END of mac-ageing-container definition.
    } // END of mac-ageing-grouping definition.

    grouping  platform-grouping {
    description
        "Describes the platform";
    container platform {
        if-feature feature-list:HAVE_CMMD;
        if-feature feature-list:NOT_HAVE_MARVELL;
        if-feature feature-list:NOT_HAVE_MARVELL;
        if-feature feature-list:HAVE_BROADCOM_OR_HAVE_MARVELL;
        description
            "Describes the platform";
        container config {
            description
                "platform related confguration data";
            uses platform-extended-soc-top;
        } // END of config-container definition.
    } // END of platform-container definition.
    } // END of platform-grouping definition.

    grouping  mdb-grouping {
    description
        "Container for MDB profile";
    container mdb {
        if-feature feature-list:HAVE_DNX;
        if-feature feature-list:HAVE_BCM_UFT;
        if-feature feature-list:HAVE_CMMD;
        if-feature feature-list:NOT_HAVE_MARVELL;
        if-feature feature-list:NOT_HAVE_MARVELL;
        if-feature feature-list:HAVE_BROADCOM_OR_HAVE_MARVELL;
        description
            "Container for MDB profile";
        container config {
            presence "yes";
            description
                "Configuration data for MDB profile";
            uses platform-profile-mdb-config;
        } // END of config-container definition.
        container state {
            config false;
            description
                "Operational state data for MDB profile";
            uses platform-profile-mdb-config;
        } // END of state-container definition.
    } // END of mdb-container definition.
    } // END of mdb-grouping definition.

    grouping  custom-profile-grouping {
    description
        "Container for custom profile";
    container custom-profile {
        // when " ipi-platform-profile:profiles/forwarding-profiles/config/profile == '8' ";
        if-feature feature-list:HAVE_BCM_UFT;
        if-feature feature-list:HAVE_CMMD;
        if-feature feature-list:NOT_HAVE_DUNE;
        if-feature feature-list:NOT_HAVE_MARVELL;
        if-feature feature-list:NOT_HAVE_MARVELL;
        if-feature feature-list:HAVE_BROADCOM_OR_HAVE_MARVELL;
        description
            "Container for custom profile";
        container config {
            description
                "Configuration data for custom profile";
            uses platform-custom-profile-config;
        } // END of config-container definition.
        container state {
            config false;
            description
                "Operational state data for custom profile";
            uses platform-custom-profile-config;
        } // END of state-container definition.
    } // END of custom-profile-container definition.
    } // END of custom-profile-grouping definition.

    grouping  state-grouping {
    description
        "Operational state data for table-limit";
    container state {
        if-feature feature-list:HAVE_BCM_UFT;
        if-feature feature-list:HAVE_CMMD;
        if-feature feature-list:HAVE_BROADCOM_OR_HAVE_MARVELL;
        config false;
        description
            "Operational state data for table-limit";
        uses platform-profile-table-limit-state;
    } // END of state-container definition.
    } // END of state-grouping definition.

    grouping  table-sizes-grouping {
    description
        "Container for table-sizes";
    container table-sizes {
        if-feature feature-list:HAVE_CMMD;
        if-feature feature-list:NOT_HAVE_DUNE;
        if-feature feature-list:NOT_HAVE_MARVELL;
        if-feature feature-list:NOT_HAVE_MARVELL;
        if-feature feature-list:HAVE_BROADCOM_OR_HAVE_MARVELL;
        config false;
        description
            "Container for table-sizes";

        list table-size {
            key "profile";
            config false;
            description
                "The list of table-size";
            leaf profile  {
                type  leafref {
                    path  "../state/profile";
                }
                description "Forwarding Profile KAPS Profile type.";
            } // END of profile definition.

            container state {
                config false;
                description
                    "This container defines table-size information Operational states.";
                uses platform-profile-table-size-state;
            } // END of state-container definition.
        } // End of table-size-list
    } // END of table-sizes-container definition.
    } // END of table-sizes-grouping definition.

    grouping  inner-l2-grouping {
    description
        "Container for inner-l2";
    container inner-l2 {
        // when " ipi-platform-profile:hardware/load-balance/config/enable ";
        if-feature feature-list:HAVE_L2;
        if-feature feature-list:HAVE_DNX;
        if-feature feature-list:HAVE_CMMD;
        if-feature feature-list:NOT_HAVE_MARVELL;
        if-feature feature-list:NOT_HAVE_MARVELL;
        if-feature feature-list:HAVE_BROADCOM_OR_HAVE_MARVELL;
        description
            "Container for inner-l2";
        container config {
            description
                "Configuration data for l2 inner";
            uses platform-extended-load-balance-inner-l2-config;
        } // END of config-container definition.
        container state {
            config false;
            description
                "Operational state data for l2 inner";
            uses platform-extended-load-balance-inner-l2-config;
        } // END of state-container definition.
    } // END of inner-l2-container definition.
    } // END of inner-l2-grouping definition.

    grouping  inner-ipv4-grouping {
    description
        "Container for inner-ipv4";
    container inner-ipv4 {
        // when " ipi-platform-profile:hardware/load-balance/config/enable ";
        if-feature feature-list:HAVE_L3;
        if-feature feature-list:HAVE_DNX;
        if-feature feature-list:HAVE_CMMD;
        if-feature feature-list:NOT_HAVE_MARVELL;
        if-feature feature-list:NOT_HAVE_MARVELL;
        if-feature feature-list:HAVE_BROADCOM_OR_HAVE_MARVELL;
        description
            "Container for inner-ipv4";
        container config {
            description
                "Configuration data for ipv4 inner";
            uses platform-load-balance-ipv4-inner-config;
        } // END of config-container definition.
        container state {
            config false;
            description
                "Operational state data for ipv4 inner";
            uses platform-load-balance-ipv4-inner-config;
        } // END of state-container definition.
    } // END of inner-ipv4-container definition.
    } // END of inner-ipv4-grouping definition.

    grouping  tunnel-grouping {
    description
        "Container for l3 tunnel";
    container tunnel {
        // when " ipi-platform-profile:hardware/load-balance/config/enable ";
        if-feature feature-list:HAVE_L3;
        if-feature feature-list:HAVE_CMMD;
        if-feature feature-list:NOT_HAVE_DUNE;
        if-feature feature-list:NOT_HAVE_MARVELL;
        if-feature feature-list:NOT_HAVE_MARVELL;
        if-feature feature-list:HAVE_BROADCOM_OR_HAVE_MARVELL;
        description
            "Container for l3 tunnel";
        container config {
            description
                "Configuration data for l3 tunnel";
            uses platform-load-balance-l3-tunnel-config;
        } // END of config-container definition.
        container state {
            config false;
            description
                "Operational state data for l3 tunnel";
            uses platform-load-balance-l3-tunnel-config;
        } // END of state-container definition.
    } // END of tunnel-container definition.
    } // END of tunnel-grouping definition.

    grouping  vxlan-grouping {
    description
        "Container for vxlan";
    container vxlan {
        // when " ipi-platform-profile:hardware/load-balance/config/enable ";
        if-feature feature-list:HAVE_VXLAN;
        if-feature feature-list:HAVE_CMMD;
        if-feature feature-list:NOT_HAVE_DUNE;
        if-feature feature-list:NOT_HAVE_MARVELL;
        if-feature feature-list:NOT_HAVE_MARVELL;
        if-feature feature-list:HAVE_BROADCOM_OR_HAVE_MARVELL;
        description
            "Container for vxlan";
        container inner-l2 {
            description
                "Container for vxlan inner l2";
            container config {
                description
                    "Configuration data for inner l2 vxlan";
                uses platform-load-balance-vxlan-inner-l2-config;
            } // END of config-container definition.
            container state {
                config false;
                description
                    "Operational state data for inner l2 vxlan";
                uses platform-load-balance-vxlan-inner-l2-config;
            } // END of state-container definition.
        } // END of inner-l2-container definition.
        container inner-l3 {
            description
                "Container for vxlan inner l3";
            container config {
                description
                    "Configuration data for inner l3 vxlan";
                uses platform-load-balance-vxlan-inner-l3-config;
            } // END of config-container definition.
            container state {
                config false;
                description
                    "Operational state data for inner l3 vxlan";
                uses platform-load-balance-vxlan-inner-l3-config;
            } // END of state-container definition.
        } // END of inner-l3-container definition.
    } // END of vxlan-container definition.
    } // END of vxlan-grouping definition.

    grouping  mpls-ler-grouping {
    description
        "Container for mpls-ler";
    container mpls-ler {
        // when " ipi-platform-profile:hardware/load-balance/config/enable ";
        if-feature feature-list:HAVE_CMMD;
        if-feature feature-list:NOT_HAVE_DUNE;
        if-feature feature-list:NOT_HAVE_MARVELL;
        if-feature feature-list:NOT_HAVE_MARVELL;
        if-feature feature-list:HAVE_BROADCOM_OR_HAVE_MARVELL;
        description
            "Container for mpls-ler";
        container inner-l2 {
            // when " !ipi-platform-profile-extended:mpls-ler/inner-l3 ";
            description
                "Container for mpls-ler inner l2";
            container config {
                description
                    "Configuration data for mpls-ler inner l2";
                uses platform-load-balance-mpls-ler-inner-l2-config;
            } // END of config-container definition.
            container state {
                config false;
                description
                    "Operational state data for mpls-ler inner l2";
                uses platform-load-balance-mpls-ler-inner-l2-config;
            } // END of state-container definition.
        } // END of inner-l2-container definition.
        container inner-l3 {
            // when " !ipi-platform-profile-extended:mpls-ler/inner-l2 ";
            description
                "Container for mpls-ler inner l3";
            container config {
                description
                    "Configuration data for mpls-ler inner l3";
                uses platform-load-balance-mpls-ler-inner-l3-config;
            } // END of config-container definition.
            container state {
                config false;
                description
                    "Operational state data for mpls-ler inner l3";
                uses platform-load-balance-mpls-ler-inner-l3-config;
            } // END of state-container definition.
        } // END of inner-l3-container definition.
    } // END of mpls-ler-container definition.
    } // END of mpls-ler-grouping definition.

    grouping  l4-port-grouping {
    description
        "Container for l4 port load-balance";
    container l4-port {
        // when " ipi-platform-profile:hardware/load-balance/config/enable ";
        if-feature feature-list:HAVE_DNX;
        if-feature feature-list:HAVE_CMMD;
        if-feature feature-list:NOT_HAVE_MARVELL;
        if-feature feature-list:NOT_HAVE_MARVELL;
        if-feature feature-list:HAVE_BROADCOM_OR_HAVE_MARVELL;
        description
            "Container for l4 port load-balance";
        container config {
            description
                "Configuration data for l4 port";
            uses platform-load-balance-l4-port-config;
        } // END of config-container definition.
        container state {
            config false;
            description
                "Operational state data for l4 port";
            uses platform-load-balance-l4-port-config;
        } // END of state-container definition.
    } // END of l4-port-container definition.
    } // END of l4-port-grouping definition.

    grouping  cpu-control-grouping {
    description
        "Container for cpu-control";
    container cpu-control {
        if-feature feature-list:HAVE_VXLAN;
        if-feature feature-list:HAVE_CMMD;
        if-feature feature-list:NOT_HAVE_DUNE;
        if-feature feature-list:NOT_HAVE_MARVELL;
        if-feature feature-list:NOT_HAVE_MARVELL;
        if-feature feature-list:HAVE_BROADCOM_OR_HAVE_MARVELL;
        description
            "Container for cpu-control";
        container packets {
            description
                "Container for cpu-control packets";
            container config {
                description
                    "Configuration data for cpu-control packets";
                uses platform-cpu-control-packets-config;
            } // END of config-container definition.
            container state {
                config false;
                description
                    "Operational state data for cpu-control packets";
                uses platform-cpu-control-packets-config;
            } // END of state-container definition.
        } // END of packets-container definition.
    } // END of cpu-control-container definition.
    } // END of cpu-control-grouping definition.

    grouping  port-channel-grouping {
    description
        "Configuration data for Platform profile port-channel";
    container port-channel {
        if-feature feature-list:HAVE_CMMD;
        if-feature feature-list:NOT_HAVE_MARVELL;
        if-feature feature-list:NOT_HAVE_MARVELL;
        if-feature feature-list:HAVE_BROADCOM_OR_HAVE_MARVELL;
        description
            "Configuration data for Platform profile port-channel";
        container interfaces {
            if-feature feature-list:HAVE_LACP;
            if-feature feature-list:NOT_HAVE_DUNE;
            description
                "Configuration data for Platform profile interfaces";

            list interface {
                key "name";
                description
                    "List of platform profile interfaces";
                leaf name  {
                    type  leafref {
                        path  "../config/name";
                    }
                    description "Interface name for which OSPFv3 is being configured.";
                } // END of name definition.

                container config {
                    description
                        "Configuration data for OSPFv3 interface";
                    uses platform-interface-config;
                    uses platform-port-channel-config;
                } // END of config-container definition.
                container state {
                    config false;
                    description
                        "Operational state data for OSPFv3 interface";
                    uses platform-interface-config;
                    uses platform-port-channel-config;
                } // END of state-container definition.
            } // End of interface-list
        } // END of interfaces-container definition.
    } // END of port-channel-container definition.
    } // END of port-channel-grouping definition.


}
