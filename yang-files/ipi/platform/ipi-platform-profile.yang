/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-profile.yang
*
*/

submodule ipi-platform-profile {

    yang-version 1.1;

    belongs-to  ipi-platform { prefix ipi-platform; }

    import feature-list {
        prefix feature-list;
        revision-date 2026-09-15;
    }

    import cml-data-types {
        prefix cml-data-types;
        revision-date 2026-05-15;
    }

    import ipi-platform-profile-types {
        prefix ipi-platform-profile-types;
        revision-date 2026-04-16;
    }

    include ipi-platform-profile-extended { revision-date 2025-07-01;}
    include ipi-platform-profile-hardware-l2vpn-instances-limits { revision-date 2025-11-12;}
    include ipi-platform-profile-hardware-routing-limits { revision-date 2025-10-20;}
    organization
        "IP Infusion Inc.";

    contact
        "Address: 3965 Freedom Circle, Suite 200, Santa Clara, CA 95054
         Phone: +1 408-400-1900
         E-mail: support@ipinfusion.com
         Web: http://www.ipinfusion.com/";

    description
        "Datamodel for Platform profile object";


    revision "2026-08-14" {
        description "Added kbp-disable command to all kbp platforms";
        reference " 0.30.46.";
    }

    revision "2026-04-16" {
        description "Added new cpu-queue mgmt under ltsw platform";
        reference " 0.30.45.";
    }

    revision "2026-03-23" {
        description "Making l3-slowpath/rsvd mc cpu queue configurable ";
        reference " 0.30.44.";
    }

    revision "2026-02-12" {
        description "Handled twamp-ipv4 disable command for Q2 ";
        reference " 0.30.43.";
    }

    revision "2026-02-09" {
        description "changed the config sequence for twamp-ipv4 and qos-policer ";
        reference " 0.30.42.";
    }

    revision "2026-01-06" {
        description "Disable unset of twamp-ipv6-mpls on Q2 ";
        reference " 0.30.41.";
    }

    revision "2025-12-26" {
        description "Given support to enable/disable ingress v6 group for LTSW platform";
        reference " 0.30.40.";
    }

    revision "2025-12-11" {
        description "Remove the not supported ipv6-bgp-flowspec filter creation";
        reference " 0.30.23.";
    }

    revision "2025-11-13" {
        description "Added a new grouping to get filters stats with unit/core";
        reference " 0.30.22.";
    }

    revision "2025-11-12" {
        description "Rename E-Line service to E-LINE in hardware-l2vpn-limits";
        reference " 0.30.21.";
    }

    revision "2025-10-31" {
        description "Added dependentObject for filter disable case";
        reference " 0.30.20.";
    }

    revision "2025-10-30" {
        description "moving profile ingress-mirror to the last in the order";
        reference " 0.30.19.";
    }

    revision "2025-10-26" {
        description "Add stream-telemetry yaml file into hardware-l2vpn-limits";
        reference " 0.30.18.";
    }

    revision "2025-10-23" {
        description "Disabled creating twamp-ipv6-mpls group on Q2 platforms. It is only required on Q1 platforms. ";
        reference " 0.30.17.";
    }

    revision "2025-10-20" {
        description "Renamed hardware-capacity container to hardware-routing-limits and added new hardware-l2vpn-instances state container";
        reference " 0.30.16.";
    }

    revision "2025-10-07" {
        description "Support for hash-offset load-balance configuration is required only on Q1 platforms.";
        reference " 0.30.15.";
    }

    revision "2025-09-16" {
        description "updated the helpstring for evpn-mpls-mh prependstr";
        reference " 0.30.14.";
    }

    revision "2025-09-13" {
        description "Add gnmi support to the hardware-capacity counters";
        reference " 0.30.13.";
    }

    revision "2025-09-12" {
        description "Add hardware-capacity state container";
        reference " 0.30.12.";
    }

    revision "2025-09-11" {
        description "Updated helpstring for evpn-mpls-mh hw filter";
        reference " 0.30.11.";
    }

    revision "2025-09-10" {
        description "Modification of CPU queues(PLATFORM_CPU_QUEUE_NAME_T) for XGS platform ";
        reference " 0.30.10.";
    }

    revision "2025-09-09" {
        description "Added sniff to CPU queue type";
        reference " 0.30.9.";
    }

    revision "2025-09-05" {
        description "Streaming Telemetry support for hardware profile filters";
        reference " 0.30.8.";
    }

    revision "2025-08-28" {
        description "Support AS5916-54XL";
        reference " 0.30.7.";
    }

    revision "2025-08-07" {
        description "Blocking hardware-profile filter ingress-ipv6 for LTSW platform";
        reference " 0.30.6.";
    }

    revision "2025-07-28" {
        description "Supporting hardware-profile filter bfd-group for TH5";
        reference " 0.30.5.";
    }

    revision "2025-07-10" {
        description "Added new attributes trunk-hash-offset, ecmp-hash-offset and hash-seed under load-balance config";
        reference " 0.30.4.";
    }

    revision "2025-07-08" {
        description "hardware-profile eedb mode for scaling";
        reference " 0.30.3.";
    }

    revision "2025-07-03" {
        description "modified the datatype and removed unset cli for ingress-acl";
        reference " 0.30.2.";
    }

    revision "2025-06-18" {
        description "Added HAVE_DNX for ingress-ipv4-subif-extended";
        reference " 0.30.1.";
    }

    revision "2025-06-16" {
        description "Added twamp-light control as a dependentObject for hardware-profile";
        reference " 0.30.0.";
    }

    revision "2025-06-11" {
        description "Added Dependent Object for advanced parser to address the sequence during reboot";
        reference " 0.29.29.";
    }

    revision "2025-06-09" {
        description "Blocking forwarding profile for Hurican4 family";
        reference " 0.29.28.";
    }

    revision "2025-05-22" {
        description "Blocking hardware-profile filter ingress-ipv6 for TD4";
        reference " 0.29.27.";
    }

    revision "2025-05-14" {
        description "Blocking hardware-profile filter bfd-group for TH5";
        reference " 0.29.26.";
    }

    revision "2025-05-01" {
        description "Moved up ingress-ipv4-qos-copp/ingress-ipv6-qos-copp attr";
        reference " 0.29.25.";
    }

    revision "2025-04-28" {
        description "Added hardware-profile filter ingress-qos-ipv6";
        reference " 0.29.24.";
    }

    revision "2025-04-25" {
        description "hardware-profile filter egress-ipv6 CLI disabled for ltsw_new";
        reference " 0.29.23.";
    }

    revision "2025-04-10" {
        description "Added hardware-profile qos-subif-policer and qos-subif-extended";
        reference " 0.29.22.";
    }

    revision "2025-04-08" {
        description "added hardware-profile ingress-ipv4-subif-ext";
        reference " 0.29.21.";
    }

    revision "2025-04-07" {
        description "Added support for Speculative options for DPI";
        reference " 0.29.20.";
    }

    revision "2025-04-04" {
        description "Added mode2/mode3 for hardware-profile port mode for S9600-28dx/64x/56dx/32x";
        reference " 0.29.19.";
    }

    revision "2025-03-27" {
        description "Added Roce Qpairs for Load-balance";
        reference " 0.29.18.";
    }

    revision "2025-03-25" {
        description "Add ingress-ipv6-qos-copp filter and remove ingress-ipv4-qos and copp when dependency";
        reference " 0.29.17.";
    }

    revision "2025-03-20" {
        description "rearranged attribute order for qos-policer and ingress-ipv6";
        reference " 0.29.16.";
    }

    revision "2025-03-17" {
        description "Added kbp-disable to hardware-profile--config";
        reference " 0.29.15.";
    }

    revision "2025-02-21" {
        description "removed mode2/mode3 for hardware-profile port mode for S9600-28dx/64x/56dx/32x";
        reference " 0.29.14.";
    }

    revision "2025-02-14" {
        description "Added support for hardware-profile port mode for S9610-46DX and 48DX";
        reference " 0.29.13.";
    }

    revision "2025-01-31" {
        description "Fix for the issue while enabling hardware-profile twamp";
        reference " 0.29.12.";
    }

    revision "2025-01-30" {
        description "Removed support for hardware-profile port mode for UFIS9510_28DC ";
        reference " 0.29.11.";
    }

    revision "2025-01-06" {
        description "Updated ingress-ipv4-qos-copp filter";
        reference " 0.29.10.";
    }

    revision "2024-12-16" {
        description "Supported ipv4/ipv6 acl on l2 interfaces";
        reference " 0.29.9.";
    }

    revision "2024-12-14" {
        description "Added hardware-profile filter ingress-ipv4-qos-copp";
        reference " 0.29.8.";
    }

    revision "2024-12-12" {
        description "Readded the UFT TD4 options";
        reference " 0.29.7.";
    }

    revision "2024-12-11" {
        description "Corrected attribute details for multi-level-ecmp";
        reference " 0.29.6.";
    }

    revision "2024-12-05" {
        description "Added new attribute multi-level-ecmp under load-balance config";
        reference " 0.29.5.";
    }

    revision "2024-11-19" {
        description "Added UFT support for TH-5";
        reference " 0.29.4.";
    }

    revision "2024-11-14" {
        description "updated the xml changes to create the group first, which has more qualifier";
        reference " 0.29.3.";
    }

    revision "2024-11-06" {
        description "Removed support for hardware-profile port mode for TH5";
        reference " 0.29.2.";
    }

    revision "2024-11-05" {
        description "Added new ingress-ipv4-l2,ingress-ipv6-l2 filter for L2 interface";
        reference " 0.29.1.";
    }

    revision "2024-10-31" {
        description "Added to port-channel load-balance the option to set RTAG7 by default on all aggregator interfaces";
        reference " 0.29.0.";
    }

    revision "2024-10-08" {
        description "added symmetric type for load balance l2 and ipv4 ";
        reference " 0.28.9.";
    }

    revision "2024-09-25" {
        description "Imported ipi-platform-profile-types";
        reference " 0.28.7.";
    }

    revision "2024-09-10" {
        description "Added if-feature check for hardware profile aclif";
        reference " 0.28.4.";
    }

    revision "2024-09-05" {
        description "Added new attribute for hardware-profile port mode for UFIS9321-64E mode";
        reference " 0.28.3.";
    }

    revision "2024-09-03" {
        description "Added new egress-l2-mlag filter for mlag active-active interface";
        reference " 0.28.6.";
    }

    revision "2024-08-29" {
        description "Removed input parameters for advanced parser cli";
        reference " 0.28.5.";
    }

    revision "2024-08-28" {
        description "Added new attribute for hardware-profile port mode for AS9817-64D mode";
        reference " 0.28.2.";
    }

    revision "2024-08-21" {
        description "Enable support for ingress-ipv6-ext-subif in DNX";
        reference " 0.28.1.";
    }

    revision "2024-07-31" {
        description "Added support for load-balance flb CLI";
        reference " 0.28.0.";
    }

    revision "2024-07-19" {
        description "Fix storm-control and hardware-profile filter dependency in Q2 boards";
        reference " 0.27.6.";
    }

    revision "2024-07-15" {
        description "Corrected default values of hardware profile port-config";
        reference " 0.27.5.";
    }

    revision "2024-06-19" {
        description "Added platform Clis checks for switchport protected CLI";
        reference " 0.27.4.";
    }

    revision "2024-06-17" {
        description "Added new attribute for hardware-profile port mode for AS9947-36XKB mode";
        reference " 0.27.3.";
    }

    revision "2024-06-03" {
        description "Added small field groups at last in hardware-profile-filters-config";
        reference " 0.27.2.";
    }

    revision "2024-04-16" {
        description "Moved evpn-mpls-multi-homing profile to new grouping to add the dependency on other profiles";
        reference " 0.27.1.";
    }

    revision "2024-04-15" {
        description "Added TCAM utilization recovery logs";
        reference " 0.26.3.";
    }

    revision "2024-03-20" {
        description "Reduced route-mode support for TD4 ";
        reference " 0.26.2.";
    }

    revision "2024-02-27" {
        description "Added cpu-queue and copp support for Marvell";
        reference " 0.26.1.";
    }

    revision "2024-02-22" {
        description "Removed the cli micro-bfd profile ";
        reference " 0.26.0.";
    }

    revision "2024-02-20" {
        description "Added UFT support for TH-4";
        reference " 0.25.0.";
    }

    revision "2024-02-09" {
        description "Added lpm-128-bit support for TD-4";
        reference " 0.25.0.";
    }

    revision "2024-02-01" {
        description "Added error-message tag for attributes ingres-ipv4 ingres-ipv4-ext ingres-ipv4-subif";
        reference " 0.24.0.";
    }

    revision "2024-01-22" {
        description "Removed DNX check for hardware-profile seamless-bfd (enable|disable)";
        reference " 0.23.5.";
    }

    revision "2023-12-15" {
        description "Added protcol and ipv6 option under load-balance for Marvell";
        reference " 0.23.4.";
    }

    revision "2023-11-27" {
        description "Added support for hardware-profile port mode for S9600-28DX ";
        reference " 0.23.3.";
    }

    revision "2023-11-13" {
        description "Added support for hardware-profile port mode for S9500-30XS ";
        reference " 0.23.2.";
    }

    revision "2023-11-08" {
        description "Added support for hardware-profile port mode for AS7316-26xb mode";
        reference " 0.23.1.";
    }

    revision "2023-10-02" {
        description "Add load-balance command for Marvell";
        reference " 0.23.0.";
    }

    revision "2023-09-21" {
        description "Enable support for ingress-ipv6-extended and ingress-ipv6-extended-vlan in DNX";
        reference " 0.22.10.";
    }

    revision "2023-09-19" {
        description "Implementation of CLI hardware filter ingress-l2-subif and inghress-ipv4-subif";
        reference " 0.22.9.";
    }

    revision "2023-08-23" {
        description "Implementation of CLI hardware profile aclif (failover|no-failover)";
        reference " 0.22.8.";
    }

    revision "2023-08-17" {
        description "Added a separate command to enable/disable the twamp-ipv6 mpls group";
        reference " 0.22.7.";
    }

    revision "2023-08-07" {
        description "Adding profile ingress-mirror";
        reference " 0.22.6.";
    }

    revision "2023-08-01" {
        description "Adding trident chipset for lpm-128bit-profile";
        reference " 0.22.5.";
    }

    revision "2023-07-30" {
        description "support bgp-flowspec-mode attribute";
        reference " 0.22.5.";
    }

    revision "2023-07-21" {
        description "cfm disable for q2 ipbase";
        reference " 0.22.4.";
    }

    revision "2023-07-12" {
        description "Added ipv6-ipsg as an option to hardware-profile filter";
        reference " 0.22.3.";
    }

    revision "2023-06-27" {
        description "Added tomahawk3 forward profiles";
        reference " 0.22.2.";
    }

    revision "2023-06-20" {
        description "Added support for short packet handling";
        reference " 0.22.1.";
    }

    revision "2023-06-16" {
        description "Removed port mode support on AS9716-32D XGS TOMAHAWK3 ";
        reference " 0.22.0.";
    }

    revision "2023-06-08" {
        description "Added CML_FORCE_RELOAD_FLUSH_DB flag for port-mode attributes";
        reference " 0.15.1.";
    }

    revision "2023-05-31" {
        description "Added support for dune port mode for 5916-54x_54xm_5xks";
        reference " 0.15.0.";
    }

    revision "2023-05-19" {
        description "Added support for dune port mode and port-group";
        reference " 0.14.9.";
    }

    revision "2023-05-08" {
        description "Added support for dune port mode";
        reference " 0.14.8.";
    }

    revision "2023-05-05" {
        description "port mode CLI added for as9716-32d";
        reference " 0.14.7.";
    }

    revision "2023-05-02" {
        description "port mode CLI added for UFIS9610-36D";
        reference " 0.14.6.";
    }

    revision "2023-04-26" {
        description "New CLI added for port isolation profile";
        reference " 0.14.5.";
    }

    revision "2023-03-28" {
        description "Adding cfm-continuity-check-message attr for DNX";
        reference " 0.14.4.";
    }

    revision "2023-03-17" {
        description "Enabling RTAG7 MPLS option in DC IP BASE";
        reference " 0.14.3.";
    }

    revision "2023-03-11" {
        description "Removed autoPopulate-custom for micro-bfd CLI";
        reference " 0.14.2.";
    }

    revision "2023-03-03" {
        description "filter group support for BGP Flowspec";
        reference " 0.14.1.";
    }

    revision "2023-03-02" {
        description "Removed micro-bfd profile cli for DNX boards";
        reference " 0.14.0.";
    }

    revision "2023-02-27" {
        description "Updated attribute egress-ipv6-dnx datatype from CML_ENABLE_DISABLE_T to CML_EMPTY_T";
        reference " 0.13.0.";
    }

    revision "2023-01-12" {
        description "Removed forwarding profile config support for HR4";
        reference " 0.12.9.";
    }

    revision "2022-12-21" {
        description "Install ingress-ipv6-ext and ingress-ipv6-ext-vlan only on supported Qumran boards";
        reference " 0.12.8.";
    }

    revision "2022-12-20" {
        description "Blocked forwarding-ipv4";
        reference " 0.12.7.";
    }

    revision "2022-12-14" {
        description "Added support for hardware-profile port mode for UFIS9600-56dx mode";
        reference " 0.12.6.";
    }

    revision "2022-12-09" {
        description "hardware-profile filter bfd-group CLI disabled for HURRICANE4";
        reference " 0.12.5.";
    }

    revision "2022-12-08" {
        description "Added HAVE_DNX for voq-scale Attribute";
        reference " 0.12.4.";
    }

    revision "2022-12-01" {
        description "implementation of hardware profile statistics egress-acl|voq-scale CLI";
        reference " 0.12.3.";
    }

    revision "2022-11-16" {
        description "Added profile filter ingress-ipv6-ext-vlan";
        reference " 0.12.2.";
    }

    revision "2022-11-02" {
        description "Added profile filter ingress-ipv6-ext";
        reference " 0.12.1.";
    }

    revision "2022-10-31" {
        description "Added attribute name cfm-slm in statistics in DNX";
        reference " 0.12.0.";
    }

    revision "2022-10-21" {
        description "changed attribute name for ingress-ipv4 in dune";
        reference " 0.11.7.";
    }

    revision "2022-10-17" {
        description "Added hardware-profile filter evpn-mpls-cw";
        reference " 0.11.6.";
    }

    revision "2022-10-12" {
        description "Added attribute for VOQ stats ";
        reference " 0.11.5.";
    }

    revision "2022-09-15" {
        description "Added implicit_delete on kaps profile ";
        reference " 0.11.4.";
    }

    revision "2022-07-22" {
        description "Added attribute ingress-ipv4-custom2";
        reference " 0.11.3.";
    }

    revision "2022-07-20" {
        description "Added implicit_delete on hardware load-balance";
        reference " 0.11.2.";
    }

    revision "2022-06-27" {
        description "Added new attribute for hardware-profile seamless-bfd (enable|disable)";
        reference " 0.11.1.";
    }

    revision "2022-06-01" {
        description "Updated the yang file with feature";
        reference " 0.11.0.";
    }

    revision "2022-05-02" {
        description "Added new attribute for hardware-profile port mode for UFIS9600-64X and UFIS9600-32X mode";
        reference " 0.10.3.";
    }

    revision "2022-01-07" {
        description "Changed cpu-q-default from attribute to rpc";
        reference " 0.10.3.";
    }

    revision "2022-01-06" {
        description "Added new Attribute hardware-profile port-config";
        reference " 0.10.2.";
    }

    revision "2021-12-27" {
        description "Added implicit-delete to load-balance config";
        reference " 0.10.1.";
    }

    revision "2021-11-22" {
        description "Updated with changes for DNX Broadcom platform hardware profiles";
        reference " 0.10.0.";
    }

    revision "2021-10-12" {
        description "Updated attribute ingress-ipv4 and egress-ipv6 datatype from CML_EMPTY_T to CML_ENABLE_DISABLE_T";
        reference " 0.9.0.";
    }

    revision "2021-09-06" {
        description "Updated description for attribute group-id,Removed enable-status attribute";
        reference " 0.8.0.";
    }

    revision "2021-07-29" {
        description "Added new filter type ipsg and ipsg-ipv6 group";
        reference " 0.7.0.";
    }

    revision "2021-07-28" {
        description "Added new attributes for forwarding profile, cpu-queue and load-balance";
        reference " 0.6.0.";
    }

    revision "2021-06-29" {
        description "Added attribute ingress-ipv6-acl";
        reference " 0.5.0.";
    }

    revision "2021-06-25" {
        description "Added new filter type dhcp-snoop and dhcp-snoop-ipv6 group";
        reference " 0.4.0.";
    }

    revision "2021-06-23" {
        description "Updated attribute ingress-bfd datatype from CML_EMPTY_T to CML_ENABLE_DISABLE_T";
        reference " 0.3.0.";
    }

    revision "2021-06-17" {
        description "Updated with changes for non-DNX Broadcom platform hardware profiles";
        reference " 0.2.0.";
    }

    revision "2021-04-27" {
        description "Added Get API support for TCAM Utilization filter group";
        reference " 0.2.0.";
    }

    revision "2021-03-29" {
        description "Initial Version";
        reference " 0.1.0.";
    }

    grouping hardware-profile-config {
        description
            "Grouping for hardware-profile config objects.";
        leaf flow-control  {
            if-feature feature-list:HAVE_BCM_UFT;
            if-feature feature-list:HAVE_DUNE;
            type  empty;
            description "Use this attribute to enable or disable hardware profile flowcontrol.";
        } // END of flow-control definition.

        leaf aclif  {
            if-feature feature-list:HAVE_DUNE;
            type  ipi-platform-profile-types:platform_aclif_type_t;
            description "Use this attribute to set or unset the hardware profile aclif";
        } // END of aclif definition.

        leaf seamless-bfd  {
            if-feature feature-list:HAVE_CUSTOM1_HW_BFD;
            if-feature feature-list:HAVE_SBFD;
            type  empty;
            description "Use this attribute to enable or disable hardware profile seamless-bfd.";
        } // END of seamless-bfd definition.

        leaf kbp-disable  {
            if-feature feature-list:HAVE_DNX;
            type  empty;
            description "Use this attribute to enable or disable kbp hardware profile.";
        } // END of kbp-disable definition.

        leaf ufis9600-64x-port-mode  {
            if-feature feature-list:HAVE_DUNE;
            type  ipi-platform-profile-types:platform_ufis9600_64x_port_mode_type_t;
            default "mode1";
            description "use this attribute to configure or unconfigure hardware profile port
                        modes";
        } // END of ufis9600-64x-port-mode definition.

        leaf as7315_27x-port-mode  {
            if-feature feature-list:HAVE_DUNE;
            type  ipi-platform-profile-types:platform_as7315_27x_port_mode_type_t;
            default "mode1";
            description "use this attribute to configure or unconfigure hardware profile port
                        modes";
        } // END of as7315_27x-port-mode definition.

        leaf as5916_as5912_54x-port-mode  {
            if-feature feature-list:HAVE_DUNE;
            type  ipi-platform-profile-types:platform_as5916_as5912_54x_port_mode_type_t;
            default "mode1";
            description "use this attribute to configure or unconfigure hardware profile port
                        modes";
        } // END of as5916_as5912_54x-port-mode definition.

        leaf as7316_26xb-port-mode  {
            if-feature feature-list:HAVE_DUNE;
            type  ipi-platform-profile-types:platform_as7316_26xb_port_mode_type_t;
            default "mode1";
            description "use this attribute to configure or unconfigure hardware profile port
                        modes";
        } // END of as7316_26xb-port-mode definition.

        leaf s9500_30xs-port-mode  {
            if-feature feature-list:HAVE_DUNE;
            type  ipi-platform-profile-types:platform_s9500_30xs_port_mode_type_t;
            default "mode1";
            description "use this attribute to configure or unconfigure hardware profile port
                        modes";
        } // END of s9500_30xs-port-mode definition.

        leaf ufis9600-32x-port-mode  {
            if-feature feature-list:HAVE_DUNE;
            type  ipi-platform-profile-types:platform_ufis9600_32x_port_mode_type_t;
            default "mode2";
            description "use this attribute to configure or unconfigure hardware profile port
                        modes";
        } // END of ufis9600-32x-port-mode definition.

        leaf ufis9600-56dx-port-mode  {
            if-feature feature-list:HAVE_DUNE;
            type  ipi-platform-profile-types:platform_ufis9600_56dx_port_mode_type_t;
            default "mode1";
            description "use this attribute to configure or unconfigure hardware profile port
                        modes";
        } // END of ufis9600-56dx-port-mode definition.

        leaf ufis9600-28dx-port-mode  {
            if-feature feature-list:HAVE_DUNE;
            type  ipi-platform-profile-types:platform_ufis9600_28dx_port_mode_type_t;
            default "mode1";
            description "use this attribute to configure or unconfigure hardware profile port
                        modes";
        } // END of ufis9600-28dx-port-mode definition.

        leaf ufis9610-36d-port-mode  {
            if-feature feature-list:HAVE_DUNE;
            type  ipi-platform-profile-types:platform_ufis9610_36d_port_mode_type_t;
            default "mode1";
            description "use this attribute to configure or unconfigure hardware profile port
                        modes";
        } // END of ufis9610-36d-port-mode definition.

        leaf ufis9610-46dx-port-mode  {
            if-feature feature-list:HAVE_DUNE;
            type  ipi-platform-profile-types:platform_ufis9610_46dx_port_mode_type_t;
            default "mode1";
            description "use this attribute to configure or unconfigure hardware profile port
                        modes";
        } // END of ufis9610-46dx-port-mode definition.

        leaf ufis9610-48dx-port-mode  {
            if-feature feature-list:HAVE_DUNE;
            type  ipi-platform-profile-types:platform_ufis9610_48dx_port_mode_type_t;
            default "mode1";
            description "use this attribute to configure or unconfigure hardware profile port
                        modes";
        } // END of ufis9610-48dx-port-mode definition.

        leaf as9947_36xkb-port-mode  {
            if-feature feature-list:HAVE_DNX;
            type  ipi-platform-profile-types:platform_as9947_36kbx_port_mode_type_t;
            default "mode1";
            description "use this attribute to configure or unconfigure hardware profile port
                        modes";
        } // END of as9947_36xkb-port-mode definition.

        leaf custom-service-queue-profile  {
            if-feature feature-list:HAVE_DUNE;
            type  ipi-platform-profile-types:platform_qos_queue_profile_type_t;
            default "profile1";
            description "Use this attribute to configure or unconfigure hardware profile
                        service-queue profile support.";
        } // END of custom-service-queue-profile definition.

        leaf bgp-flowspec-mode  {
            // when " !ipi-platform-profile:profiles/hardware-profile/filters/config/ipv4-bgp-flowspec ";
            if-feature feature-list:HAVE_DUNE;
            if-feature feature-list:HAVE_BGP_FLOWSPEC;
            type  ipi-platform-profile-types:platform_bgp_flowspec_mode_t;
            description "use this attribute to set bgp-flowspce-mode";
        } // END of bgp-flowspec-mode definition.

        leaf eedb  {
            if-feature feature-list:HAVE_DNX;
            type  ipi-platform-profile-types:platform_eedb_mode_t;
            default "mode1";
            description "Use this attribute to set hardware-profile eedb";
        } // END of eedb definition.

    } // END of hardware-profile-config definition.
    grouping hardware-profile-filters-config {
        description
            "Grouping for hardware-profile filter config objects.";
        leaf ingress-ip-outer  {
            if-feature feature-list:HAVE_ACL;
            if-feature feature-list:HAVE_CUSTOM3_ACL;
            type  empty;
            description "Use this attribute to enable or disable the outer ip header filter";
        } // END of ingress-ip-outer definition.

        leaf egress-ipv6  {
            if-feature feature-list:HAVE_ACL;
            if-feature feature-list:NOT_HAVE_DUNE;
            type  cml-data-types:cml_enable_disable_t;
            description "Use this attribute to enable or disable Egress IPv6 filter groups.
                        Disabling filter groups increases the configurable filter entries.";
        } // END of egress-ipv6 definition.

        leaf egress-dst-ipv6  {
            if-feature feature-list:HAVE_ACL;
            if-feature feature-list:HAVE_CUSTOM3_ACL;
            type  empty;
            description "Use this attribute to enable or disable Egress Dst IPv6 filter groups.
                        Disabling filter groups increases the configurable filter entries.";
        } // END of egress-dst-ipv6 definition.

        leaf egress-src-ipv6  {
            if-feature feature-list:HAVE_ACL;
            if-feature feature-list:HAVE_CUSTOM3_ACL;
            type  empty;
            description "Use this attribute to enable or disable Egress Src IPv6 filter groups.
                        Disabling filter groups increases the configurable filter entries.";
        } // END of egress-src-ipv6 definition.

        leaf egress-ipv6-dnx  {
            if-feature feature-list:HAVE_ACL;
            if-feature feature-list:HAVE_DNX;
            type  empty;
            description "Use this command to enable or disable egress IPv6 filter groups.
                        Disabling filter groups increases the configurable filter entries.";
        } // END of egress-ipv6-dnx definition.

        leaf ingress-ipv6  {
            if-feature feature-list:HAVE_ACL;
            if-feature feature-list:HAVE_DUNE;
            type  empty;
            description "Use this attribute to enable or disable Ingress IPv6 filter groups.
                        Disabling filter groups increases the configurable filter entries.";
        } // END of ingress-ipv6 definition.

        leaf twamp-ipv4  {
            if-feature feature-list:HAVE_TWAMP_HW_OFFLOAD;
            if-feature feature-list:HAVE_TWAMP;
            if-feature feature-list:HAVE_DUNE;
            if-feature feature-list:NOT_HAVE_DNX;
            type  empty;
            description "Use this attribute to enable or disable TWAMP IPv4 Forwarding filter
                        groups. Disabling filter groups increases the configurable filter
                        entries.";
        } // END of twamp-ipv4 definition.

        leaf qos-policer  {
            // when " !ipi-platform-profile:profiles/hardware-profile/filters/config/qos + !ipi-platform-profile:profiles/hardware-profile/filters/config/qos-extended ";
            if-feature feature-list:HAVE_ACL;
            if-feature feature-list:HAVE_DUNE;
            type  empty;
            description "Use this attribute to enable or disable QoS policer filter groups.
                        Disabling filter groups increases the configurable filter entries.";
        } // END of qos-policer definition.

        leaf qos-subif-policer  {
            // when " !ipi-platform-profile:profiles/hardware-profile/filters/config/qos + !ipi-platform-profile:profiles/hardware-profile/filters/config/qos-extended + !ipi-platform-profile:profiles/hardware-profile/filters/config/qos-policer ";
            if-feature feature-list:HAVE_ACL;
            if-feature feature-list:HAVE_DUNE;
            if-feature feature-list:NOT_HAVE_DNX;
            type  empty;
            description "Use this attribute to enable or disable QoS subif policer filter
                        groups. Disabling filter groups increases the configurable filter
                        entries.";
        } // END of qos-subif-policer definition.

        leaf qos-ipv6  {
            if-feature feature-list:HAVE_ACL;
            if-feature feature-list:HAVE_DUNE;
            type  empty;
            description "Use this attribute to enable or disable QoS filter group for IPv6
                        traffic. Disabling filter groups increases the configurable filter
                        entries.";
        } // END of qos-ipv6 definition.

        leaf ingress-ipv6-acl  {
            if-feature feature-list:HAVE_ACL;
            if-feature feature-list:NOT_HAVE_DUNE;
            type  cml-data-types:cml_enable_disable_t;
            description "Use this attribute to enable or disable Ingress IPv6 filter groups.
                        Disabling filter groups increases the configurable filter entries.";
        } // END of ingress-ipv6-acl definition.

        leaf ipv4-bgp-flowspec  {
            if-feature feature-list:HAVE_ACL;
            if-feature feature-list:HAVE_DUNE;
            if-feature feature-list:HAVE_BGP_FLOWSPEC;
            type  empty;
            description "Use this attribute to enable or disable Ingress IPv4 BGP FLOWSPEC
                        filter groups. Disabling filter groups increases the configurable
                        filter entries.";
        } // END of ipv4-bgp-flowspec definition.

        leaf qos-extended  {
            // when " !ipi-platform-profile:profiles/hardware-profile/filters/config/qos + !ipi-platform-profile:profiles/hardware-profile/filters/config/qos-policer ";
            if-feature feature-list:HAVE_ACL;
            if-feature feature-list:HAVE_DUNE;
            type  empty;
            description "Use this attribute to enable or disable QoS extended filter groups.
                        Disabling filter groups increases the configurable filter entries.";
        } // END of qos-extended definition.

        leaf qos-subif-extended  {
            // when " !ipi-platform-profile:profiles/hardware-profile/filters/config/qos + !ipi-platform-profile:profiles/hardware-profile/filters/config/qos-policer + !ipi-platform-profile:profiles/hardware-profile/filters/config/qos-extended ";
            if-feature feature-list:HAVE_ACL;
            if-feature feature-list:HAVE_DUNE;
            if-feature feature-list:NOT_HAVE_DNX;
            type  empty;
            description "Use this attribute to enable or disable QoS extended filter groups.
                        Disabling filter groups increases the configurable filter entries.";
        } // END of qos-subif-extended definition.

        leaf ingress-ipv4-extended  {
            if-feature feature-list:HAVE_ACL;
            if-feature feature-list:HAVE_DUNE;
            type  empty;
            description "Use this attribute to enable or disable Ingress IPv4 extended filter
                        groups. Disabling filter groups increases the configurable filter
                        entries.";
        } // END of ingress-ipv4-extended definition.

        leaf ingress-ipv4-subif-extended  {
            if-feature feature-list:HAVE_ACL;
            if-feature feature-list:HAVE_DUNE;
            if-feature feature-list:NOT_HAVE_DNX;
            type  empty;
            description "Use this attribute to enable or disable Ingress IPv4 subif extended
                        filter groups. Disabling filter groups increases the configurable
                        filter entries.";
        } // END of ingress-ipv4-subif-extended definition.

        leaf ingress-ipv6-qos  {
            if-feature feature-list:HAVE_ACL;
            if-feature feature-list:HAVE_DUNE;
            type  empty;
            description "Use this attribute to enable or disable Ingress IPv6 QoS filter
                        groups. Disabling filter groups increases the configurable filter
                        entries.";
        } // END of ingress-ipv6-qos definition.

        leaf ingress-ipv4-qos  {
            if-feature feature-list:HAVE_ACL;
            if-feature feature-list:HAVE_DUNE;
            type  empty;
            description "Use this attribute to enable or disable Ingress IPv4 QoS filter
                        groups. Disabling filter groups increases the configurable filter
                        entries.";
        } // END of ingress-ipv4-qos definition.

        leaf ingress-ipv6-qos-copp  {
            if-feature feature-list:HAVE_ACL;
            if-feature feature-list:HAVE_DNX;
            if-feature feature-list:HAVE_COPP_FILTER;
            if-feature feature-list:HAVE_IPV6;
            type  empty;
            description "Use this attribute to enable or disable Ingress IPv6 QoS and CoPP
                        filter groups. Disabling filter groups increases the configurable
                        filter entries.";
        } // END of ingress-ipv6-qos-copp definition.

        leaf ingress-ipv4-qos-copp  {
            if-feature feature-list:HAVE_ACL;
            if-feature feature-list:HAVE_DNX;
            if-feature feature-list:HAVE_COPP_FILTER;
            type  empty;
            description "Use this attribute to enable or disable Ingress IPv4 QoS and CoPP
                        filter groups. Disabling filter groups increases the configurable
                        filter entries.";
        } // END of ingress-ipv4-qos-copp definition.

        leaf ingress-layer2-extended  {
            // when " !ipi-platform-profile:profiles/hardware-profile/filters/config/ingress-layer2 ";
            if-feature feature-list:HAVE_ACL;
            if-feature feature-list:HAVE_DUNE;
            type  empty;
            description "Use this attribute to enable or disable Ingress L2 extended filter
                        groups. Disabling filter groups increases the configurable filter
                        entries.";
        } // END of ingress-layer2-extended definition.

        leaf ingress-ipv6-extended  {
            if-feature feature-list:HAVE_ACL;
            if-feature feature-list:HAVE_DUNE;
            type  empty;
            description "Use this attribute to enable or disable Ingress IPv6 extended filter
                        groups. Disabling filter groups increases the configurable filter
                        entries.";
        } // END of ingress-ipv6-extended definition.

        leaf ingress-ipv6-extended-vlan  {
            if-feature feature-list:HAVE_ACL;
            if-feature feature-list:HAVE_DUNE;
            type  empty;
            description "Use this attribute to enable or disable Ingress IPv6 extended vlan
                        filter groups. Disabling filter groups increases the configurable
                        filter entries.";
        } // END of ingress-ipv6-extended-vlan definition.

        leaf ingress-ipv6-extended-subif  {
            if-feature feature-list:HAVE_ACL;
            if-feature feature-list:HAVE_DNX;
            type  empty;
            description "Use this attribute to enable or disable Ingress IPv6 extended subif
                        filter groups. Disabling filter groups increases the configurable
                        filter entries.";
        } // END of ingress-ipv6-extended-subif definition.

        leaf ingress-ipv4-custom0  {
            if-feature feature-list:HAVE_ACL;
            if-feature feature-list:NOT_HAVE_DUNE;
            type  cml-data-types:cml_enable_disable_t;
            description "Use this attribute to enable or disable Ingress IPv4 filter groups.
                        Disabling filter groups increases the configurable filter entries.";
        } // END of ingress-ipv4-custom0 definition.

        leaf ingress-ipv4-subif  {
            if-feature feature-list:HAVE_ACL;
            if-feature feature-list:HAVE_DUNE;
            type  empty;
            description "Use this attribute to enable or disable Ingress IPv4 extended filter
                        groups. Disabling filter groups increases the configurable filter
                        entries.";
        } // END of ingress-ipv4-subif definition.

        leaf ingress-arp  {
            if-feature feature-list:HAVE_ACL;
            type  empty;
            description "Use this attribute to enable or disable Ingress ARP filter groups.";
        } // END of ingress-arp definition.

        leaf egress-qos-policer  {
            if-feature feature-list:HAVE_ACL;
            if-feature feature-list:HAVE_DUNE;
            if-feature feature-list:HAVE_DNX;
            type  empty;
            description "Use this attribute to enable or disable Egress QoS policer filter
                        groups. Disabling filter groups increases the configurable filter
                        entries.";
        } // END of egress-qos-policer definition.

        leaf egress-qos-policer-ext  {
            if-feature feature-list:HAVE_ACL;
            if-feature feature-list:HAVE_CUSTOM3_ACL;
            type  empty;
            description "Use this attribute to enable or disable Egress QoS policer filter
                        groups. Disabling filter groups increases the configurable filter
                        entries.";
        } // END of egress-qos-policer-ext definition.

        leaf egress-ipv4  {
            if-feature feature-list:HAVE_ACL;
            if-feature feature-list:HAVE_DUNE;
            if-feature feature-list:NOT_HAVE_CUSTOM3_ACL;
            type  empty;
            description "Use this attribute to enable or disable Egress IPv4 filter groups.
                        Disabling filter groups increases the configurable filter entries.";
        } // END of egress-ipv4 definition.

        leaf egress-ipv4-dnx  {
            if-feature feature-list:HAVE_ACL;
            if-feature feature-list:HAVE_DUNE;
            if-feature feature-list:HAVE_CUSTOM3_ACL;
            type  empty;
            description "Use this attribute to enable or disable Egress IPv4 filter groups.
                        Disabling filter groups increases the configurable filter entries.";
        } // END of egress-ipv4-dnx definition.

        leaf egress-l2-mlag  {
            if-feature feature-list:HAVE_ACL;
            if-feature feature-list:HAVE_DUNE;
            if-feature feature-list:HAVE_CUSTOM3_ACL;
            type  empty;
            description "Use this attribute to enable or disable Egress l2 filter groups.
                        Disabling filter groups increases the configurable filter entries.";
        } // END of egress-l2-mlag definition.

        leaf egress-ipv4-ext  {
            if-feature feature-list:HAVE_ACL;
            if-feature feature-list:HAVE_DNX;
            type  empty;
            description "Use this attribute to enable or disable Egress IPv4 ext filter groups.
                        Disabling filter groups increases the configurable filter entries.";
        } // END of egress-ipv4-ext definition.

        leaf egress-layer2  {
            if-feature feature-list:HAVE_ACL;
            if-feature feature-list:HAVE_DUNE;
            if-feature feature-list:NOT_HAVE_CUSTOM3_ACL;
            type  empty;
            description "Use this attribute to enable or disable Egress L2 filter groups.
                        Disabling filter groups increases the configurable filter entries.";
        } // END of egress-layer2 definition.

        leaf egress-layer2-dnx  {
            if-feature feature-list:HAVE_ACL;
            if-feature feature-list:HAVE_CUSTOM3_ACL;
            type  empty;
            description "Use this attribute to enable or disable Egress L2 filter groups.
                        Disabling filter groups increases the configurable filter entries.";
        } // END of egress-layer2-dnx definition.

        leaf egress-layer2-ext  {
            if-feature feature-list:HAVE_ACL;
            if-feature feature-list:HAVE_DNX;
            type  empty;
            description "Use this attribute to enable or disable Egress L2 ext filter groups.
                        Disabling filter groups increases the configurable filter entries.";
        } // END of egress-layer2-ext definition.

        leaf ingress-layer2-subif  {
            // when " !ipi-platform-profile:profiles/hardware-profile/filters/config/ingress-layer2 ";
            if-feature feature-list:HAVE_ACL;
            if-feature feature-list:HAVE_DUNE;
            type  empty;
            description "Use this attribute to enable or disable Ingress L2 extended filter
                        groups. Disabling filter groups increases the configurable filter
                        entries.";
        } // END of ingress-layer2-subif definition.

        leaf cfm-domain-name-string  {
            if-feature feature-list:HAVE_CFM;
            if-feature feature-list:HAVE_DUNE;
            if-feature feature-list:NOT_HAVE_DNX;
            type  empty;
            description "Use this attribute to enable or disable CFM domain name filter groups.
                        Disabling filter groups increases the configurable filter entries.";
        } // END of cfm-domain-name-string definition.

        leaf twamp-ipv4-dnx  {
            if-feature feature-list:HAVE_TWAMP_HW_OFFLOAD;
            if-feature feature-list:HAVE_TWAMP;
            if-feature feature-list:HAVE_DUNE;
            if-feature feature-list:HAVE_DNX;
            type  empty;
            description "Use this attribute to enable or disable TWAMP IPv4 Forwarding filter
                        groups. Disabling filter groups increases the configurable filter
                        entries.";
        } // END of twamp-ipv4-dnx definition.

        leaf twamp-ipv6  {
            if-feature feature-list:HAVE_TWAMP_HW_OFFLOAD;
            if-feature feature-list:HAVE_TWAMP;
            if-feature feature-list:HAVE_DUNE;
            type  empty;
            description "Use this attribute to enable or disable TWAMP IPv6 Forwarding filter
                        groups. Disabling filter groups increases the configurable filter
                        entries.";
        } // END of twamp-ipv6 definition.

        leaf twamp-ipv6-mpls  {
            if-feature feature-list:HAVE_TWAMP_HW_OFFLOAD;
            if-feature feature-list:HAVE_TWAMP;
            if-feature feature-list:HAVE_DUNE;
            if-feature feature-list:NOT_HAVE_DNX;
            type  empty;
            description "Use this attribute to enable or disable TWAMP IPv6 for MPLS Forwarding
                        filter groups. This group should be enabled in addition to twamp-ipv6.
                        Disabling filter groups increases the configurable filter entries.";
        } // END of twamp-ipv6-mpls definition.

        leaf vxlan-arp-nd  {
            if-feature feature-list:HAVE_VXLAN;
            if-feature feature-list:HAVE_DUNE;
            type  empty;
            description "Use this attribute to enable or disable VxLAN Forwarding filter
                        groups. Disabling filter groups increases the configurable filter
                        entries.";
        } // END of vxlan-arp-nd definition.

        leaf vxlan-multi-homing  {
            if-feature feature-list:HAVE_VXLAN;
            if-feature feature-list:HAVE_DUNE;
            type  empty;
            description "Use this attribute to enable or disable VxLAN Multi Homing Forwarding
                        filter groups. Disabling filter groups increases the configurable
                        filter entries.";
        } // END of vxlan-multi-homing definition.

        leaf vxlan-short-pkt  {
            if-feature feature-list:HAVE_VXLAN;
            if-feature feature-list:HAVE_DUNE;
            if-feature feature-list:HAVE_DNX;
            type  empty;
            description "Use this attribute to enable or disable VxLAN Short Packet Forwarding
                        filter groups. Disabling filter groups increases the configurable
                        filter entries.";
        } // END of vxlan-short-pkt definition.

        leaf evpn-mpls-control-word  {
            if-feature feature-list:HAVE_NVO;
            if-feature feature-list:HAVE_MPLS;
            if-feature feature-list:HAVE_DUNE;
            if-feature feature-list:NOT_HAVE_DNX;
            type  empty;
            description "Use this attribute to enable or disable EVPN-MPLS control-word option";
        } // END of evpn-mpls-control-word definition.

        leaf ingress-bfd  {
            if-feature feature-list:HAVE_BFD_HW_OFFLOAD;
            if-feature feature-list:NOT_HAVE_CUSTOM1_HW_BFD;
            type  cml-data-types:cml_enable_disable_t;
            description "Use this attribute to enable or disable Ingress BFD filter groups.
                        Disabling filter groups increases the configurable filter entries.";
        } // END of ingress-bfd definition.

        leaf dhcp-snoop  {
            if-feature feature-list:HAVE_DHCP_SNOOP;
            if-feature feature-list:HAVE_DUNE;
            type  empty;
            description "Use this attribute to enable or disable Dhcp snooping filter groups.
                        Disabling filter groups increases the configurable filter entries.";
        } // END of dhcp-snoop definition.

        leaf dhcp-snoop-ipv6  {
            if-feature feature-list:HAVE_DHCP_SNOOP;
            if-feature feature-list:HAVE_DUNE;
            type  empty;
            description "Use this attribute to enable or disable Dhcp snooping ipv6 filter
                        groups. Disabling filter groups increases the configurable filter
                        entries.";
        } // END of dhcp-snoop-ipv6 definition.

        leaf ipsg  {
            if-feature feature-list:HAVE_DHCP_SNOOP;
            if-feature feature-list:HAVE_DUNE;
            type  empty;
            description "Use this attribute to enable or disable IP Source Guard(IPSG) filter
                        groups. Disabling filter groups increases the configurable filter
                        entries.";
        } // END of ipsg definition.

        leaf ipsg-ipv6  {
            if-feature feature-list:HAVE_DHCP_SNOOP;
            if-feature feature-list:HAVE_BROADCOM;
            type  empty;
            description "Use this attribute to enable or disable IP Source Guard(IPSG) ipv6
                        filter groups. Disabling filter groups increases the configurable
                        filter entries.";
        } // END of ipsg-ipv6 definition.

        leaf isolation  {
            // when " ipi-platform-profile-extended:platform/config/soc == '10' ";
            if-feature feature-list:NOT_HAVE_DUNE;
            type  cml-data-types:cml_enable_disable_t;
            description "Use this attribute to enable or disable port isolation. Disabling
                        filter groups increases the configurable filter entries.";
        } // END of isolation definition.

        leaf ingress-ipv4  {
            if-feature feature-list:HAVE_ACL;
            if-feature feature-list:HAVE_DUNE;
            type  empty;
            description "Use this attribute to enable or disable Ingress IPv4 filter groups.
                        Disabling filter groups increases the configurable filter entries.";
        } // END of ingress-ipv4 definition.

        leaf ingress-layer2  {
            // when " !ipi-platform-profile:profiles/hardware-profile/filters/config/ingress-layer2-extended ";
            if-feature feature-list:HAVE_ACL;
            if-feature feature-list:HAVE_DUNE;
            type  empty;
            description "Use this attribute to enable or disable Ingress L2 filter groups.
                        Disabling filter groups increases the configurable filter entries.";
        } // END of ingress-layer2 definition.

        leaf qos  {
            // when " !ipi-platform-profile:profiles/hardware-profile/filters/config/qos-extended + !ipi-platform-profile:profiles/hardware-profile/filters/config/qos-policer ";
            if-feature feature-list:HAVE_ACL;
            if-feature feature-list:HAVE_DUNE;
            type  empty;
            description "Use this attribute to enable or disable QoS filter groups. Disabling
                        filter groups increases the configurable filter entries.";
        } // END of qos definition.

        leaf ingress-mirror  {
            if-feature feature-list:HAVE_ADVANCE_MIRROR;
            if-feature feature-list:HAVE_BROADCOM;
            if-feature feature-list:NOT_HAVE_DUNE;
            type  empty;
            description "Use this attribute to enable or disable Ingress Mirror filter groups.
                        Disabling filter groups increases the configurable filter entries.";
        } // END of ingress-mirror definition.

    } // END of hardware-profile-filters-config definition.
    grouping hardware-profile-filter-evpn-mpls-multi-homing {
        description
            "Grouping for hardware profile filter evpn mpls multi-homing.";
        leaf evpn-mpls-multi-homing  {
            if-feature feature-list:HAVE_NVO;
            if-feature feature-list:HAVE_MPLS;
            if-feature feature-list:HAVE_DUNE;
            type  empty;
            description "Use this attribute to enable or disable EVPN-MPLS Multi Homing
                        Forwarding filter groups. Disabling filter groups increases the
                        configurable filter entries.";
        } // END of evpn-mpls-multi-homing definition.

    } // END of hardware-profile-filter-evpn-mpls-multi-homing definition.
    grouping platform-advanced-parser-soc-enable {
        description
            "Grouping for hw SOC property config objects.";
        leaf parser-enable  {
            if-feature feature-list:HAVE_MPLS;
            if-feature feature-list:HAVE_DUNE;
            if-feature feature-list:NOT_HAVE_DNX;
            type  empty;
            description "This Object is set parser enable";
        } // END of parser-enable definition.

        leaf parser-nibble-map  {
            if-feature feature-list:HAVE_MPLS;
            if-feature feature-list:HAVE_DUNE;
            if-feature feature-list:NOT_HAVE_DNX;
            type  ipi-platform-profile-types:platform_parser_type_t;
            description "This Object is to set speculation option";
        } // END of parser-nibble-map definition.

    } // END of platform-advanced-parser-soc-enable definition.
    grouping hardware-profiles-statistics-config {
        description
            "Grouping for hardware-profile statistics config objects.";
        leaf voq-scale  {
            if-feature feature-list:HAVE_DNX;
            type  ipi-platform-profile-types:platform_voq_scale_type_t;
            default "full";
            description "Use this attribute to set voq scale for the hardware profile
                        statistics";
        } // END of voq-scale definition.

        leaf virtual-output-queue-full-color-forward-drop  {
            if-feature feature-list:HAVE_DNX;
            type  ipi-platform-profile-types:cml_voq_full_color_fwd_drop_t;
            default "voq-full-color";
            description "Use this attribute to enable  Virtual Output Queue Forward Drop or
                        Virtual Output Queue Full Color filter groups. Disabling filter groups
                        increases the configurable filter entries.";
        } // END of virtual-output-queue-full-color-forward-drop definition.

        leaf ingress-acl  {
            if-feature feature-list:HAVE_DUNE;
            if-feature feature-list:NOT_HAVE_DNX;
            type  ipi-platform-profile-types:platform_ing_acl_stat;
            description "Use this attribute to enable or disable Ingress ACL QoS and PBR filter
                        groups. Disabling filter groups increases the configurable filter
                        entries.";
        } // END of ingress-acl definition.

        leaf egress-acl  {
            if-feature feature-list:HAVE_DUNE;
            if-feature feature-list:NOT_HAVE_DNX;
            type  empty;
            description "Use this attribute to enable or disable Egress ACL filter groups.
                        Disabling filter groups increases the configurable filter entries.";
        } // END of egress-acl definition.

        leaf egress-policer  {
            if-feature feature-list:HAVE_DNX;
            type  empty;
            description "Use this attribute to enable or disable Egress policer filter groups.
                        Disabling filter groups increases the configurable filter entries.";
        } // END of egress-policer definition.

        leaf ingress-qos  {
            if-feature feature-list:HAVE_DUNE;
            if-feature feature-list:NOT_HAVE_DNX;
            type  empty;
            description "Use this attribute to enable or disable explicitly for QoS filter
                        groups. Disabling filter groups increases the configurable filter
                        entries.";
        } // END of ingress-qos definition.

        leaf attachment-circuit-logical-if  {
            if-feature feature-list:HAVE_DUNE;
            if-feature feature-list:NOT_HAVE_DNX;
            type  empty;
            description "Use this attribute to enable or disable attachment circuits logical
                        filter groups. Disabling filter groups increases the configurable
                        filter entries.";
        } // END of attachment-circuit-logical-if definition.

        leaf tunnel-logical-if  {
            if-feature feature-list:HAVE_DUNE;
            if-feature feature-list:NOT_HAVE_DNX;
            type  empty;
            description "Use this attribute to enable or disable tunnel logical filter groups.
                        Disabling filter groups increases the configurable filter entries.";
        } // END of tunnel-logical-if definition.

        leaf evpn-mpls-stats  {
            if-feature feature-list:HAVE_NVO;
            if-feature feature-list:HAVE_MPLS;
            if-feature feature-list:HAVE_DUNE;
            if-feature feature-list:NOT_HAVE_DNX;
            type  empty;
            description "Use this attribute to enable or disable hardware statistics for
                        evpn-mpls.";
        } // END of evpn-mpls-stats definition.

        leaf mpls-pseudowire  {
            if-feature feature-list:HAVE_DUNE;
            if-feature feature-list:HAVE_MPLS_STATS;
            if-feature feature-list:NOT_HAVE_DNX;
            type  empty;
            description "Use this attribute to enable or disable MPLS Pseudowire filter groups.
                        Disabling filter groups increases the configurable filter entries.";
        } // END of mpls-pseudowire definition.

        leaf cfm-frame-loss-measurements  {
            if-feature feature-list:HAVE_DUNE;
            if-feature feature-list:HAVE_CFM;
            type  empty;
            description "Use this attribute to enable or disable CFM Loss Measurements filter
                        groups. Disabling filter groups increases the configurable filter
                        entries.";
        } // END of cfm-frame-loss-measurements definition.

        leaf cfm-synthetic-loss-measurements  {
            if-feature feature-list:HAVE_DNX;
            if-feature feature-list:HAVE_CFM;
            type  empty;
            description "Use this attribute to enable or disable CFM Loss Measurements filter
                        groups. Disabling filter groups increases the configurable filter
                        entries.";
        } // END of cfm-synthetic-loss-measurements definition.

        leaf cfm-continuity-check-messages  {
            if-feature feature-list:HAVE_DUNE;
            if-feature feature-list:CCM_HW_OFFLOAD;
            if-feature feature-list:NOT_HAVE_DNX;
            type  empty;
            description "Use this attribute to enable or disable CFM Continuity Check Messages
                        filter groups. Disabling filter groups increases the configurable
                        filter entries.";
        } // END of cfm-continuity-check-messages definition.

        leaf cfm-continuity-check-message  {
            if-feature feature-list:HAVE_DNX;
            if-feature feature-list:CCM_HW_OFFLOAD;
            type  cml-data-types:cml_enable_disable_t;
            description "Use this attribute to enable or disable CFM Continuity Check Messages
                        filter groups. Disabling filter groups increases the configurable
                        filter entries.";
        } // END of cfm-continuity-check-message definition.

        leaf virtual-output-queue-full-color  {
            // when " !ipi-platform-profile:profiles/hardware-profile/statistics/config/virtual-output-queue-forward-drop ";
            if-feature feature-list:HAVE_DUNE;
            if-feature feature-list:NOT_HAVE_DNX;
            type  empty;
            description "Use this attribute to enable or disable Virtual Output Queue Full
                        Color filter groups. Disabling filter groups increases the
                        configurable filter entries.";
        } // END of virtual-output-queue-full-color definition.

        leaf virtual-output-queue-forward-drop  {
            // when " !ipi-platform-profile:profiles/hardware-profile/statistics/config/virtual-output-queue-full-color ";
            if-feature feature-list:HAVE_DUNE;
            if-feature feature-list:NOT_HAVE_DNX;
            type  empty;
            description "Use this attribute to enable or disable Virtual Output Queue Forward
                        Drop filter groups. Disabling filter groups increases the configurable
                        filter entries.";
        } // END of virtual-output-queue-forward-drop definition.

    } // END of hardware-profiles-statistics-config definition.
    grouping hardware-tcam-state {
        description
            "Grouping for hardware tcam state objects.";
        leaf warning-threshold-level  {
            type  int32;
            description "Warning TCAM threshold level in percentage. Value of -1 means the
                        field is not applicable.";
        } // END of warning-threshold-level definition.

        leaf critical-alert-threshold-level  {
            type  int32;
            description "Alert TCAM threshold level in percentage. Value of -1 means the field
                        is not applicable.";
        } // END of critical-alert-threshold-level definition.

    } // END of hardware-tcam-state definition.
    grouping hardware-tcam-filter-group-state {
        description
            "Grouping for hardware tcam filter group state objects.";
        leaf group-id  {
            type  uint32;
            description "A unique number corresponding to each TCAM group. This attribute is
                        used solely for defining the key for the TCAM utilization filter
                        groups object list. It's value shouldn't be interpreted.";
        } // END of group-id definition.

        leaf group-name  {
            type  cml-data-types:cml_line_t {
                length "1..1965";
            }
            description "TCAM Utilization filter group name.";
        } // END of group-name definition.

        leaf free-entries  {
            type  int32;
            description "Count of free entries in the TCAM group. Value of -1 means the field
                        is not applicable.";
        } // END of free-entries definition.

        leaf used-entries  {
            type  int32;
            description "Percentage of entries used in the TCAM group.Value of -1 means the
                        field is not applicable.";
        } // END of used-entries definition.

        leaf used-percentage  {
            type  int32;
            description "Percentage of entries used in the TCAM group. Value of -1 means the
                        field is not applicable.";
        } // END of used-percentage definition.

        leaf total-entries  {
            type  int32;
            description "Count of total entries in the TCAM group.Total is summation of
                        dedicated entries and shared entries.Value of -1 means the field is
                        not applicable.";
        } // END of total-entries definition.

        leaf dedicated-entries  {
            type  int32;
            description "Count of total entries dedicated to TCAM group. Dedicated entries are
                        fixed to the TCAM group and are the minimum guaranteed number. Value
                        of -1 means the field is not applicable.";
        } // END of dedicated-entries definition.

        leaf shared-entries  {
            type  int32;
            description "Count of entries which are shared across TCAM groups. Value of -1
                        means the field is not applicable.";
        } // END of shared-entries definition.

    } // END of hardware-tcam-filter-group-state definition.
    grouping hardware-unit-state {
        description
            "State information for each hardware unit/core.";
        leaf unit  {
            type  uint32;
            description "Unit ID";
        } // END of unit definition.

        leaf core  {
            type  uint32;
            description "Core ID";
        } // END of core definition.

    } // END of hardware-unit-state definition.
    grouping hardware-tcam-filter-top {
        description
            "Grouping for hardware tcam filter";
        container tcam-utilization {
            if-feature feature-list:HAVE_ACL;
            config false;
            description
                "This container defines TCAM Utilization information.";
            container state {
                config false;
                description
                    "This container defines TCAM Utilization information Operational
                            states.";
                uses hardware-tcam-state;
            } // END of state-container definition.
            uses hardware-filter-group;
        } // END of tcam-utilization-container definition.
    } // END of hardware-tcam-filter-top definition.
    grouping hardware-tcam-filter-platform-top {
        description
            "Grouping for hardware tcam filter";
        container tcam-utilization {
            if-feature feature-list:HAVE_ACL;
            config false;
            description
                "This container defines TCAM Utilization information.";
            container state {
                config false;
                description
                    "This container defines TCAM Utilization information Operational
                            states.";
                uses hardware-tcam-state;
            } // END of state-container definition.
            container hardware-units {
                config false;
                description
                    "This container defines per-unit/core TCAM data.";

                list hardware-unit {
                    key "unit core";
                    config false;
                    description
                        "List of hardware units and cores";
                    leaf unit  {
                        type  leafref {
                            path  "../state/unit";
                        }
                        description "Unit ID";
                    } // END of unit definition.

                    leaf core  {
                        type  leafref {
                            path  "../state/core";
                        }
                        description "Core ID";
                    } // END of core definition.

                    container state {
                        config false;
                        description
                            "Operational states per hardware unit/core.";
                        uses hardware-unit-state;
                    } // END of state-container definition.
                    uses hardware-filter-group;
                } // End of hardware-unit-list
            } // END of hardware-units-container definition.
        } // END of tcam-utilization-container definition.
    } // END of hardware-tcam-filter-platform-top definition.
    grouping hardware-filter-group {
        description
            "grouping for TCAM Utilization filter-groups.";
        container filter-groups {
            config false;
            description
                "This container defines TCAM Utilization filter-groups information.";

            list filter-group {
                key "group-id";
                config false;
                description
                    "The list of named filter-group.";
                leaf group-id  {
                    type  leafref {
                        path  "../state/group-id";
                    }
                    description "A unique number corresponding to each TCAM group. This attribute is
                                used solely for defining the key for the TCAM utilization filter
                                groups object list. It's value shouldn't be interpreted.";
                } // END of group-id definition.

                container state {
                    config false;
                    description
                        "This container defines filter-group information Operational states.";
                    uses hardware-tcam-filter-group-state;
                } // END of state-container definition.
            } // End of filter-group-list
        } // END of filter-groups-container definition.
    } // END of hardware-filter-group definition.
    grouping platform-kaps-config {
        description
            "Grouping for forwarding-profiles kaps config objects.";
        leaf profile-type  {
            type  ipi-platform-profile-types:platform_kaps_profile_type_t;
            description "forwarding profile for KAPS";
        } // END of profile-type definition.

    } // END of platform-kaps-config definition.
    grouping platform-ext-tcam-config {
        description
            "Grouping for forwarding-profiles external-tcam config objects.";
        leaf profile-type  {
            type  ipi-platform-profile-types:platform_ext_tcam_profile_type_t;
            default "profile-one";
            description "forwarding profile for external TCAM";
        } // END of profile-type definition.

    } // END of platform-ext-tcam-config definition.
    grouping platform-custom-tcam-config {
        description
            "Grouping for forwarding-profiles external-tcam config objects.";
        leaf profile-type  {
            type  ipi-platform-profile-types:platform_tcam_custom_profile_t;
            mandatory true;
            description "forwarding profile for type for custom-TCAM";
        } // END of profile-type definition.

        leaf ipv4-percentage  {
            type  uint8 {
                 range "10..90"  {
                    description "10..90: Supported range 10 - 90";
                 }
            }
            units "%";
            mandatory true;
            description "Use this attribute to set Percentage of entries for ipv4 routes";
        } // END of ipv4-percentage definition.

        leaf ipv6-percentage  {
            type  uint8 {
                 range "10..90"  {
                    description "10..90: Supported range 10 - 90";
                 }
            }
            units "%";
            mandatory true;
            description "Use this attribute to set Percentage of entries for ipv6 routes";
        } // END of ipv6-percentage definition.

    } // END of platform-custom-tcam-config definition.
    grouping platform-kaps-state {
        description
            "Grouping for KAPS Forwarding Profile state objects.";
        leaf profile  {
            type  ipi-platform-profile-types:platform_kaps_forwading_profile_t;
            description "Profile type";
        } // END of profile definition.

        leaf is-active  {
            type  boolean;
            description "Active in hardware";
        } // END of is-active definition.

        leaf public-db-size  {
            type  uint32;
            description "Public-db size";
        } // END of public-db-size definition.

        leaf private-db-size  {
            type  uint32;
            description "Private-db size";
        } // END of private-db-size definition.

    } // END of platform-kaps-state definition.
    grouping platform-elk-tcam-state {
        description
            "Grouping for External TCAM Forwarding Profile state objects.";
        leaf profile  {
            type  ipi-platform-profile-types:platform_elk_tcam_forwading_profile_t;
            description "Profile type";
        } // END of profile definition.

        leaf is-active  {
            type  boolean;
            description "Active in hardware";
        } // END of is-active definition.

        leaf ipv4-db-size  {
            type  uint32;
            description "IPv4 DB size";
        } // END of ipv4-db-size definition.

        leaf ipv6-db-size  {
            type  uint32;
            description "IPv6 DB size";
        } // END of ipv6-db-size definition.

    } // END of platform-elk-tcam-state definition.
    grouping platform-rate-limit-config {
        description
            "Grouping for cpu-queue rate-limit config objects.";
        leaf queue-name  {
            type  ipi-platform-profile-types:platform_cpu_queue_name_t;
            description "This attribute specifies CPU queue name for rate limiting config";
        } // END of queue-name definition.

        leaf rate  {
            type  int32 {
                 range "0..100000"  {
                    description "0..100000:Feature : HAVE_DUNE Supported range 0 - 100000Not Feature :
                            HAVE_DUNE  Supported range 0 - 100000";
                 }
            }
            description "CPU queue Rate";
        } // END of rate definition.

        leaf monitor-status  {
            if-feature feature-list:HAVE_DUNE;
            type  ipi-platform-profile-types:platform_cpu_queue_monitor_t;
            description "monitor cpu queue usage";
        } // END of monitor-status definition.

    } // END of platform-rate-limit-config definition.
    grouping platform-load-balance-config {
        description
            "Grouping for load-balance config objects.";
        leaf enable  {
            type  empty;
            mandatory true;
            description "This Object is set loadBalance";
        } // END of enable definition.

        leaf mpls-label-based  {
            type  empty;
            description "This Object is set for load balancing based on mpls labels";
        } // END of mpls-label-based definition.

        leaf mpls-inner-stack  {
            // when " ipi-platform-profile:hardware/hw-soc-property/config/parser-enable ";
            if-feature feature-list:HAVE_MPLS;
            if-feature feature-list:HAVE_DUNE;
            if-feature feature-list:NOT_HAVE_DNX;
            type  ipi-platform-profile-types:platform_load_balance_mpls_inner_stack_t;
            description "This Object is set for Source IPV4 based load balancing";
        } // END of mpls-inner-stack definition.

        leaf rtag7-all-lag-if  {
            if-feature feature-list:NOT_HAVE_DUNE;
            type  empty;
            description "Use this attribute to enable RTAG7 on every aggregator interface";
        } // END of rtag7-all-lag-if definition.

        leaf multi-level-ecmp  {
            // when " ipi-platform-profile:hardware/load-balance/config/enable ";
            if-feature feature-list:HAVE_L3;
            if-feature feature-list:HAVE_DUNE;
            if-feature feature-list:NOT_HAVE_DNX;
            type  empty;
            description "Use this attribute to enable or disable multi level ECMP load
                        balancing";
        } // END of multi-level-ecmp definition.

        leaf trunk-hash-offset  {
            // when " ipi-platform-profile:hardware/load-balance/config/enable ";
            if-feature feature-list:HAVE_DUNE;
            if-feature feature-list:NOT_HAVE_DNX;
            type  uint8 {
                 range "0..15"  {
                    description "0..15: Supported range 0 - 15";
                 }
            }
            description "Set trunk hash offset (valid range: 0-15)";
        } // END of trunk-hash-offset definition.

        leaf ecmp-hash-offset  {
            // when " ipi-platform-profile:hardware/load-balance/config/enable ";
            if-feature feature-list:HAVE_DUNE;
            if-feature feature-list:NOT_HAVE_DNX;
            type  uint8 {
                 range "0..15"  {
                    description "0..15: Supported range 0 - 15";
                 }
            }
            description "Set ecmp hash offset (valid range: 0-15)";
        } // END of ecmp-hash-offset definition.

        leaf hash-seed  {
            // when " ipi-platform-profile:hardware/load-balance/config/enable ";
            if-feature feature-list:HAVE_DUNE;
            if-feature feature-list:NOT_HAVE_DNX;
            type  uint16 {
                 range "1..65535"  {
                    description "1..65535: Supported range 1 - 65535";
                 }
            }
            description "Set hash seed (valid range: 1-65535)";
        } // END of hash-seed definition.

    } // END of platform-load-balance-config definition.
    grouping platform-load-balance-l2-config {
        description
            "Grouping for load-balance l2 config objects.";
        leaf dest-mac-based  {
            if-feature feature-list:NOT_HAVE_DNX;
            type  empty;
            description "This Object is set for Destination Mac address based load balancing";
        } // END of dest-mac-based definition.

        leaf src-mac-based  {
            if-feature feature-list:NOT_HAVE_DNX;
            type  empty;
            description "This Object is set for Source Mac address based load balancing";
        } // END of src-mac-based definition.

        leaf ether-type-based  {
            type  empty;
            description "This Object is set for Ether-type based load balancing";
        } // END of ether-type-based definition.

        leaf vlan-based  {
            type  empty;
            description "This Object is set for Vlan based load balancing";
        } // END of vlan-based definition.

    } // END of platform-load-balance-l2-config definition.
    grouping platform-load-balance-ipv4-config {
        description
            "Grouping for load-balance ipv4 config objects.";
        leaf src-ipv4-address-based  {
            if-feature feature-list:NOT_HAVE_DNX;
            type  empty;
            description "This Object is set for Source IPV4 based load balancing";
        } // END of src-ipv4-address-based definition.

        leaf dest-ipv4-address-based  {
            if-feature feature-list:NOT_HAVE_DNX;
            type  empty;
            description "This Object is set for Destination IPV4 based load balancing";
        } // END of dest-ipv4-address-based definition.

        leaf src-l4-port-based  {
            if-feature feature-list:NOT_HAVE_DNX;
            type  empty;
            description "This Object is set for Source L4 port based load balancing";
        } // END of src-l4-port-based definition.

        leaf dest-l4-port-based  {
            if-feature feature-list:NOT_HAVE_DNX;
            type  empty;
            description "This Object is set for Destination L4 port based load balancing";
        } // END of dest-l4-port-based definition.

        leaf protocol-id-based  {
            type  empty;
            description "This Object is set for Protocol Id based load balancing";
        } // END of protocol-id-based definition.

        leaf rocev2-dest-qpairs  {
            if-feature feature-list:NOT_HAVE_DUNE;
            type  empty;
            description "This Object is set for qpairs based load balancing on ROCE";
        } // END of rocev2-dest-qpairs definition.

    } // END of platform-load-balance-ipv4-config definition.
    grouping platform-load-balance-flb-base-config {
        description
            "Grouping for load-balance flb config objects.";
        leaf enable  {
            type  empty;
            mandatory true;
            description "This Object is set loadBalance";
        } // END of enable definition.

    } // END of platform-load-balance-flb-base-config definition.
    grouping platform-cpu-queue-top {
        description
            "Grouping for platform cpu-queue objects.";
        container cpu-queue {
            if-feature feature-list:HAVE_BROADCOM_OR_HAVE_MARVELL;
            description
                "This container defines cpu-queue configuration and state information.";
            container rate-limits {
                description
                    "This container defines rate-limits configuration and state
                            information.";

                list rate-limit {
                    key "queue-name";
                    description
                        "The list of rate-limit configuration.";
                    leaf queue-name  {
                        type  leafref {
                            path  "../config/queue-name";
                        }
                        description "This attribute specifies CPU queue name for rate limiting config";
                    } // END of queue-name definition.

                    container config {
                        description
                            "This container defines cpu-queue rate-limit configuration.";
                        uses platform-rate-limit-config;
                        uses platform-extended-rate-limit-config;
                    } // END of config-container definition.
                    container state {
                        config false;
                        description
                            "This container defines cpu-queue rate-limit information Operational
                                    states.";
                        uses platform-rate-limit-config;
                        uses platform-extended-rate-limit-config;
                    } // END of state-container definition.
                } // End of rate-limit-list
            } // END of rate-limits-container definition.
        } // END of cpu-queue-container definition.
    } // END of platform-cpu-queue-top definition.
    grouping platform-load-balance-ipv6-config {
        description
            "Grouping for load-balance ipv6 config objects.";
        leaf src-ipv6-address-based  {
            if-feature feature-list:NOT_HAVE_DNX;
            type  empty;
            description "This Object is set for Source IPV6 based load balancing";
        } // END of src-ipv6-address-based definition.

        leaf dest-ipv6-address-based  {
            if-feature feature-list:NOT_HAVE_DNX;
            type  empty;
            description "This Object is set for Destination IPV6 based load balancing";
        } // END of dest-ipv6-address-based definition.

        leaf src-l4-port-based  {
            if-feature feature-list:NOT_HAVE_DNX;
            type  empty;
            description "This Object is set for Source L4 port based load balancing";
        } // END of src-l4-port-based definition.

        leaf dest-l4-port-based  {
            if-feature feature-list:NOT_HAVE_DNX;
            type  empty;
            description "This Object is set for Destination L4 port based load balancing";
        } // END of dest-l4-port-based definition.

        leaf next-header-based  {
            type  empty;
            description "This Object is set for Next Header Field for IPV6";
        } // END of next-header-based definition.

        leaf rocev2-dest-qpairs  {
            if-feature feature-list:NOT_HAVE_DUNE;
            type  empty;
            description "This Object is set for qpairs based load balancing on ROCE";
        } // END of rocev2-dest-qpairs definition.

    } // END of platform-load-balance-ipv6-config definition.
    grouping mvl-platform-load-balance-config {
        description
            "Marvell Grouping for load-balance config objects.";
        leaf enable  {
            if-feature feature-list:HAVE_MARVELL;
            type  empty;
            mandatory true;
            description "This Object is set loadBalance";
        } // END of enable definition.

        leaf mpls-label-based  {
            if-feature feature-list:HAVE_MARVELL;
            if-feature feature-list:HAVE_MPLS;
            type  empty;
            description "This Object is set for load balancing based on mpls labels";
        } // END of mpls-label-based definition.

    } // END of mvl-platform-load-balance-config definition.
    grouping mvl-platform-load-balance-l2-config {
        description
            "Marvell Grouping for load-balance l2 config objects.";
        leaf dest-mac-based  {
            if-feature feature-list:HAVE_MARVELL;
            type  empty;
            description "This Object is set for Destination Mac address based load balancing";
        } // END of dest-mac-based definition.

        leaf src-mac-based  {
            if-feature feature-list:HAVE_MARVELL;
            type  empty;
            description "This Object is set for Source Mac address based load balancing";
        } // END of src-mac-based definition.

        leaf ether-type-based  {
            if-feature feature-list:HAVE_MARVELL;
            type  empty;
            description "This Object is set for Ether-type based load balancing";
        } // END of ether-type-based definition.

        leaf vlan-based  {
            if-feature feature-list:HAVE_MARVELL;
            type  empty;
            description "This Object is set for Vlan based load balancing";
        } // END of vlan-based definition.

        leaf ing-intf-based  {
            if-feature feature-list:HAVE_MARVELL;
            type  empty;
            description "This Object is set for Source Physical Port based load balancing";
        } // END of ing-intf-based definition.

    } // END of mvl-platform-load-balance-l2-config definition.
    grouping mvl-platform-load-balance-ipv4-config {
        description
            "Marvell Grouping for load-balance ipv4 config objects.";
        leaf src-ipv4-address-based  {
            if-feature feature-list:HAVE_MARVELL;
            type  empty;
            description "This Object is set for Source IPV4 based load balancing";
        } // END of src-ipv4-address-based definition.

        leaf dest-ipv4-address-based  {
            if-feature feature-list:HAVE_MARVELL;
            type  empty;
            description "This Object is set for Destination IPV4 based load balancing";
        } // END of dest-ipv4-address-based definition.

        leaf src-l4-port-based  {
            if-feature feature-list:HAVE_MARVELL;
            type  empty;
            description "This Object is set for Source L4 port based load balancing";
        } // END of src-l4-port-based definition.

        leaf dest-l4-port-based  {
            if-feature feature-list:HAVE_MARVELL;
            type  empty;
            description "This Object is set for Destination L4 port based load balancing";
        } // END of dest-l4-port-based definition.

        leaf protocol-id-based  {
            type  empty;
            description "This Object is set for Protocol Id based load balancing";
        } // END of protocol-id-based definition.

    } // END of mvl-platform-load-balance-ipv4-config definition.
    grouping mvl-platform-load-balance-ipv6-config {
        description
            "Marvell Grouping for load-balance ipv6 config objects.";
        leaf flow-label-based  {
            if-feature feature-list:HAVE_MARVELL;
            type  empty;
            description "Flowlabel based load balancing";
        } // END of flow-label-based definition.

        leaf src-ipv6-address-based  {
            type  empty;
            description "This Object is set for Source IPV6 based load balancing";
        } // END of src-ipv6-address-based definition.

        leaf dest-ipv6-address-based  {
            type  empty;
            description "This Object is set for Destination IPV6 based load balancing";
        } // END of dest-ipv6-address-based definition.

        leaf src-l4-port-based  {
            type  empty;
            description "This Object is set for Source L4 port based load balancing";
        } // END of src-l4-port-based definition.

        leaf dest-l4-port-based  {
            type  empty;
            description "This Object is set for Destination L4 port based load balancing";
        } // END of dest-l4-port-based definition.

        leaf next-header-based  {
            type  empty;
            description "This Object is set for Next Header Field for IPV6";
        } // END of next-header-based definition.

    } // END of mvl-platform-load-balance-ipv6-config definition.

    grouping  forwarding-profile-route-modes-grouping {
    description
        "This container defines forwarding-profiles-route-modes configuration
                and state information";
    container forwarding-profile-route-modes {
        if-feature feature-list:HAVE_BROADCOM;
        if-feature feature-list:HAVE_CMMD;
        if-feature feature-list:HAVE_BROADCOM_OR_HAVE_MARVELL;
        description
            "This container defines forwarding-profiles-route-modes configuration
                    and state information";
        container config {
            if-feature feature-list:HAVE_BCM_UFT;
            if-feature feature-list:NOT_HAVE_DUNE;
            description
                "This container defines forwarding-profiles-route-modes configuration.";
            uses platform-extended-forwarding-profile-route-modes-config;
        } // END of config-container definition.
        container state {
            if-feature feature-list:HAVE_BCM_UFT;
            if-feature feature-list:NOT_HAVE_DUNE;
            config false;
            description
                "This container defines forwarding-profile-route-modes operational
                        states.";
            uses platform-extended-forwarding-profile-route-modes-config;
        } // END of state-container definition.
    } // END of forwarding-profile-route-modes-container definition.
    } // END of forwarding-profile-route-modes-grouping definition.

    grouping  profiles-grouping {
    description
        "Top level container for platform profiles, including configuration and
                state data";
    container profiles {
        if-feature feature-list:HAVE_BROADCOM;
        if-feature feature-list:HAVE_CMMD;
        if-feature feature-list:HAVE_BROADCOM_OR_HAVE_MARVELL;
        description
            "Top level container for platform profiles, including configuration and
                    state data";
        container hardware-profile {
            description
                "This container defines hardware-profile configuration and state
                        information.";
            container config {
                description
                    "This container defines hardware-profile configuration.";
                uses hardware-profile-config;
            } // END of config-container definition.
            container state {
                config false;
                description
                    "This container defines hardware-profile Operational states.";
                uses hardware-profile-config;
            } // END of state-container definition.
            container filters {
                description
                    "This container defines hardware-profile filter configuration and state
                            information.";
                container config {
                    description
                        "This container defines hardware-profile filter configuration.";
                    uses hardware-profile-filters-config;
                } // END of config-container definition.
                container state {
                    config false;
                    description
                        "This container defines hardware-profile filter Operational states.";
                    uses hardware-profile-filters-config;
                } // END of state-container definition.
                uses hardware-tcam-filter-platform-top;
            } // END of filters-container definition.
            container filter-evpn-mpls-mh {
                description
                    "This container defined hardware profile-filter evpn-mpls-mh
                            configuration and state information.";
                container config {
                    description
                        "This container defines hardware-profile filter evpn-mpls-mh
                                configuration";
                    uses hardware-profile-filter-evpn-mpls-multi-homing;
                } // END of config-container definition.
                container state {
                    config false;
                    description
                        "This container defines hardware-profile filter evpn-mpls-mh
                                Operational states";
                    uses hardware-profile-filter-evpn-mpls-multi-homing;
                } // END of state-container definition.
                uses hardware-tcam-filter-top;
            } // END of filter-evpn-mpls-mh-container definition.
            container statistics {
                description
                    "This container defines hardware-profile statistics configuration and
                            state information.";
                container config {
                    description
                        "This container defines hardware-profile statistics configuration.";
                    uses hardware-profiles-statistics-config;
                } // END of config-container definition.
                container state {
                    config false;
                    description
                        "This container defines hardware-profile statistics Operational states.";
                    uses hardware-profiles-statistics-config;
                } // END of state-container definition.
            } // END of statistics-container definition.
            uses hardware-l2vpn-instances-limits-grouping;
        } // END of hardware-profile-container definition.
        container forwarding-profiles {
            description
                "This container defines forwarding-profiles configuration and state
                        information.";
            container config {
                if-feature feature-list:HAVE_BCM_UFT;
                if-feature feature-list:NOT_HAVE_DUNE;
                description
                    "This container defines forwarding-profiles configuration.";
                uses platform-extended-forwarding-profile-config;
            } // END of config-container definition.
            container state {
                if-feature feature-list:HAVE_BCM_UFT;
                if-feature feature-list:NOT_HAVE_DUNE;
                config false;
                description
                    "This container defines forwarding-profiles operational states.";
                uses platform-extended-forwarding-profile-config;
            } // END of state-container definition.
            container kaps {
                if-feature feature-list:HAVE_DUNE;
                if-feature feature-list:HAVE_BCM_UFT;
                if-feature feature-list:NOT_HAVE_DNX;
                description
                    "This container defines forwarding-profiles KAPS configuration and
                            state information.";
                container config {
                    description
                        "This container defines forwarding-profiles KAPS configuration.";
                    uses platform-kaps-config;
                } // END of config-container definition.
                container state {
                    config false;
                    description
                        "This container definesforwarding-profiles KAPS Operational states.";
                    uses platform-kaps-config;
                } // END of state-container definition.
            } // END of kaps-container definition.
            container external-tcam {
                if-feature feature-list:HAVE_DUNE;
                if-feature feature-list:HAVE_BCM_UFT;
                if-feature feature-list:NOT_HAVE_DNX;
                description
                    "This container defines forwarding-profiles external-TCAM configuration
                            and state information.";
                container config {
                    description
                        "This container defines forwarding-profiles external-TCAM
                                configuration.";
                    uses platform-ext-tcam-config;
                } // END of config-container definition.
                container state {
                    config false;
                    description
                        "This container definesforwarding-profiles external-TCAM Operational
                                states.";
                    uses platform-ext-tcam-config;
                } // END of state-container definition.
            } // END of external-tcam-container definition.
            container custom-tcam {
                if-feature feature-list:HAVE_DUNE;
                if-feature feature-list:HAVE_BCM_UFT;
                if-feature feature-list:NOT_HAVE_DNX;
                description
                    "This container defines forwarding-profiles custom-TCAM configuration
                            and state information.";
                container config {
                    presence "forwarding-profiles custom-tcam configuration";
                    description
                        "This container defines forwarding-profiles custom-TCAM configuration.";
                    uses platform-custom-tcam-config;
                } // END of config-container definition.
                container state {
                    config false;
                    description
                        "This container defines forwarding-profiles custom-TCAM Operational
                                states.";
                    uses platform-custom-tcam-config;
                } // END of state-container definition.
            } // END of custom-tcam-container definition.
            container table-limit {
                if-feature feature-list:HAVE_BCM_UFT;
                config false;
                description
                    "This container defines profile table maximum supported values state
                            information.";

                list kaps {
                    if-feature feature-list:HAVE_DUNE;
                    key "profile";
                    config false;
                    description
                        "The list of forwarding-profiles KAPS.";
                    leaf profile  {
                        type  leafref {
                            path  "../state/profile";
                        }
                        description "Forwarding Profile KAPS Profile type.";
                    } // END of profile definition.

                    container state {
                        config false;
                        description
                            "This container defines KAPS information Operational states.";
                        uses platform-kaps-state;
                    } // END of state-container definition.
                } // End of kaps-list

                list external-tcam {
                    if-feature feature-list:HAVE_DUNE;
                    if-feature feature-list:HAVE_ELK_TCAM;
                    key "profile";
                    config false;
                    description
                        "The list of forwarding-profiles external-TCAM.";
                    leaf profile  {
                        type  leafref {
                            path  "../state/profile";
                        }
                        description "Forwarding Profile External TCAM Profile type.";
                    } // END of profile definition.

                    container state {
                        config false;
                        description
                            "This container defines external-TCAM information Operational states.";
                        uses platform-elk-tcam-state;
                    } // END of state-container definition.
                } // End of external-tcam-list
                uses state-grouping;
                uses table-sizes-grouping;
            } // END of table-limit-container definition.
            uses mdb-grouping;
            uses custom-profile-grouping;
            uses hardware-routing-limits-grouping;
        } // END of forwarding-profiles-container definition.
    } // END of profiles-container definition.
    } // END of profiles-grouping definition.

    grouping  hardware-grouping {
    description
        "Top level container for hardware, including configuration and state
                data";
    container hardware {
        if-feature feature-list:HAVE_BROADCOM;
        if-feature feature-list:HAVE_CMMD;
        if-feature feature-list:HAVE_BROADCOM_OR_HAVE_MARVELL;
        description
            "Top level container for hardware, including configuration and state
                    data";
        container hw-soc-property {
            description
                "This container defines hardware SOC property enable configuration and
                        state information.";
            container config {
                description
                    "This container defines hardware load-balance configuration.";
                uses platform-advanced-parser-soc-enable;
            } // END of config-container definition.
            container state {
                config false;
                description
                    "This container defines hardware load-balance Operational states.";
                uses platform-advanced-parser-soc-enable;
            } // END of state-container definition.
        } // END of hw-soc-property-container definition.
        container load-balance {
            if-feature feature-list:HAVE_BROADCOM;
            description
                "This container defines hardware load-balance configuration and state
                        information.";
            container config {
                presence "hardware load-balance configuration";
                description
                    "This container defines hardware load-balance configuration.";
                uses platform-load-balance-config;
                uses platform-extended-load-balance-config;
            } // END of config-container definition.
            container state {
                config false;
                description
                    "This container defines hardware load-balance Operational states.";
                uses platform-load-balance-config;
                uses platform-extended-load-balance-config;
            } // END of state-container definition.
            container l2 {
                // when " ipi-platform-profile:hardware/load-balance/config/enable ";
                if-feature feature-list:HAVE_L2;
                description
                    "This container defines load-balance l2 configuration and state
                            information.";
                container config {
                    description
                        "This container defines load-balance l2 configuration.";
                    uses platform-load-balance-l2-config;
                    uses platform-extended-load-balance-l2-config;
                } // END of config-container definition.
                container state {
                    config false;
                    description
                        "This container defines load-balance l2 Operational states.";
                    uses platform-load-balance-l2-config;
                    uses platform-extended-load-balance-l2-config;
                } // END of state-container definition.
                uses inner-l2-grouping;
            } // END of l2-container definition.
            container ipv4 {
                // when " ipi-platform-profile:hardware/load-balance/config/enable ";
                if-feature feature-list:HAVE_L3;
                description
                    "This container defines load-balance ipv4 configuration and state
                            information.";
                container config {
                    description
                        "This container defines load-balance ipv4 configuration.";
                    uses platform-load-balance-ipv4-config;
                    uses platform-extended-load-balance-ipv4-config;
                } // END of config-container definition.
                container state {
                    config false;
                    description
                        "This container defines load-balance ipv4 Operational states.";
                    uses platform-load-balance-ipv4-config;
                    uses platform-extended-load-balance-ipv4-config;
                } // END of state-container definition.
                uses inner-ipv4-grouping;
            } // END of ipv4-container definition.
            container ipv6 {
                // when " ipi-platform-profile:hardware/load-balance/config/enable ";
                if-feature feature-list:HAVE_L3;
                description
                    "This container defines load-balance ipv6 configuration and state
                            information.";
                container config {
                    description
                        "This container defines load-balance ipv6 configuration.";
                    uses platform-load-balance-ipv6-config;
                    uses platform-extended-load-balance-ipv6-config;
                } // END of config-container definition.
                container state {
                    config false;
                    description
                        "This container defines load-balance ipv6 Operational states.";
                    uses platform-load-balance-ipv6-config;
                    uses platform-extended-load-balance-ipv6-config;
                } // END of state-container definition.
            } // END of ipv6-container definition.
            uses tunnel-grouping;
            uses vxlan-grouping;
            uses mpls-ler-grouping;
            uses l4-port-grouping;
            uses port-channel-grouping;
        } // END of load-balance-container definition.
        container dram-tune {
            if-feature feature-list:HAVE_BROADCOM;
            config false;
            description
                "This container defines dram-tuning-profiles information.";
            container state {
                config false;
                description
                    "This container defines operational data for dram-tune";
                leaf dram-tune-status  {
                    if-feature feature-list:HAVE_BROADCOM;
                    type  int32;
                    default "0";
                    description "Use this attribute to configure or unconfigure hardware profile
                                service-queue profile support.";
                } // END of dram-tune-status definition.

            } // END of state-container definition.
        } // END of dram-tune-container definition.
        uses platform-cpu-queue-top;
        uses mac-ageing-grouping;
        uses platform-grouping;
        uses cpu-control-grouping;
    } // END of hardware-container definition.
    } // END of hardware-grouping definition.

    grouping  mvl-hardware-grouping {
    description
        "Top level container for Marvell hardware, including configuration and
                state data";
    container mvl-hardware {
        if-feature feature-list:HAVE_MARVELL;
        if-feature feature-list:HAVE_CMMD;
        if-feature feature-list:HAVE_BROADCOM_OR_HAVE_MARVELL;
        description
            "Top level container for Marvell hardware, including configuration and
                    state data";
        container load-balance {
            description
                "This container defines marvell load-balance configuration and state
                        information.";
            container config {
                presence "marvell load-balance configuration";
                description
                    "This container defines Marvell load-balancel configuration.";
                uses mvl-platform-load-balance-config;
            } // END of config-container definition.
            container state {
                config false;
                description
                    "This container defines marvell load-balance configuration Operational
                            states.";
                uses mvl-platform-load-balance-config;
            } // END of state-container definition.
            container l2 {
                // when " ipi-platform-profile:mvl-hardware/load-balance/config/enable ";
                if-feature feature-list:HAVE_L2;
                description
                    "This container defines load-balance l2 configuration and state
                            information.";
                container config {
                    description
                        "This container defines load-balance l2 configuration.";
                    uses mvl-platform-load-balance-l2-config;
                } // END of config-container definition.
                container state {
                    config false;
                    description
                        "This container defines load-balance l2 Operational states.";
                    uses mvl-platform-load-balance-l2-config;
                } // END of state-container definition.
                uses inner-l2-grouping;
            } // END of l2-container definition.
            container ipv4 {
                // when " ipi-platform-profile:mvl-hardware/load-balance/config/enable ";
                if-feature feature-list:HAVE_L3;
                description
                    "This container defines load-balance ipv4 configuration and state
                            information.";
                container config {
                    description
                        "This container defines load-balance ipv4 configuration.";
                    uses mvl-platform-load-balance-ipv4-config;
                } // END of config-container definition.
                container state {
                    config false;
                    description
                        "This container defines load-balance ipv4 Operational states.";
                    uses mvl-platform-load-balance-ipv4-config;
                } // END of state-container definition.
                uses inner-ipv4-grouping;
            } // END of ipv4-container definition.
            container ipv6 {
                // when " ipi-platform-profile:mvl-hardware/load-balance/config/enable ";
                if-feature feature-list:HAVE_L3;
                description
                    "This container defines load-balance ipv6 configuration and state
                            information.";
                container config {
                    description
                        "This container defines load-balance ipv6 configuration.";
                    uses mvl-platform-load-balance-ipv6-config;
                } // END of config-container definition.
                container state {
                    config false;
                    description
                        "This container defines load-balance ipv6 Operational states.";
                    uses mvl-platform-load-balance-ipv6-config;
                } // END of state-container definition.
            } // END of ipv6-container definition.
            uses tunnel-grouping;
            uses vxlan-grouping;
            uses mpls-ler-grouping;
            uses l4-port-grouping;
            uses port-channel-grouping;
        } // END of load-balance-container definition.
        uses platform-cpu-queue-top;
    } // END of mvl-hardware-container definition.
    } // END of mvl-hardware-grouping definition.


}
