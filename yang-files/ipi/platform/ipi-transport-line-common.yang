/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-transport-line-common.yang
*
*/

module ipi-transport-line-common {

    yang-version 1.1;

    namespace   "http://www.ipinfusion.com/yang/ocnos/ipi-transport-line-common";

    prefix "ipi-transport-line-common";

    import ipi-platform-port {
        prefix ipi-platform-port;
        revision-date 2022-06-01;
    }

    import ipi-platform {
        prefix ipi-platform;
        revision-date 2026-08-14;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for optical transport line system
                elements";


    revision "2022-06-01" {
        description "Updated the yang file with feature";
        reference " 0.3.0.";
    }

    revision "2021-06-24" {
        description "Attribute optical-port-type added and admin-state removed.";
        reference " 0.2.0.";
    }

    revision "2021-01-25" {
        description "Initial revision";
        reference " 0.1.0.";
    }



    typedef  cml_optical_port_type_t {
        type enumeration {
            enum terminal-client {
                value 0;
                description "Client-facing port on a terminal optics device";
            }
            enum terminal-line {
                value 1;
                description "Line-facing port on a terminal optics device";
            }
        }
        description "type definition for CML_OPTICAL_PORT_TYPE_T";
    }    grouping transport-line-common-port-state {
        description
            "Operational state data describing optical line ports";
        leaf optical-port-type  {
            type  cml_optical_port_type_t;
            description "This indicates the type of optical port";
        } // END of optical-port-type definition.

    } // END of transport-line-common-port-state definition.

    grouping  optical-port-grouping {
    description
        "Contains data specific to ports on optical transport devices";
    container optical-port {
        if-feature feature-list:HAVE_COHERENT_OPTICS;
        if-feature feature-list:HAVE_CMMD;
        config false;
        description
            "Contains data specific to ports on optical transport devices";
        container state {
            config false;
            description
                "Operational state data for optical ports";
            uses transport-line-common-port-state;
        } // END of state-container definition.
    } // END of optical-port-container definition.
    } // END of optical-port-grouping definition.

    augment /ipi-platform:components/ipi-platform:component/ipi-platform-port:port {
        if-feature feature-list:HAVE_CMMD;
        description
            "Contains data specific to ports on optical transport devices";
        uses optical-port-grouping;
    }


}
