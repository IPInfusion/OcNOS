/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-power-rail.yang
*
*/

submodule ipi-platform-power-rail {

    yang-version 1.1;

    belongs-to  ipi-platform { prefix ipi-platform; }

    import feature-list {
        prefix feature-list;
        revision-date 2026-09-15;
    }

    import ipi-platform-types {
        prefix ipi-platform-types;
        revision-date 2026-04-16;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for power-rail component in platform
                datamodel";


    revision "2022-06-01" {
        description "Updated the yang file with feature";
        reference " 0.4.0.";
    }

    revision "2021-09-03" {
        description "Update descriptions of attribute";
        reference " 0.3.0.";
    }

    revision "2021-07-21" {
        description "New attributes added";
        reference " 0.2.0.";
    }

    revision "2021-01-25" {
        description "Initial version adding support to power-rail component in ipi-platform module";
        reference " 0.1.0.";
    }

    grouping power-rail-state {
        description
            "power-rail data for platform components";
        leaf power-vddr-status  {
            type  ipi-platform-types:cml_cmm_power_rail_t;
            description "Power status for VCC 3.3V on Main board";
        } // END of power-vddr-status definition.

        leaf power-core-status  {
            type  ipi-platform-types:cml_cmm_power_rail_t;
            description "Power status for Mac 1V on Main board";
        } // END of power-core-status definition.

        leaf v1p1-power-rail  {
            type  ipi-platform-types:cml_cmm_power_rail_t;
            description "Power status for Mac AVS 1V on Main board";
        } // END of v1p1-power-rail definition.

        leaf main-board-power-rail  {
            type  ipi-platform-types:cml_cmm_power_rail_t;
            description "Power status for Main Board";
        } // END of main-board-power-rail definition.

        leaf vcc-5v-power-status  {
            type  ipi-platform-types:cml_cmm_power_rail_t;
            description "Power status of VCC 5V";
        } // END of vcc-5v-power-status definition.

        leaf vcc-3v-power-status  {
            type  ipi-platform-types:cml_cmm_power_rail_t;
            description "Power status of VCC 3.3 V";
        } // END of vcc-3v-power-status definition.

        leaf vcc-1v-mac-power-status  {
            type  ipi-platform-types:cml_cmm_power_rail_t;
            description "Power status of VCC MAC 1V";
        } // END of vcc-1v-mac-power-status definition.

        leaf vcc-1v-mac-avs-power-status  {
            type  ipi-platform-types:cml_cmm_power_rail_t;
            description "Power status of VCC MAC AVS 1V";
        } // END of vcc-1v-mac-avs-power-status definition.

        leaf vccv1p05-power-status  {
            type  ipi-platform-types:cml_cmm_power_rail_t;
            description "Power status of VCC 1.05V";
        } // END of vccv1p05-power-status definition.

        leaf vccv1p5-power-status  {
            type  ipi-platform-types:cml_cmm_power_rail_t;
            description "Power status of VCC 1.5V";
        } // END of vccv1p5-power-status definition.

        leaf vccv1p8-power-status  {
            type  ipi-platform-types:cml_cmm_power_rail_t;
            description "Power status of VCC 1.8V";
        } // END of vccv1p8-power-status definition.

        leaf v1p05-power-rail  {
            type  ipi-platform-types:cml_cmm_power_rail_t;
            description "Power rail 1.05V status";
        } // END of v1p05-power-rail definition.

        leaf vcc-power-rail  {
            type  ipi-platform-types:cml_cmm_power_rail_t;
            description "Power rail VCC status";
        } // END of vcc-power-rail definition.

        leaf sbv1p5-power-rail  {
            type  ipi-platform-types:cml_cmm_power_rail_t;
            description "Power rail SBV 1.5 status";
        } // END of sbv1p5-power-rail definition.

        leaf v1p0-power-rail  {
            type  ipi-platform-types:cml_cmm_power_rail_t;
            description "Power rail 1.0V status";
        } // END of v1p0-power-rail definition.

        leaf v1p5-power-rail  {
            type  ipi-platform-types:cml_cmm_power_rail_t;
            description "Power rail 1.5V status";
        } // END of v1p5-power-rail definition.

        leaf v3p3-power-rail  {
            type  ipi-platform-types:cml_cmm_power_rail_t;
            description "Power rail 3.3V status";
        } // END of v3p3-power-rail definition.

        leaf v1p8-power-rail  {
            type  ipi-platform-types:cml_cmm_power_rail_t;
            description "Power rail 1.8V status";
        } // END of v1p8-power-rail definition.

        leaf v1p9-power-rail  {
            type  ipi-platform-types:cml_cmm_power_rail_t;
            description "Power rail 1.9V status";
        } // END of v1p9-power-rail definition.

        leaf v1p35-power-rail  {
            type  ipi-platform-types:cml_cmm_power_rail_t;
            description "Power Rail 1.35 status";
        } // END of v1p35-power-rail definition.

        leaf vcc-avs-1v-power-status  {
            type  ipi-platform-types:cml_cmm_power_rail_t;
            description "Power status of VCC AVS 1V";
        } // END of vcc-avs-1v-power-status definition.

        leaf ddrvtt-power-status  {
            type  ipi-platform-types:cml_cmm_power_rail_t;
            description "Power statistics for VCC 5V on Main board";
        } // END of ddrvtt-power-status definition.

        leaf vcc-mac-v1p25-power-status  {
            type  ipi-platform-types:cml_cmm_power_rail_t;
            description "Power status of VCC MAC 1.25 V";
        } // END of vcc-mac-v1p25-power-status definition.

        leaf mac-v1p8-power-status  {
            type  ipi-platform-types:cml_cmm_power_rail_t;
            description "Power status of MAC 1.8 V";
        } // END of mac-v1p8-power-status definition.

        leaf power-supply-1-power-status  {
            type  ipi-platform-types:cml_cmm_power_rail_t;
            description "Power status of Power Supply 1";
        } // END of power-supply-1-power-status definition.

        leaf power-supply-2-power-status  {
            type  ipi-platform-types:cml_cmm_power_rail_t;
            description "Power status of Power Supply 2";
        } // END of power-supply-2-power-status definition.

        leaf power-supply-1-power-rail  {
            type  ipi-platform-types:cml_cmm_power_rail_t;
            description "Power rail status of Power Supply 1";
        } // END of power-supply-1-power-rail definition.

        leaf power-supply-2-power-rail  {
            type  ipi-platform-types:cml_cmm_power_rail_t;
            description "Power rail status of Power Supply 2";
        } // END of power-supply-2-power-rail definition.

        leaf power-supply-1-v12-power-rail  {
            type  ipi-platform-types:cml_cmm_power_rail_t;
            description "Power rail status of Power Supply 1 12V";
        } // END of power-supply-1-v12-power-rail definition.

        leaf power-supply-2-v12-power-rail  {
            type  ipi-platform-types:cml_cmm_power_rail_t;
            description "Power rail status of Power Supply 2 12V";
        } // END of power-supply-2-v12-power-rail definition.

        leaf power-supply-1-ac-alert-power-rail  {
            type  ipi-platform-types:cml_cmm_power_rail_t;
            description "Power rail status of Power Supply 1 AC alert";
        } // END of power-supply-1-ac-alert-power-rail definition.

        leaf power-supply-2-ac-alert-power-rail  {
            type  ipi-platform-types:cml_cmm_power_rail_t;
            description "Power rail status of Power Supply 2 AC alert";
        } // END of power-supply-2-ac-alert-power-rail definition.

        leaf power-vccp-status  {
            type  ipi-platform-types:cml_cmm_power_rail_t;
            description "Power status for VCCP on Main board";
        } // END of power-vccp-status definition.

        leaf v5a-power-rail  {
            type  ipi-platform-types:cml_cmm_power_rail_t;
            description "Power rail 5VA status";
        } // END of v5a-power-rail definition.

        leaf v3p3a-power-rail  {
            type  ipi-platform-types:cml_cmm_power_rail_t;
            description "Power rail 3.3VA status";
        } // END of v3p3a-power-rail definition.

        leaf hot-swap-1-power-rail  {
            type  ipi-platform-types:cml_cmm_power_rail_t;
            description "Power rail for hot swap 1";
        } // END of hot-swap-1-power-rail definition.

        leaf hot-swap-2-power-rail  {
            type  ipi-platform-types:cml_cmm_power_rail_t;
            description "Power rail for hot swap 2";
        } // END of hot-swap-2-power-rail definition.

        leaf xp0r-v75-power-rail  {
            type  ipi-platform-types:cml_cmm_power_rail_t;
            description "Power status of XP0R 75V";
        } // END of xp0r-v75-power-rail definition.

        leaf xp1r-v07-cp-power-rail  {
            type  ipi-platform-types:cml_cmm_power_rail_t;
            description "Power status of XP1R 07V_CP";
        } // END of xp1r-v07-cp-power-rail definition.

    } // END of power-rail-state definition.

    grouping  power-rail-grouping {
    description
        "Container for power-rail component";
    container power-rail {
        if-feature feature-list:HAVE_CMMD;
        config false;
        description
            "Container for power-rail component";
        container state {
            config false;
            description
                "Operational state data for power-rail components";
            uses power-rail-state;
        } // END of state-container definition.
    } // END of power-rail-container definition.
    } // END of power-rail-grouping definition.


}
