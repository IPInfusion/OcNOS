/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-profile-hardware-l2vpn-instances-limits.yang
*
*/

submodule ipi-platform-profile-hardware-l2vpn-instances-limits {

    yang-version 1.1;

    belongs-to  ipi-platform { prefix ipi-platform; }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Hardware L2VPN instances limits and usage information";


    revision "2025-11-12" {
        description "Rename E-Line service to E-LINE in hardware-l2vpn-limits";
        reference " 0.1.2.";
    }

    revision "2025-10-26" {
        description "Add stream-telemetry yaml file";
        reference " 0.1.1.";
    }

    revision "2025-10-20" {
        description "Initial Version";
        reference " 0.1.0.";
    }



    typedef  platform_l2vpn_services_t {
        type enumeration {
            enum E-LAN {
                value 1;
                description "E-LAN service";
            }
            enum E-LINE {
                value 2;
                description "E-LINE Service";
            }
        }
        description "type definition for PLATFORM_L2VPN_SERVICES_T";
    }    grouping hardware-l2vpn-instances-limits-state {
        description
            "Attributes used for database capacity and usage";
        leaf capacity  {
            type  uint32;
            description "Maximum number of entries in the database";
        } // END of capacity definition.

        leaf used  {
            type  uint32;
            description "Number of entries in use in the database";
        } // END of used definition.

        leaf free  {
            type  uint32;
            description "Number of entries available in the database";
        } // END of free definition.

        leaf percentage  {
            type  uint8;
            units "%";
            description "Proportion of entries in use, expressed as a percentage";
        } // END of percentage definition.

    } // END of hardware-l2vpn-instances-limits-state definition.
    grouping l2vpn-services-state {
        description
            "L2VPN services attributes";
        leaf name  {
            type  platform_l2vpn_services_t;
            description "Service name";
        } // END of name definition.

    } // END of l2vpn-services-state definition.
    grouping l2vpn-services-top {
        description
            "L2VPN services information";
        container services {
            config false;
            description
                "Enclosing container for the services consuming L2VPN resources";

            list service {
                key "name";
                config false;
                description
                    "The list of services consuming L2VPN resources";
                leaf name  {
                    type  leafref {
                        path  "../state/name";
                    }
                    description "Service name";
                } // END of name definition.

                container state {
                    config false;
                    description
                        "Operational state data for L2VPN services";
                    uses l2vpn-services-state;
                    uses hardware-l2vpn-instances-limits-state;
                } // END of state-container definition.
            } // End of service-list
        } // END of services-container definition.
    } // END of l2vpn-services-top definition.
    grouping hardware-l2vpn-instances-limits-instances-top {
        description
            "L2VPN instances information";
        container instances {
            config false;
            description
                "Instances information";
            container state {
                config false;
                description
                    "Operational state data for the L2VPN instances capacity and usage";
                uses hardware-l2vpn-instances-limits-state;
            } // END of state-container definition.
            uses l2vpn-services-top;
        } // END of instances-container definition.
    } // END of hardware-l2vpn-instances-limits-instances-top definition.
    grouping hardware-l2vpn-instances-limits-vsi-top {
        description
            "VSI database";
        container vsi {
            config false;
            description
                "VSI database";
            container state {
                config false;
                description
                    "Operational state data for the VSI table capacity and usage";
                uses hardware-l2vpn-instances-limits-state;
            } // END of state-container definition.
            uses l2vpn-services-top;
        } // END of vsi-container definition.
    } // END of hardware-l2vpn-instances-limits-vsi-top definition.
    grouping hardware-l2vpn-instances-limits-mc-group-top {
        description
            "Multicast groups database";
        container multicast-groups {
            config false;
            description
                "Multicast groups database";
            container state {
                config false;
                description
                    "Operational state data for the Multicast groups hardware table
                            capacity and usage";
                uses hardware-l2vpn-instances-limits-state;
            } // END of state-container definition.
            uses l2vpn-services-top;
        } // END of multicast-groups-container definition.
    } // END of hardware-l2vpn-instances-limits-mc-group-top definition.

    grouping  hardware-l2vpn-instances-limits-grouping {
    description
        "Container for hardware L2VPN instances limits and usage attributes";
    container hardware-l2vpn-instances-limits {
        if-feature feature-list:HAVE_BROADCOM;
        if-feature feature-list:HAVE_DUNE;
        if-feature feature-list:HAVE_CMMD;
        config false;
        description
            "Container for hardware L2VPN instances limits and usage attributes";
        uses hardware-l2vpn-instances-limits-instances-top;
        uses hardware-l2vpn-instances-limits-vsi-top;
        uses hardware-l2vpn-instances-limits-mc-group-top;
    } // END of hardware-l2vpn-instances-limits-container definition.
    } // END of hardware-l2vpn-instances-limits-grouping definition.


}
