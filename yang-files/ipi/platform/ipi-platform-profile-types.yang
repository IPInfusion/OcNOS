/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-profile-types.yang
*
*/

module ipi-platform-profile-types {

    yang-version 1.1;

    namespace   "http://www.ipinfusion.com/yang/ocnos/ipi-platform-profile-types";

    prefix "ipi-platform-profile-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-platform-profile-types";


    revision "2026-04-16" {
        description "Added new cpu-queue mgmt under ltsw platform";
        reference " 0.3.5.";
    }

    revision "2026-03-23" {
        description "Making l3-slowpath/rsvd mc cpu queue configurable ";
        reference " 0.3.4.";
    }

    revision "2025-09-10" {
        description "Modification of CPU queues(PLATFORM_CPU_QUEUE_NAME_T) for XGS platform ";
        reference " 0.3.3.";
    }

    revision "2025-09-09" {
        description "Added sniff to CPU queue type";
        reference " 0.3.2.";
    }

    revision "2025-07-08" {
        description "Added support for hardware-profile eedb mode";
        reference " 0.3.1.";
    }

    revision "2025-07-03" {
        description "Added datatype for ingress-acl hardware-profile";
        reference " 0.3.0.";
    }

    revision "2025-04-07" {
        description "Added support for Speculative options for DPI";
        reference " 0.2.7.";
    }

    revision "2025-04-04" {
        description "Added mode2/mode3 for hardware-profile port mode for S9600-28dx/64x/56dx/32x";
        reference " 0.2.6.";
    }

    revision "2025-02-21" {
        description "removed mode2/mode3 for hardware-profile port mode for S9600-28dx/64x/56dx/32x";
        reference " 0.2.5.";
    }

    revision "2025-02-14" {
        description "Added support for hardware-profile port mode for S9610-46DX and 48DX";
        reference " 0.2.4.";
    }

    revision "2025-01-30" {
        description "Removed support for hardware-profile port mode for UFIS9510_28DC ";
        reference " 0.2.3.";
    }

    revision "2024-12-23" {
        description "Updated helpstring for AS9947-36xkb port-mode 2";
        reference " 0.2.2.";
    }

    revision "2024-11-06" {
        description "Removed support for hardware-profile port mode for TH5";
        reference " 0.2.1.";
    }

    revision "2024-10-18" {
        description "Added Tomahawk5";
        reference " 0.2.0.";
    }

    revision "2024-10-08" {
        description "Added enum type for load-balance cli";
        reference " 0.1.1.";
    }

    revision "2024-09-25" {
        description "Initial Version";
        reference " 0.1.0.";
    }



    typedef  platform_ufis9600_64x_port_mode_type_t {
        type enumeration {
            enum mode1 {
                value 1;
                description "64X100G (Default)";
            }
            enum mode2 {
                value 2;
                description "4X1G  + 63X100G (ce0 breakout to 4X1G)";
            }
            enum mode3 {
                value 3;
                description "4X10G + 63X100G (ce0 breakout to 4X10G)";
            }
            enum mode4 {
                value 4;
                description "4X25G + 63X100G (ce0 breakout to 4X25G)";
            }
        }
        description "type definition for PLATFORM_UFIS9600_64X_PORT_MODE_TYPE_T";
    }

    typedef  platform_loadbalance_type_t {
        type enumeration {
            enum symmetric {
                value 1;
                description "Symmetrical based load balancing";
            }
            enum non-symmetric {
                value 2;
                description "Non symmetrical based load balancing";
            }
        }
        description "type definition for PLATFORM_LOADBALANCE_TYPE_T";
    }

    typedef  platform_as7315_27x_port_mode_type_t {
        type enumeration {
            enum mode1 {
                value 1;
                description "20X10G + 4X25G + 3X100G (default)";
            }
            enum mode2 {
                value 2;
                description "20X10G + 4X25G + 12X25G";
            }
            enum mode3 {
                value 3;
                description "20X10G + 4X25G + 2X100G + 4X25G(ce2 breakout to 4X25G)";
            }
        }
        description "type definition for PLATFORM_AS7315_27X_PORT_MODE_TYPE_T";
    }

    typedef  platform_as5916_as5912_54x_port_mode_type_t {
        type enumeration {
            enum mode1 {
                value 1;
                description "48X10G + 6X100G (default)";
            }
            enum mode2 {
                value 2;
                description "48X10G + 24X25G";
            }
        }
        description "type definition for PLATFORM_AS5916_AS5912_54X_PORT_MODE_TYPE_T";
    }

    typedef  platform_as7316_26xb_port_mode_type_t {
        type enumeration {
            enum mode1 {
                value 1;
                description "16X10G + 8X25G + 2X100G (default)";
            }
            enum mode2 {
                value 2;
                description "16X10G + 8X25G + 8X25G";
            }
            enum mode3 {
                value 3;
                description "16X10G + 8X25G + 1X100G + 4X25G (ce0 breakout to 4X25G)";
            }
            enum mode4 {
                value 4;
                description "16X10G + 8X25G + 1X100G + 4X25G (ce1 breakout to 4X25G)";
            }
        }
        description "type definition for PLATFORM_AS7316_26XB_PORT_MODE_TYPE_T";
    }

    typedef  platform_s9500_30xs_port_mode_type_t {
        type enumeration {
            enum mode1 {
                value 1;
                description "20X10G + 8X25G + 2X100G (default)";
            }
            enum mode2 {
                value 2;
                description "20X10G + 8X25G + 8X25G";
            }
            enum mode3 {
                value 3;
                description "20X10G + 8X25G + 1X100G + 4X25G(ce0 breakout to 4X25G)";
            }
            enum mode4 {
                value 4;
                description "20X10G + 8X25G + 1X100G + 4X25G(ce1 breakout to 4X25G)";
            }
        }
        description "type definition for PLATFORM_S9500_30XS_PORT_MODE_TYPE_T";
    }

    typedef  platform_ufis9600_32x_port_mode_type_t {
        type enumeration {
            enum mode1 {
                value 1;
                description "32X100G (Default)";
            }
            enum mode2 {
                value 2;
                description "4X1G  + 31X100G (ce0 breakout to 4X1G)";
            }
            enum mode3 {
                value 3;
                description "4X10G + 31X100G (ce0 breakout to 4X10G)";
            }
            enum mode4 {
                value 4;
                description "4X25G + 31X100G (ce0 breakout to 4X25G)";
            }
        }
        description "type definition for PLATFORM_UFIS9600_32X_PORT_MODE_TYPE_T";
    }

    typedef  platform_ufis9600_56dx_port_mode_type_t {
        type enumeration {
            enum mode1 {
                value 1;
                description "8X400Gb + 48X100G (Default)";
            }
            enum mode2 {
                value 2;
                description "8X400Gb + 4X1G  + 47X100G (ce0 breakout to 4X1G)";
            }
            enum mode3 {
                value 3;
                description "8X400Gb + 4X10G + 47X100G (ce0 breakout to 4X10G)";
            }
            enum mode4 {
                value 4;
                description "8X400Gb + 4X25G + 47X100G (ce0 breakout to 4X25G)";
            }
        }
        description "type definition for PLATFORM_UFIS9600_56DX_PORT_MODE_TYPE_T";
    }

    typedef  platform_ufis9600_28dx_port_mode_type_t {
        type enumeration {
            enum mode1 {
                value 1;
                description "4X400Gb + 24X100G (Default)";
            }
            enum mode2 {
                value 2;
                description "4X400Gb + 4X1G  + 23X100G (ce0 breakout to 4X1G)";
            }
            enum mode3 {
                value 3;
                description "4X400Gb + 4X10G + 23X100G (ce0 breakout to 4X10G)";
            }
            enum mode4 {
                value 4;
                description "4X400Gb + 4X25G + 23X100G (ce0 breakout to 4X25G)";
            }
        }
        description "type definition for PLATFORM_UFIS9600_28DX_PORT_MODE_TYPE_T";
    }

    typedef  platform_ufis9610_36d_port_mode_type_t {
        type enumeration {
            enum mode1 {
                value 1;
                description "36X400G (Default : Without KBP)";
            }
            enum mode2 {
                value 2;
                description "32X400G With KBP Support";
            }
        }
        description "type definition for PLATFORM_UFIS9610_36D_PORT_MODE_TYPE_T";
    }

    typedef  platform_ufis9610_46dx_port_mode_type_t {
        type enumeration {
            enum mode1 {
                value 1;
                description "6X400G + 40X100G (Default)";
            }
            enum mode2 {
                value 2;
                description "6X400G  + 38X100G + 4x25G";
            }
        }
        description "type definition for PLATFORM_UFIS9610_46DX_PORT_MODE_TYPE_T";
    }

    typedef  platform_ufis9610_48dx_port_mode_type_t {
        type enumeration {
            enum mode1 {
                value 1;
                description "8X400G + 40X100G (Default)";
            }
            enum mode2 {
                value 2;
                description "8X400G  + 38X100G + 4x25G";
            }
        }
        description "type definition for PLATFORM_UFIS9610_48DX_PORT_MODE_TYPE_T";
    }

    typedef  platform_qos_queue_profile_type_t {
        type enumeration {
            enum profile1 {
                value 1;
                description "supported new 4 queue-bundle per service (default)";
            }
            enum profile2 {
                value 2;
                description "supported new 8 queue-bundle per service";
            }
        }
        description "type definition for PLATFORM_QOS_QUEUE_PROFILE_TYPE_T";
    }

    typedef  platform_kaps_profile_type_t {
        type enumeration {
            enum profile-one {
                value 1;
                description "select kaps profile one";
            }
            enum profile-two {
                value 2;
                description "select kaps profile two";
            }
        }
        description "type definition for PLATFORM_KAPS_PROFILE_TYPE_T";
    }

    typedef  platform_ext_tcam_profile_type_t {
        type enumeration {
            enum profile-one {
                value 3;
                description "select elk-tcam profile one";
            }
            enum profile-two {
                value 4;
                description "select elk-tcam profile two";
            }
            enum profile-three {
                value 5;
                description "select elk-tcam profile three";
            }
        }
        description "type definition for PLATFORM_EXT_TCAM_PROFILE_TYPE_T";
    }

    typedef  platform_aclif_type_t {
        type enumeration {
            enum failover {
                value 1;
                description "Configure failover";
            }
            enum no-failover {
                value 2;
                description "Configiure no failover";
            }
        }
        description "type definition for PLATFORM_ACLIF_TYPE_T";
    }

    typedef  platform_tcam_custom_profile_t {
        type enumeration {
            enum custom-profile {
                value 6;
                description "define elk-tcam custom profile";
            }
        }
        description "type definition for PLATFORM_TCAM_CUSTOM_PROFILE_T";
    }

    typedef  platform_kaps_forwading_profile_t {
        type enumeration {
            enum kaps-profile-one {
                value 9;
                description "kaps,profile one";
            }
            enum kaps-profile-two {
                value 10;
                description "kaps,profile two";
            }
        }
        description "type definition for PLATFORM_KAPS_FORWADING_PROFILE_T";
    }

    typedef  platform_ing_acl_stat {
        type enumeration {
            enum disable {
                value 0;
                description "Disable";
            }
            enum enable {
                value 1;
                description "Enable";
            }
        }
        description "type definition for PLATFORM_ING_ACL_STAT";
    }

    typedef  platform_elk_tcam_forwading_profile_t {
        type enumeration {
            enum elk-tcam-profile-one {
                value 11;
                description "elk-tcam,profile one";
            }
            enum elk-tcam-profile-two {
                value 12;
                description "elk-tcam,profile two";
            }
            enum elk-tcam-profile-three {
                value 13;
                description "elk-tcam,profile three";
            }
        }
        description "type definition for PLATFORM_ELK_TCAM_FORWADING_PROFILE_T";
    }

    typedef  platform_cpu_queue_name_t {
        type enumeration {
            enum mgmt-route-leak {
                value 33;
                if-feature feature-list:HAVE_DUNE;
                description "mgmt-route-leak queue parameters";
            }
            enum icmp-redirect {
                value 34;
                if-feature feature-list:HAVE_DUNE;
                description "ICMP-redirect queue parameters";
            }
            enum cfm {
                value 36;
                if-feature feature-list:HAVE_DUNE;
                description "CFM Error queue parameters";
            }
            enum cpu.q0 {
                if-feature feature-list:HAVE_DUNE;
                description "cpu.q0";
            }
            enum best-effort {
                if-feature feature-list:HAVE_CUSTOM5_QOS;
                description "Best-effort queue parameters";
            }
            enum cpu-queue-0 {
                if-feature feature-list:NOT_HAVE_DUNE;
                if-feature feature-list:NOT_HAVE_MARVELL;
                if-feature feature-list:NOT_HAVE_CUSTOM5_QOS;
                description "Best-effort queue(cpu.q0) parameters";
            }
            enum cpu.q1 {
                if-feature feature-list:HAVE_DUNE;
                description "cpu.q1";
            }
            enum cpu-queue-1 {
                if-feature feature-list:NOT_HAVE_DUNE;
                if-feature feature-list:NOT_HAVE_MARVELL;
                if-feature feature-list:NOT_HAVE_CUSTOM5_QOS;
                description "cpu.q1 parameters";
            }
            enum cpu.q2 {
                if-feature feature-list:HAVE_DUNE;
                description "cpu.q2";
            }
            enum cpu-queue-2 {
                if-feature feature-list:NOT_HAVE_DUNE;
                if-feature feature-list:NOT_HAVE_MARVELL;
                if-feature feature-list:NOT_HAVE_CUSTOM5_QOS;
                description "cpu.q2 parameters";
            }
            enum cpu.q3 {
                if-feature feature-list:HAVE_DUNE;
                description "cpu.q3";
            }
            enum cpu-queue-3 {
                if-feature feature-list:NOT_HAVE_DUNE;
                if-feature feature-list:NOT_HAVE_MARVELL;
                if-feature feature-list:NOT_HAVE_CUSTOM5_QOS;
                description "cpu.q3 parameters";
            }
            enum cpu.q4 {
                if-feature feature-list:HAVE_DUNE;
                description "cpu.q4";
            }
            enum ipmc-miss {
                if-feature feature-list:HAVE_CUSTOM5_QOS;
                description "IPMC-Miss  queue parameters";
            }
            enum cpu-queue-4 {
                if-feature feature-list:NOT_HAVE_DUNE;
                if-feature feature-list:NOT_HAVE_MARVELL;
                if-feature feature-list:NOT_HAVE_CUSTOM5_QOS;
                description "cpu.q4 parameters";
            }
            enum cpu.q5 {
                if-feature feature-list:HAVE_DUNE;
                description "cpu.q5";
            }
            enum l3-miss {
                if-feature feature-list:HAVE_CUSTOM5_QOS;
                description "L3-Miss queue parameters";
            }
            enum cpu-queue-5 {
                if-feature feature-list:NOT_HAVE_DUNE;
                if-feature feature-list:NOT_HAVE_MARVELL;
                if-feature feature-list:NOT_HAVE_CUSTOM5_QOS;
                description "MPLS queue parameters (For GAL label mpls oam packets) or cpu.q5 parameters";
            }
            enum cpu.q6 {
                if-feature feature-list:HAVE_DUNE;
                description "cpu.q6";
            }
            enum cpu-queue-6 {
                if-feature feature-list:NOT_HAVE_DUNE;
                if-feature feature-list:NOT_HAVE_MARVELL;
                if-feature feature-list:NOT_HAVE_CUSTOM5_QOS;
                description "cpu.q6 parameters";
            }
            enum cpu.q7 {
                if-feature feature-list:HAVE_DUNE;
                description "cpu.q7";
            }
            enum ipmc-reserved {
                if-feature feature-list:HAVE_CUSTOM5_QOS;
                description "ipmc-reserved parameters";
            }
            enum cpu-queue-7 {
                if-feature feature-list:NOT_HAVE_DUNE;
                if-feature feature-list:NOT_HAVE_MARVELL;
                if-feature feature-list:NOT_HAVE_CUSTOM5_QOS;
                description "cpu.q7 parameters";
            }
            enum igmp {
                if-feature feature-list:HAVE_MARVELL;
                description "IGMP queue parameters";
            }
            enum l3-slowpath {
                if-feature feature-list:HAVE_CUSTOM5_QOS;
                description "l3-slowpath parameters";
            }
            enum isis {
                if-feature feature-list:HAVE_MARVELL;
                if-feature feature-list:HAVE_ISISD;
                description "ISIS queue parameters";
            }
            enum sflow {
                if-feature feature-list:HAVE_SFLOW;
                if-feature feature-list:HAVE_CUSTOM5_QOS;
                description "SFLOW queue parameters";
            }
            enum reserved-mc {
                if-feature feature-list:HAVE_MARVELL;
                description "reserved-mc queue parameters";
            }
            enum bgp {
                if-feature feature-list:HAVE_BGPD;
                if-feature feature-list:HAVE_CUSTOM5_QOS;
                description "BGP queue parameters";
            }
            enum link-local {
                if-feature feature-list:HAVE_MARVELL;
                description "Link-local  queue parameters";
            }
            enum vrrp {
                if-feature feature-list:HAVE_VRRPD;
                if-feature feature-list:HAVE_CUSTOM5_QOS;
                description "VRRP queue parameters";
            }
            enum ospf {
                if-feature feature-list:HAVE_MARVELL;
                if-feature feature-list:HAVE_OSPFD;
                description "OSPF queue parameters";
            }
            enum ldp-rsvp {
                if-feature feature-list:HAVE_MPLS;
                if-feature feature-list:HAVE_CUSTOM5_QOS;
                description "LDP-RSVP queue parameters";
            }
            enum rip {
                if-feature feature-list:HAVE_RIPD;
                if-feature feature-list:HAVE_CUSTOM5_QOS;
                description "RIP queue parameters";
            }
            enum rsvp-ldp {
                if-feature feature-list:HAVE_MARVELL;
                if-feature feature-list:HAVE_MPLS;
                description "RSVP/LDP queue parameters";
            }
            enum vrrp-rip-dhcp {
                if-feature feature-list:HAVE_MARVELL;
                description "VRRP/RIP/DHCP queue parameters";
            }
            enum dhcp {
                if-feature feature-list:HAVE_CUSTOM5_QOS;
                description "DHCP queue parameters";
            }
            enum pim {
                if-feature feature-list:HAVE_MARVELL;
                if-feature feature-list:HAVE_PIMD;
                description "PIM queue parameters";
            }
            enum nd {
                if-feature feature-list:HAVE_IPV6;
                if-feature feature-list:HAVE_CUSTOM5_QOS;
                description "ND queue parameters";
            }
            enum icmp {
                if-feature feature-list:HAVE_MARVELL;
                description "ICMP queue parameters";
            }
            enum mpls {
                if-feature feature-list:HAVE_MPLS;
                if-feature feature-list:HAVE_CUSTOM5_QOS;
                description "MPLS queue parameters (For GAL label mpls oam packets)";
            }
            enum arp {
                if-feature feature-list:HAVE_MARVELL;
                description "ARP queue parameters";
            }
            enum bpdu {
                if-feature feature-list:HAVE_MARVELL;
                description "BPDU queue parameters";
            }
            enum oamp {
                if-feature feature-list:HAVE_MARVELL;
                description "OAMP queue parameters";
            }
            enum ccm {
                if-feature feature-list:HAVE_CFM;
                if-feature feature-list:HAVE_CUSTOM5_QOS;
                description "CCM queue parameters";
            }
            enum bfd {
                if-feature feature-list:HAVE_BFD;
                if-feature feature-list:HAVE_CUSTOM5_QOS;
                description "BFD queue parameters";
            }
            enum ptp {
                if-feature feature-list:HAVE_PTPD;
                if-feature feature-list:HAVE_CUSTOM5_QOS;
                description "PTP queue parameters";
            }
            enum trill-isis {
                if-feature feature-list:HAVE_TRILLD;
                if-feature feature-list:HAVE_CUSTOM5_QOS;
                description "TRILL queue parameters";
            }
            enum acl {
                if-feature feature-list:NOT_HAVE_DUNE;
                if-feature feature-list:NOT_HAVE_MARVELL;
                if-feature feature-list:NOT_HAVE_CUSTOM5_QOS;
                description "ACL queue parameters (for acl logging)";
            }
            enum vxlan {
                if-feature feature-list:HAVE_VXLAN;
                if-feature feature-list:NOT_HAVE_DUNE;
                if-feature feature-list:NOT_HAVE_MARVELL;
                if-feature feature-list:NOT_HAVE_CUSTOM5_QOS;
                description "VXLAN queue parameters";
            }
            enum dsp {
                if-feature feature-list:HAVE_DUNE;
                description "DSP queue parameters";
            }
            enum evpn {
                if-feature feature-list:HAVE_DUNE;
                if-feature feature-list:HAVE_BGP_EVPN;
                description "EVPN queue parameters";
            }
            enum nhop {
                if-feature feature-list:HAVE_DUNE;
                description "nhop queue parameters";
            }
            enum guest {
                if-feature feature-list:HAVE_DUNE;
                if-feature feature-list:HAVE_GUEST_VM;
                description "Guest queue parameters";
            }
            enum mgmt {
                if-feature feature-list:HAVE_CUSTOM5_QOS;
                description "Mgmt traffic parameters(eg. ssh/telnet/snmp/netconf ssh and tls)";
            }
            enum sniff {
                if-feature feature-list:HAVE_ADVANCE_MIRROR;
                if-feature feature-list:HAVE_SNIFF_INTF;
                if-feature feature-list:NOT_HAVE_DUNE;
                if-feature feature-list:NOT_HAVE_MARVELL;
                if-feature feature-list:NOT_HAVE_CUSTOM5_QOS;
                description "Sniff queue parameters";
            }
        }
        description "type definition for PLATFORM_CPU_QUEUE_NAME_T";
    }

    typedef  platform_cpu_queue_monitor_t {
        type enumeration {
            enum no-monitor {
                value 0;
                description "do not monitor cpu queue usage";
            }
            enum monitor {
                value 1;
                description "monitor cpu queue usage";
            }
        }
        description "type definition for PLATFORM_CPU_QUEUE_MONITOR_T";
    }

    typedef  platform_load_trill_t {
        type enumeration {
            enum outer-l2 {
                value 1;
                description "TRILL outer l2 header (outer SMAC or outer DMAC or outer VLAN)";
            }
            enum inner-l2 {
                value 2;
                description "TRILL inner l2 header (inner SMAC or inner DMAC or inner VLAN or trill tunnel)";
            }
            enum inner-l3 {
                value 3;
                description "TRILL inner l3 header (inner SIP or inner DIP or L4 srx/dest port)";
            }
        }
        description "type definition for PLATFORM_LOAD_TRILL_T";
    }

    typedef  platform_load_hash_t {
        type enumeration {
            enum crc16-bisync {
                value 0;
                description "16-bit CRC16 using the BISYNC Polynomial (DEFAULT)";
            }
            enum crc16-ccitt {
                value 1;
                description "16-bit CRC16 using the CCITT Polynomial";
            }
            enum crc32-lo {
                value 2;
                description "16 LSBs of computated CRC32";
            }
            enum crc32-hi {
                value 3;
                description "16 MSBs of computated CRC32";
            }
        }
        description "type definition for PLATFORM_LOAD_HASH_T";
    }

    typedef  platform_lacp_psc_t {
        type enumeration {
            enum dst-mac {
                value 1;
                description "Destination Mac address based load balancing";
            }
            enum src-mac {
                value 2;
                description "Source Mac address based load balancing";
            }
            enum src-dst-mac {
                value 3;
                description "Source and Destination Mac address based load balancing";
            }
            enum src-ip {
                value 4;
                description "Source IP address based load balancing";
            }
            enum dst-ip {
                value 5;
                description "Destination IP address based load balancing";
            }
            enum src-dst-ip {
                value 6;
                description "Source and Destination IP address based load balancing";
            }
            enum rtag7 {
                value 13;
                description "rtag7 hashing based on pkt type";
            }
        }
        description "type definition for PLATFORM_LACP_PSC_T";
    }

    typedef  platform_forwarding_profile_t {
        type enumeration {
            enum l2-profile-one {
                value 0;
                description "L2 profile One";
            }
            enum l2-profile-two {
                value 1;
                description "L2 profile Two";
            }
            enum l2-profile-three {
                value 2;
                description "L2 profile Three (default)";
            }
            enum l3-profile {
                value 3;
                description "L3 profile";
            }
            enum l3-128bit-profile {
                value 4;
                description "L3 profile with 128 bit prefix support";
            }
            enum lpm-profile {
                value 5;
                description "LPM profile (not supported on Helix4)";
            }
            enum lpm-128bit-profile {
                value 6;
                description "LPM profile with 128 bit prefix support (supported on Tomahawk and
                    Tomahawk2)";
            }
            enum custom-profile {
                value 8;
                description "custom profile (supported on Tomahawk - Tomahawk2 and Helix4)";
            }
        }
        description "type definition for PLATFORM_FORWARDING_PROFILE_T";
    }

    typedef  platform_forwarding_profile_route_mode_t {
        type enumeration {
            enum narrow {
                value 0;
                description "Reduced Data mode ";
            }
            enum wide {
                value 1;
                description "Full Data mode (default)";
            }
        }
        description "type definition for PLATFORM_FORWARDING_PROFILE_ROUTE_MODE_T";
    }

    typedef  platform_lpm_custom_profile_t {
        type enumeration {
            enum 2 {
                value 2;
                description "Two banks for lpm and Remaining banks can be used by any";
            }
        }
        description "type definition for PLATFORM_LPM_CUSTOM_PROFILE_T";
    }

    typedef  platform_cpu_queue_lossy_t {
        type enumeration {
            enum lossless {
                value 0;
                description "Configure cpu queue as lossless";
            }
            enum lossy {
                value 1;
                description "Configure cpu queue as lossy";
            }
        }
        description "type definition for PLATFORM_CPU_QUEUE_LOSSY_T";
    }

    typedef  platform_mdb_profile_t {
        type enumeration {
            enum balanced {
                value 0;
                description "select mdb profile balanced";
            }
            enum balanced-p-and-p {
                value 1;
                description "select mdb profile balanced-p-and-p";
            }
            enum l2-xl {
                value 2;
                description "select mdb profile l2-xl";
            }
            enum l3-xl {
                value 3;
                description "select mdb profile l3-xl";
            }
            enum balanced-extended {
                value 4;
                description "select mdb profile balanced-extended";
            }
        }
        description "type definition for PLATFORM_MDB_PROFILE_T";
    }

    typedef  platform_mdb_kaps_type_t {
        type enumeration {
            enum 1 {
                value 1;
                description "kaps cfg 1";
            }
        }
        description "type definition for PLATFORM_MDB_KAPS_TYPE_T";
    }

    typedef  platform_voq_scale_type_t {
        type enumeration {
            enum full {
                value 1;
                description "VOQ scale full (default)";
            }
            enum half {
                value 2;
                description "VOQ scale half";
            }
        }
        description "type definition for PLATFORM_VOQ_SCALE_TYPE_T";
    }

    typedef  platform_soc_type_t {
        type enumeration {
            enum qax {
                value 0;
                description "QAX SOC";
            }
            enum qux {
                value 1;
                description "QUX SOC";
            }
            enum qmx {
                value 2;
                description "QMX SOC";
            }
            enum dnx {
                value 3;
                description "DNX SOC";
            }
            enum tomahawk {
                value 4;
                description "Tomahawk SOC";
            }
            enum tomahawk2 {
                value 5;
                description "Tomahawk2 SOC";
            }
            enum tomahawk3 {
                value 6;
                description "Tomahawk3 SOC";
            }
            enum tomahawkplus {
                value 7;
                description "TomahawkPlus SOC";
            }
            enum trident2 {
                value 8;
                description "Trident2 SOC";
            }
            enum trident2plus {
                value 9;
                description "Trident2Plus SOC";
            }
            enum trident3 {
                value 10;
                description "Trident3 SOC";
            }
            enum helix4 {
                value 11;
                description "Helix4 SOC";
            }
            enum saber2 {
                value 12;
                description "Saber2 SOC";
            }
            enum maverick2 {
                value 13;
                description "Maverick2 SOC";
            }
            enum hurricane4 {
                value 14;
                description "Hurricane4 SOC";
            }
            enum trident4 {
                value 15;
                description "Trident4 SOC";
            }
            enum tomahawk4 {
                value 16;
                description "Tomahawk4 SOC";
            }
            enum tomahawk5 {
                value 17;
                description "Tomahawk5 SOC";
            }
            enum unknown {
                value 18;
                description "Unknown";
            }
        }
        description "type definition for PLATFORM_SOC_TYPE_T";
    }

    typedef  platform_system_status_type_t {
        type enumeration {
            enum Normal {
                value 1;
                description "Status is normal";
            }
            enum Minor-Fault {
                value 2;
                description "Status is Minor Fault,Fault";
            }
            enum Major-Fault {
                value 3;
                description "Status is Major Fault,Fault";
            }
        }
        description "type definition for PLATFORM_SYSTEM_STATUS_TYPE_T";
    }

    typedef  platform_bgp_flowspec_mode_t {
        type enumeration {
            enum install-all {
                value 1;
                description "FLOWSPEC rules are prioritized. The all rules already installed are reinstalled when a new rule is tried to add.";
            }
            enum install-partial {
                value 2;
                description "FLOWSPEC rules are prioritized. Install not all rules already installed if possible to avoid unnecessarily reinstalling rules.";
            }
            enum no-prioritizing {
                value 3;
                description "FLOWSPEC rules are not prioritized. Install only rules requested to add but not reinstall any other rules when a new rule is tried to add.";
            }
        }
        description "type definition for PLATFORM_BGP_FLOWSPEC_MODE_T";
    }

    typedef  cml_voq_full_color_fwd_drop_t {
        type enumeration {
            enum voq-full-color {
                value 1;
                description "stats for all voq counters";
            }
            enum voq-fwd-drop {
                value 2;
                description "stats for fwd drop voq counters";
            }
        }
        description "type definition for CML_VOQ_FULL_COLOR_FWD_DROP_T";
    }

    typedef  platform_load_balance_mpls_inner_stack_t {
        type bits {
            bit inner-ipv4 {
                position 0;
                description "L3VPN Inner-IPv4";
            }
            bit inner-ipv4-inner-l4 {
                position 1;
                description "L3VPN Inner-IPv4,Inner-L4";
            }
            bit inner-ipv6 {
                position 2;
                description "L3VPN Inner-IPv6";
            }
            bit inner-ipv6-inner-l4 {
                position 3;
                description "L3VPN Inner-IPv6,Inner-L4";
            }
            bit inner-eth {
                position 4;
                description "Inner Ethernet";
            }
        }
        description "type definition for PLATFORM_LOAD_BALANCE_MPLS_INNER_STACK_T";
    }

    typedef  platform_as9947_36kbx_port_mode_type_t {
        type enumeration {
            enum mode1 {
                value 1;
                description "12X400G + 24X100G (default)";
            }
            enum mode2 {
                value 2;
                description "12X400G + 22x100G + 4x10G";
            }
        }
        description "type definition for PLATFORM_AS9947_36KBX_PORT_MODE_TYPE_T";
    }

    typedef  platform_parser_type_t {
        type enumeration {
            enum disable {
                value 1;
                description "maps the nibble to No Speculation";
            }
            enum cw {
                value 2;
                description "maps nibble to Control-Word";
            }
        }
        description "type definition for PLATFORM_PARSER_TYPE_T";
    }

    typedef  platform_eedb_mode_t {
        type enumeration {
            enum mode1 {
                value 1;
                description "Default mode";
            }
            enum mode2 {
                value 2;
                description "Large MPLS network";
            }
        }
        description "type definition for PLATFORM_EEDB_MODE_T";
    }

}
