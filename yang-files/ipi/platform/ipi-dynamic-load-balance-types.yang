/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dynamic-load-balance-types.yang
*
*/

module ipi-dynamic-load-balance-types {

    yang-version 1.1;

    namespace   "http://www.ipinfusion.com/yang/ocnos/ipi-dynamic-load-balance-types";

    prefix "ipi-dynamic-load-balance-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Dynamic load balance types";


    revision "2025-06-02" {
        description "Removed flow set sizes 64 and 128";
        reference " 0.1.2.";
    }

    revision "2025-05-20" {
        description "Added HAVE_AI_ML and HAVE_DLB feature flags";
        reference " 0.1.1.";
    }

    revision "2025-02-28" {
        description "Initial Version";
        reference " 0.1.0.";
    }



    typedef  dlb_flowset_size_t {
        type enumeration {
            enum 256 {
                value 256;
                description "Flowset size 256";
            }
            enum 512 {
                value 512;
                description "Flowset size 512";
            }
            enum 1024 {
                value 1024;
                description "Flowset size 1024";
            }
            enum 2048 {
                value 2048;
                description "Flowset size 2048";
            }
            enum 4096 {
                value 4096;
                description "Flowset size 4096";
            }
            enum 8192 {
                value 8192;
                description "Flowset size 8192";
            }
            enum 16384 {
                value 16384;
                description "Flowset size 16384";
            }
            enum 32768 {
                value 32768;
                description "Flowset size 32768";
            }
        }
        description "type definition for DLB_FLOWSET_SIZE_T";
    }

    typedef  dlb_mode_t {
        type enumeration {
            enum optimal-flow {
                value 1;
                if-feature feature-list:HAVE_DLB;
                description "dlb mode optimal-flow";
            }
            enum fixed {
                value 2;
                if-feature feature-list:HAVE_DLB;
                description "dlb mode fixed";
            }
            enum per-packet {
                value 3;
                if-feature feature-list:HAVE_DLB;
                description "dlb mode per-packet";
            }
            enum random-flow {
                value 4;
                if-feature feature-list:HAVE_DLB;
                description "dlb mode random-flow";
            }
            enum reactive-path-rebalance {
                value 5;
                if-feature feature-list:HAVE_AI_ML;
                description "dlb reactive-path-rebalance";
            }
        }
        description "type definition for DLB_MODE_T";
    }

}
