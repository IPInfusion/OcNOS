/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform.yang
*
*/

module ipi-platform {

    yang-version 1.1;

    namespace   "http://www.ipinfusion.com/yang/ocnos/ipi-platform";

    prefix "ipi-platform";

    import ipi-interface {
        prefix ipi-interface;
        revision-date 2026-03-10;
    }

    import ipi-platform-types {
        prefix ipi-platform-types;
        revision-date 2026-04-16;
    }

    import ipi-platform-profile-types {
        prefix ipi-platform-profile-types;
        revision-date 2026-04-16;
    }

    import ipi-platform-transceiver-types {
        prefix ipi-platform-transceiver-types;
        revision-date 2025-12-30;
    }

    import ipi-platform-transceiver-tibit-types {
        prefix ipi-platform-transceiver-tibit-types;
        revision-date 2022-07-14;
    }

    import ipi-platform-cmis-types {
        prefix ipi-platform-cmis-types;
        revision-date 2026-02-18;
    }

    import ietf-yang-types {
        prefix yang;
        revision-date 2013-07-15;
    }

    import cml-data-types {
        prefix cml-data-types;
        revision-date 2026-05-15;
    }

    import ipi-platform-sff8024-types {
        prefix ipi-platform-sff8024-types;
        revision-date 2026-01-06;
    }

    import feature-list {
        prefix feature-list;
        revision-date 2026-09-15;
    }

    include ipi-platform-dpll { revision-date 2024-07-01;}
    include ipi-platform-gps { revision-date 2024-07-01;}
    include ipi-platform-temperature { revision-date 2023-10-04;}
    include ipi-platform-cpu { revision-date 2023-06-12;}
    include ipi-platform-storage { revision-date 2024-12-10;}
    include ipi-platform-ram { revision-date 2023-06-12;}
    include ipi-platform-transceiver { revision-date 2026-01-27;}
    include ipi-platform-power-supply { revision-date 2026-01-02;}
    include ipi-platform-fan { revision-date 2025-06-27;}
    include ipi-platform-fan-tray { revision-date 2026-01-02;}
    include ipi-platform-chassis { revision-date 2023-12-16;}
    include ipi-platform-linecard { revision-date 2022-06-01;}
    include ipi-platform-power-rail { revision-date 2022-06-01;}
    include ipi-platform-ceragon { revision-date 2023-08-31;}
    include ipi-platform-edfa { revision-date 2023-04-11;}
    include ipi-platform-smart-sfp { revision-date 2025-07-31;}
    include ipi-platform-profile { revision-date 2026-08-14;}
    include ipi-platform-profile-extended { revision-date 2025-07-01;}
    include ipi-platform-profile-hardware-routing-limits { revision-date 2025-10-20;}
    include ipi-platform-profile-hardware-l2vpn-instances-limits { revision-date 2025-11-12;}
    include ipi-platform-cmis { revision-date 2025-09-24;}
    include ipi-platform-transceiver-tibit { revision-date 2022-07-14;}
    organization
        "IP Infusion Inc.";

    contact
        "Address: 3965 Freedom Circle, Suite 200, Santa Clara, CA 95054
         Phone: +1 408-400-1900
         E-mail: support@ipinfusion.com
         Web: http://www.ipinfusion.com/";

    description
        "This module defines a data model for representing a system
                component inventory, which can include hardware or software
                elements arranged in an arbitrary structure. The primary
                relationship supported by the model is containment, e.g.,
                components containing subcomponents.";


    revision "2026-08-14" {
        description "Added kbp-disable command to all kbp platforms";
        reference " 0.31.15.";
    }

    revision "2026-05-27" {
        description "Added new phyport mode plus disable cli command";
        reference " 0.31.14.";
    }

    revision "2026-04-16" {
        description "Added new cpu-queue mgmt under ltsw platform";
        reference " 0.31.13.";
    }

    revision "2026-03-23" {
        description "Making l3-slowpath/rsvd mc cpu queue configurable ";
        reference " 0.31.12.";
    }

    revision "2026-02-18" {
        description "CMIS: Added undefined interface, modulation and bit rate types";
        reference " 0.31.11.";
    }

    revision "2026-02-12" {
        description "Handled twamp-ipv4 disable command for Q2 ";
        reference " 0.31.10.";
    }

    revision "2026-02-09" {
        description "changed the config sequence for twamp-ipv4 and qos-policer ";
        reference " 0.31.9.";
    }

    revision "2026-01-27" {
        description "Display transceiver mapping attributes conditionally with the feature XCVR_MODEL";
        reference " 0.31.8.";
    }

    revision "2026-01-07" {
        description "Transceiver: Add 'Invalid' connector type";
        reference " 0.31.7.";
    }

    revision "2026-01-06" {
        description "Disable unset of twamp-ipv6-mpls on Q2 ";
        reference " 0.31.4.";
    }

    revision "2026-01-02" {
        description "Changed PSU and Fan remove notifications to absent keyword.";
        reference " 0.31.3.";
    }

    revision "2025-12-30" {
        description "Update transceiver identifier lists";
        reference " 0.31.2.";
    }

    revision "2025-12-26" {
        description "Given support to enable/disable ingress v6 group for LTSW platform";
        reference " 0.30.40.";
    }

    revision "2025-12-13" {
        description "Remove the not supported ipv6-bgp-flowspec filter creation";
        reference " 0.30.39.";
    }

    revision "2025-12-12" {
        description "Transceiver: Add QSFP-DD and OSFP transceiver. Remove unknown type.";
        reference " 0.31.0.";
    }

    revision "2025-11-13" {
        description "added new group for to get filters stats with unit/core";
        reference " 0.30.38.";
    }

    revision "2025-11-12" {
        description "Rename E-Line service to E-LINE in hardware-l2vpn-limits";
        reference " 0.30.37.";
    }

    revision "2025-11-06" {
        description "Added wavelength and wavelength tolerance attributes";
        reference " 0.30.36.";
    }

    revision "2025-10-31" {
        description "Added dependentObject for filter disable case";
        reference " 0.30.35.";
    }

    revision "2025-10-30" {
        description "moving profile ingress-mirror to the last in the order";
        reference " 0.30.34.";
    }

    revision "2025-10-26" {
        description "Add stream-telemetry yaml file into hardware-l2vpn-limits";
        reference " 0.30.33.";
    }

    revision "2025-10-23" {
        description "Disabled creating twamp-ipv6-mpls group on Q2 platforms. It is only required on Q1 platforms. ";
        reference " 0.35.32.";
    }

    revision "2025-10-20" {
        description "Renamed hardware-capacity container to hardware-routing-limits and added new hardware-l2vpn-instances state container";
        reference " 0.35.31.";
    }

    revision "2025-10-14" {
        description "CMIS: Added Infinera custom media interface type";
        reference " 0.35.30.";
    }

    revision "2025-10-07" {
        description "Modified the cli command supporting platforms";
        reference " 0.35.29.";
    }

    revision "2025-09-25" {
        description "Adding the OSFP 8X identifier code to the SFF8024 types file";
        reference " 0.35.28.";
    }

    revision "2025-09-24" {
        description "Add 4 new attributes in advertisement/controls/state";
        reference " 0.35.27.";
    }

    revision "2025-09-23" {
        description "CMIS: Added WTD RTXM600-411 custom interface types";
        reference " 0.35.26.";
    }

    revision "2025-09-16" {
        description "updated the helpstring for evpn-mpls-mh prependstr";
        reference " 0.35.25.";
    }

    revision "2025-09-13" {
        description "Add gnmi support to the hardware-capacity counters";
        reference " 0.35.24.";
    }

    revision "2025-09-12" {
        description "Add hardware-capacity state container";
        reference " 0.35.23.";
    }

    revision "2025-09-11" {
        description "Update cli string from evpn-mpls-mh hw filter to evpn-nw-ac";
        reference " 0.35.22.";
    }

    revision "2025-09-10" {
        description "Modification of CPU queues(PLATFORM_CPU_QUEUE_NAME_T) for XGS platform ";
        reference " 0.35.21.";
    }

    revision "2025-09-09" {
        description "Added sniff to CPU queue type";
        reference " 0.35.20.";
    }

    revision "2025-09-05" {
        description "Streaming Telemetry support for hardware profile filters";
        reference " 0.35.19.";
    }

    revision "2025-09-03" {
        description "CMIS: Added Smartoptics custom 200GBASE-DR2 interface type";
        reference " 0.35.18.";
    }

    revision "2025-08-28" {
        description "Support AS5916-54XL";
        reference " 0.35.17.";
    }

    revision "2025-08-08" {
        description "Addes ignore-snmp-generation tags for SNMP Support for ALARM MIB feature";
        reference " 0.35.16.";
    }

    revision "2025-08-07" {
        description "Blocking hardware-profile filter ingress-ipv6 for LTSW platform";
        reference " 0.35.15.";
    }

    revision "2025-07-31" {
        description "Use CMM_SFF8024_CONNECTOR_TYPE_T instead of DDM_CMM_TRANS_CONNECTOR_TYPE_T";
        reference " 0.35.14.";
    }

    revision "2025-07-29" {
        description "Added OSFP port type in enum";
        reference " 0.35.13.";
    }

    revision "2025-07-28" {
        description "Supporting hardware-profile filter bfd-group for TH5";
        reference " 0.35.12.";
    }

    revision "2025-07-24" {
        description "Added CPU core usage monitor average interval";
        reference " 0.35.11.";
    }

    revision "2025-07-22" {
        description "Added error codes in custom get and set RPCs";
        reference " 0.35.10.";
    }

    revision "2025-07-10" {
        description "Added new attributes trunk-hash-offset, ecmp-hash-offset and hash-seed under load-balance config";
        reference " 0.35.9.";
    }

    revision "2025-07-08" {
        description "Added eedb mode profile changes in dependent files";
        reference " 0.35.8.";
    }

    revision "2025-07-04" {
        description "CMIS: Added second laser temperature monitor";
        reference " 0.35.7.";
    }

    revision "2025-07-03" {
        description "modified the datatype and removed unset cli for ingress-acl";
        reference " 0.35.6.";
    }

    revision "2025-07-01" {
        description "Added unset notification for port channel load balance";
        reference " 0.35.5.";
    }

    revision "2025-06-27" {
        description "Added the fan duty cycle cli";
        reference " 0.35.4.";
    }

    revision "2025-06-26" {
        description "CMIS: Added extra interface types and baud rates";
        reference " 0.35.3.";
    }

    revision "2025-06-19" {
        description "Added HAVE_DNX for ingress-ipv4-subif-extended";
        reference " 0.35.2.";
    }

    revision "2025-06-18" {
        description "Added support for 800G OSFP transceiver";
        reference " 0.35.1.";
    }

    revision "2025-06-16" {
        description "Added twamp-session as a dependentObject for twamp-light control";
        reference " 0.35.0.";
    }

    revision "2025-06-13" {
        description "Added error codes in custom get and set RPCs";
        reference " 0.34.14.";
    }

    revision "2025-06-11" {
        description "Added Dependent Object for advanced parser to address the sequence during reboot";
        reference " 0.34.15.";
    }

    revision "2025-06-09" {
        description "Blocking forwarding profile for Hurican4 family";
        reference " 0.34.13.";
    }

    revision "2025-05-26" {
        description "Inclusion of 4th BMC PSU temperature sensor attribute";
        reference " 0.34.12.";
    }

    revision "2025-05-22" {
        description "Blocking hardware-profile filter ingress-ipv6 for TD4";
        reference " 0.34.11.";
    }

    revision "2025-05-15" {
        description "Revert transceiver CLI migration changes";
        reference " 0.34.10.";
    }

    revision "2025-05-14" {
        description "Blocking hardware-profile filter bfd-group for TH5";
        reference " 0.34.9.";
    }

    revision "2025-05-01" {
        description "Moved up ingress-ipv4-qos-copp/ingress-ipv6-qos-copp attr";
        reference " 0.34.8.";
    }

    revision "2025-04-28" {
        description "Added hardware-profile filter ingress-qos-ipv6";
        reference " 0.34.7.";
    }

    revision "2025-04-25" {
        description "hardware-profile filter egress-ipv6 CLI disabled for ltsw_new";
        reference " 0.34.6.";
    }

    revision "2025-04-14" {
        description "Added proper helpstring for Port Number";
        reference " 0.34.5.";
    }

    revision "2025-04-11" {
        description "CMIS: Added internal notifications for sending the port to interface mapping to Netconf";
        reference " 0.34.4.";
    }

    revision "2025-04-10" {
        description "Added hardware-profile qos-subif-policer and qos-subif-extended";
        reference " 0.34.3.";
    }

    revision "2025-04-08" {
        description "added hardware-profile ingress-ipv4-subif-ext";
        reference " 0.34.2.";
    }

    revision "2025-04-07" {
        description "Added support for Speculative options for DPI";
        reference " 0.34.1.";
    }

    revision "2025-04-04" {
        description "Added mode2/mode3 for hardware-profile port mode for S9600-28dx/64x/56dx/32x";
        reference " 0.34.0.";
    }

    revision "2025-04-02" {
        description "Changed names of custom get and set RPCs";
        reference " 0.33.10.";
    }

    revision "2025-04-01" {
        description "Fixing revision history";
        reference " 0.33.9.";
    }

    revision "2025-03-28" {
        description "Remove auto-restart attribute from config CLI";
        reference " 0.33.8.";
    }

    revision "2025-03-27" {
        description "Added Roce Qpairs for Load-balance";
        reference " 0.33.7.";
    }

    revision "2025-03-25" {
        description "Add ingress-ipv6-qos-copp filter and remove ingress-ipv4-qos and copp when dependency";
        reference " 0.33.6.";
    }

    revision "2025-03-20" {
        description "rearranged attribute order for qos-policer and ingress-ipv6";
        reference " 0.33.5.";
    }

    revision "2025-03-17" {
        description "Added kbp-disable to hardware-profile-config";
        reference " 0.32.41.";
    }

    revision "2025-03-14" {
        description "CLI migration from qsfp-dd references to xcvr references";
        reference " 0.33.4.";
    }

    revision "2025-03-12" {
        description "Added default cache timer for transceiver state data";
        reference " 0.33.3.";
    }

    revision "2025-03-07" {
        description "Reverted cli-commands to CLIs using attributes itself for gating and tx-shaping features";
        reference " 0.33.2.";
    }

    revision "2025-02-21" {
        description "removed mode2/mode3 for hardware-profile port mode for S9600-28dx/64x/56dx/32x";
        reference " 0.33.1.";
    }

    revision "2025-02-14" {
        description "Added support for hardware-profile port mode for S9610-46DX and 48DX";
        reference " 0.33.0.";
    }

    revision "2025-01-31" {
        description "Fix for the issue while enabling hardware-profile twamp";
        reference " 0.32.36.";
    }

    revision "2025-01-30" {
        description "Removed support for hardware-profile port mode for UFIS9510_28DC ";
        reference " 0.32.35.";
    }

    revision "2025-01-17" {
        description "[Revert]Added BelugaNOS custom get and set RPCs";
        reference " 0.32.34.";
    }

    revision "2025-01-13" {
        description "Updated ingress-ipv4-qos-copp filter";
        reference " 0.32.33.";
    }

    revision "2025-01-11" {
        description "Added BelugaNOS custom get and set RPCs";
        reference " 0.32.32.";
    }

    revision "2024-12-24" {
        description "Added media lane provision support";
        reference " 0.32.31.";
    }

    revision "2024-12-23" {
        description "Updated helpstring for AS9947-36xkb port-mode 2";
        reference " 0.32.30.";
    }

    revision "2024-12-16" {
        description "Supported ipv4/ipv6 acl on l2 interfaces";
        reference " 0.32.29.";
    }

    revision "2024-12-14" {
        description "Added hardware-profile filter ingress-ipv4-qos-copp";
        reference " 0.32.28.";
    }

    revision "2024-12-13" {
        description "Readded TD4 UFT options support";
        reference " 0.32.27.";
    }

    revision "2024-12-12" {
        description "Added CMIS module gating support";
        reference " 0.32.26.";
    }

    revision "2024-12-11" {
        description "Corrected attribute details for multi-level-ecmp";
        reference " 0.32.25.";
    }

    revision "2024-12-10" {
        description "Updated reallocated-sector-count description";
        reference " 0.32.24.";
    }

    revision "2024-12-09" {
        description "Added DDM_CMM_TRANS_IDENTIFIER_T elements";
        reference " 0.32.23.";
    }

    revision "2024-12-05" {
        description "Added new attribute multi-level-ecmp under load-balance config";
        reference " 0.32.22.";
    }

    revision "2024-11-27" {
        description "CMIS: Added C-CMIS revision 1.3 attributes";
        reference " 0.32.21.";
    }

    revision "2024-11-19" {
        description "Added UFT support for TH-5";
        reference " 0.32.20.";
    }

    revision "2024-11-14" {
        description "updated the xml changes to create the group first, which has more qualifier";
        reference " 0.32.19.";
    }

    revision "2024-11-13" {
        description "CMIS: Added new bit rates, new modulation format and new interface types";
        reference " 0.32.18.";
    }

    revision "2024-11-06" {
        description "Removed support for hardware-profile port mode for TH4";
        reference " 0.32.17.";
    }

    revision "2024-11-05" {
        description "Added new ingress-ipv4-l2,ingress-ipv6-l2 filter for L2 interface";
        reference " 0.32.16.";
    }

    revision "2024-10-31" {
        description "Added to port-channel load-balance the option to set RTAG7 by default on all aggregator interfaces";
        reference " 0.32.15.";
    }

    revision "2024-10-18" {
        description "Added Tomahawk5";
        reference " 0.32.14.";
    }

    revision "2024-10-08" {
        description "Added enum type for load-balance cli";
        reference " 0.32.13.";
    }

    revision "2024-09-25" {
        description "Removed the datatypes related to libhwconf";
        reference " 0.32.12.";
    }

    revision "2024-09-16" {
        description "Added the cpu-queues msdp and ptp to the existing lists";
        reference " 0.32.11.";
    }

    revision "2024-09-10" {
        description "Added if-feature check for hardware profile aclif";
        reference " 0.31.22.";
    }

    revision "2024-09-05" {
        description "Added support for hardware-profile port mode for S9321-64E";
        reference " 0.31.21.";
    }

    revision "2024-09-04" {
        description "CMIS: Removed recovery elements from alarm-type enum";
        reference " 0.31.20.";
    }

    revision "2024-09-03" {
        description "CMIS: Add alarm-type field for monitor recovery notifications";
        reference " 0.31.19.";
    }

    revision "2024-08-29" {
        description "Done changes in removing input parameters for advanced parser cli";
        reference " 0.31.18.";
    }

    revision "2024-08-28" {
        description "Added support for hardware-profile port mode for AS9817-64D";
        reference " 0.31.18.";
    }

    revision "2024-08-27" {
        description "Enable support for ingress-ipv6-ext-subif in DNX";
        reference " 0.31.17.";
    }

    revision "2024-08-22" {
        description "Fixed EDFA model datatype";
        reference " 0.31.16.";
    }

    revision "2024-08-20" {
        description "Fixed releases in OcNOS 6.5.3 revisions";
        reference " 0.31.15.";
    }

    revision "2024-08-19" {
        description "DB-SYNC issue is seen after configuring the temperature threshold";
        reference " 0.31.14.";
    }

    revision "2024-08-16" {
        description "CMIS: Fixes for custom application after DM review";
        reference " 0.31.13.";
    }

    revision "2024-08-15" {
        description "Added skip-yang tag to temperature threshold sensor-id when tag";
        reference " 0.31.12.";
    }

    revision "2024-08-09" {
        description "Added CMIS module laser status";
        reference " 0.31.11.";
    }

    revision "2024-08-08" {
        description "OLS-9132: User configuration for Temperature threshold";
        reference " 0.31.10.";
    }

    revision "2024-07-31" {
        description "Added support for load-balance flb CLI";
        reference " 0.31.9.";
    }

    revision "2024-07-29" {
        description "Added flag skip-netconf-validation to qsfp-dd model to skip some checks in netconf";
        reference " 0.31.8.";
    }

    revision "2024-07-25" {
        description "User configuration for Temperature threshold";
        reference " 0.31.7.";
    }

    revision "2024-07-24" {
        description "User configuration for Temperature threshold - update to resolve DB sync issue";
        reference " 0.31.6.";
    }

    revision "2024-07-22" {
        description "User configuration for Temperature threshold";
        reference " 0.31.5.";
    }

    revision "2024-07-21" {
        description "CMIS: Added custom application advertisement";
        reference " 0.31.4.";
    }

    revision "2024-07-20" {
        description "Fix storm-control and hardware-profile filter dependency in Q2 boards";
        reference " 0.31.3.";
    }

    revision "2024-07-19" {
        description "Corrected default values of hardware profile port-config";
        reference " 0.31.2.";
    }

    revision "2024-07-15" {
        description "Updated helpstring for mgmt-route-leak cpu rate config";
        reference " 0.31.0.";
    }

    revision "2024-07-05" {
        description "Include GPS GNSS and DPLL status";
        reference " 0.30.2.";
    }

    revision "2024-07-04" {
        description "Support gps satellite-system on custom3/4 PTP";
        reference " 0.30.1.";
    }

    revision "2024-06-27" {
        description "CMIS: Added custom application config CLI";
        reference " 0.30.0.";
    }

    revision "2024-06-19" {
        description "Added platform Clis checks for switchport protected CLI";
        reference " 0.29.16.";
    }

    revision "2024-06-17" {
        description "Added support for hardware-profile port mode for AS9947-36XKB";
        reference " 0.29.15.";
    }

    revision "2024-06-03" {
        description "Added small field groups at last in hardware-profile-filters-config";
        reference " 0.29.14.";
    }

    revision "2024-05-25" {
        description "CMIS: Added Ciena custom modulation formats, interface types and bit rates";
        reference " 0.29.13.";
    }

    revision "2024-05-24" {
        description "Added CDR control support";
        reference " 0.29.12.";
    }

    revision "2024-04-29" {
        description "Cli implementation for gps satellite-system";
        reference " 0.29.11.";
    }

    revision "2024-04-27" {
        description "Removed unsupported Queues from PLATFORM_CPU_QUEUE_NAME_T for Marvell";
        reference " 0.29.10.";
    }

    revision "2024-04-22" {
        description "added when condition for rtag7";
        reference " 0.29.9.";
    }

    revision "2024-04-16" {
        description "Moved evpn-mpls-multi-homing profile to new grouping to add the dependency on other profiles";
        reference " 0.29.8.";
    }

    revision "2024-04-15" {
        description "Added TCAM utilization recovery logs";
        reference " 0.29.7.";
    }

    revision "2024-04-08" {
        description "CMIS: Added host-config attribute to host side application advertisement";
        reference " 0.29.6.";
    }

    revision "2024-04-03" {
        description "Added elements for CMM_CMIS_INTERFACE_TYPE_T";
        reference " 0.29.5.";
    }

    revision "2024-03-28" {
        description "CMIS: Changed modsel-wait-time type to CML_UINT32_T";
        reference " 0.29.4.";
    }

    revision "2024-03-20" {
        description "Reduced route-mode support for TD4 ";
        reference " 0.29.3.";
    }

    revision "2024-03-15" {
        description "Added CML_OBJ_READ_ONLY_CONFIG flag for platform container for soc configuration in submodule ipi-platform-profile-extended";
        reference " 0.29.2.";
    }

    revision "2024-03-01" {
        description "CMIS: Added CDR bypass HW status information and SI advertisement";
        reference " 0.29.1.";
    }

    revision "2024-02-28" {
        description "Removed Hardware Profile Port-confige mode3 4 5 6 for UFI_S9610-36D";
        reference " 0.29.0.";
    }

    revision "2024-02-27" {
        description "Added cpu-queue and copp support for Marvell";
        reference " 0.28.4.";
    }

    revision "2024-02-26" {
        description "Added CDR control support";
        reference " 0.28.3.";
    }

    revision "2024-02-22" {
        description "Removed the cli micro-bfd profile ";
        reference " 0.28.2.";
    }

    revision "2024-02-20" {
        description "Added UFT support for TH-4";
        reference " 0.28.1.";
    }

    revision "2024-02-09" {
        description "Added lpm-128-bit support for TD-4";
        reference " 0.28.0.";
    }

    revision "2024-02-07" {
        description "Added transceiver-application-change-host and transceiver-application-change-media notification";
        reference " 0.27.2.";
    }

    revision "2024-02-06" {
        description "Added bcm-sensor-data-record attributes for Streaming Telemetry";
        reference " 0.27.1.";
    }

    revision "2024-02-01" {
        description "Added error-message tag for attributes ingres-ipv4 ingres-ipv4-ext ingres-ipv4-subif";
        reference " 0.27.0.";
    }

    revision "2024-01-31" {
        description "Added support for CMIS SI and user thresholds HW config status";
        reference " 0.26.13.";
    }

    revision "2024-01-22" {
        description "Removed if feature DNX check for hardware-profile seamless-bfd (enable|disable)";
        reference " 0.26.12.";
    }

    revision "2024-01-15" {
        description "Added CMIS modules paths for Streaming Telemetry";
        reference " 0.26.11.";
    }

    revision "2024-01-09" {
        description "Added protcol and ipv6 option under load-balance for Marvell";
        reference " 0.26.10.";
    }

    revision "2023-12-27" {
        description "Add CLI to configure QSFP-DD SI parameters";
        reference " 0.26.9.";
    }

    revision "2023-12-20" {
        description "Moving Raon cli to if-extended file";
        reference " 0.26.8.";
    }

    revision "2023-12-16" {
        description "Updated the ethernet count for 400G ports";
        reference " 0.26.7.";
    }

    revision "2023-12-15" {
        description "Added protcol and ipv6 option under load-balance for Marvell";
        reference " 0.26.6.";
    }

    revision "2023-12-13" {
        description "Added transceiver module-functional-type attribute";
        reference " 0.26.5.";
    }

    revision "2023-12-12" {
        description "CMIS: Removed mandatory high-alarm and low-alarm in user threshold configs";
        reference " 0.26.4.";
    }

    revision "2023-11-27" {
        description "Added support for hardware-profile port mode for S9600-28DX ";
        reference " 0.26.3.";
    }

    revision "2023-11-13" {
        description "Added support for hardware-profile port mode for S9500-30XS ";
        reference " 0.26.2.";
    }

    revision "2023-11-08" {
        description "Added support for hardware-profile port mode for AS7316-26xb mode";
        reference " 0.26.1.";
    }

    revision "2023-11-01" {
        description "Added CMIS module advertisements";
        reference " 0.25.10.";
    }

    revision "2023-10-31" {
        description "Added new port-config mode3 on AS7315-27X";
        reference " 0.25.9.";
    }

    revision "2023-10-27" {
        description "Added CMIS module datapath assigned interface name state info";
        reference " 0.25.8.";
    }

    revision "2023-10-19" {
        description "Added additional state attributes for datapaths in the cmis-modules model";
        reference " 0.25.7.";
    }

    revision "2023-10-18" {
        description "Handle QSFP-DD media and host lane emtpy config cases";
        reference " 0.25.6.";
    }

    revision "2023-10-16" {
        description "TIBIT Build Issue Handling";
        reference " 0.25.5.";
    }

    revision "2023-10-04" {
        description "Added streaming telemetry yaml file";
        reference " 0.25.2.";
    }

    revision "2023-10-02" {
        description "Add load-balance command for Marvell";
        reference " 0.25.4.";
    }

    revision "2023-09-27" {
        description "Supressed cmis-module runtime container for TIBIT VM";
        reference " 0.25.3.";
    }

    revision "2023-09-25" {
        description "Added when condition for type attribute";
        reference " 0.25.1.";
    }

    revision "2023-09-22" {
        description "Moved cmis-modules container under /components/component/transceiver";
        reference " 0.25.0.";
    }

    revision "2023-09-21" {
        description "Enable support for ingress-ipv6-extended and ingress-ipv6-extended-vlan in DNX";
        reference " 0.24.3.";
    }

    revision "2023-09-19" {
        description "hardware filter ingress-l2-subif and ingress-ipv4-ext group addition done";
        reference " 0.24.2.";
    }

    revision "2023-08-31" {
        description "Remove unnecessary import";
        reference " 0.24.1.";
    }

    revision "2023-08-29" {
        description "Add autoPopulate tag to QSFP-DD config media lane number key attribute";
        reference " 0.24.0.";
    }

    revision "2023-08-23" {
        description "Implementation of aclif CLI";
        reference " 0.23.9.";
    }

    revision "2023-08-22" {
        description "support bgp-flowspec-mode attribute";
        reference " 0.23.9.";
    }

    revision "2023-08-17" {
        description "Added a separate command to enable/disable the twamp-ipv6 mpls group";
        reference " 0.23.8.";
    }

    revision "2023-08-11" {
        description "Fixes made in order resolve QSFP-DD laser config DB sync issues";
        reference " 0.23.7.";
    }

    revision "2023-08-08" {
        description "Support for NAI";
        reference " 0.23.6.";
    }

    revision "2023-08-07" {
        description "Minor fixes introduced as result of review of CMIS Xpath v1.2";
        reference " 0.23.5.";
    }

    revision "2023-08-01" {
        description "Adding trident chipset for lpm-128bit-profile";
        reference " 0.23.4.";
    }

    revision "2023-07-25" {
        description "Fixed QSFP-DD per media lane laser and user threshold config DB sync issues";
        reference " 0.23.3.";
    }

    revision "2023-07-22" {
        description "cfm disable for q2 ipbase";
        reference " 0.23.2.";
    }

    revision "2023-07-21" {
        description "service-disable will be supported for all QSFP-DD modules";
        reference " 0.23.1.";
    }

    revision "2023-07-20" {
        description "Fixed missing 'port-channel load-balance rtag7' from show command";
        reference " 0.23.0.";
    }

    revision "2023-07-19" {
        description "Rename EDFA target output power config attribute name";
        reference " 0.22.9.";
    }

    revision "2023-07-17" {
        description "Changed help string for AS5916-54X and AS5912-54x ";
        reference " 0.22.8.";
    }

    revision "2023-07-12" {
        description "Added ipv6-ipsg as an option to hardware-profile filter";
        reference " 0.22.7.";
    }

    revision "2023-07-11" {
        description "Support for Marvell";
        reference " 0.22.7.";
    }

    revision "2023-06-30" {
        description "Added support for QSFP-DD configurable threshold";
        reference " 0.22.6.";
    }

    revision "2023-06-29" {
        description "Fixed QSFP-DD media side flags datatype";
        reference " 0.22.4.";
    }

    revision "2023-06-27" {
        description "Added tomahawk3 forward profiles";
        reference " 0.22.5.";
    }

    revision "2023-06-22" {
        description "Inclusion of streaming telemetry yaml files in sub-modules";
        reference " 0.17.20.";
    }

    revision "2023-06-21" {
        description "Added CCMIS media threshold alarms";
        reference " 0.22.3.";
    }

    revision "2023-06-20" {
        description "Added support for short packet handling";
        reference " 0.17.19.";
    }

    revision "2023-06-19" {
        description "Added CCMIS host threshold alarms";
        reference " 0.17.18.";
    }

    revision "2023-06-16" {
        description "Removed port mode support on AS9716-32D XGS TOMAHAWK3 ";
        reference " 0.17.17.";
    }

    revision "2023-06-09" {
        description "Added CCMIS host and media discrete alarms";
        reference " 0.17.16.";
    }

    revision "2023-06-08" {
        description "Added CML_FORCE_RELOAD_FLUSH_DB flag for port-mode attributes";
        reference " 0.17.15.";
    }

    revision "2023-06-06" {
        description "Added support for port mode 4X100G on UFIS9610-36D";
        reference " 0.17.14.";
    }

    revision "2023-05-31" {
        description "Added support for dune port mode for 5916-54x_54xm_5xks";
        reference " 0.17.13.";
    }

    revision "2023-05-25" {
        description "Added support for hardware-profile port mode for as9716-32d board";
        reference " 0.17.9.";
    }

    revision "2023-05-19" {
        description "Added support for dune port mode and port-group";
        reference " 0.17.12.";
    }

    revision "2023-05-10" {
        description "Added the empty state attribute under the component container";
        reference " 0.17.11.";
    }

    revision "2023-05-08" {
        description "Added support for dune port mode";
        reference " 0.17.10.";
    }

    revision "2023-05-02" {
        description "Added support for hardware-profile port mode for UFIS9610-36d mode";
        reference " 0.17.8.";
    }

    revision "2023-04-27" {
        description "Fix protocol status datatype for Smart SFP";
        reference " 0.17.7.";
    }

    revision "2023-04-26" {
        description "New CLI added for port isolation profile";
        reference " 0.17.6.";
    }

    revision "2023-04-14" {
        description "Initial version of EDFA datamodel";
        reference " 0.17.5.";
    }

    revision "2023-04-13" {
        description "Initial version of Smart SFP datamodel";
        reference " 0.17.4.";
    }

    revision "2023-04-12" {
        description "Remove alarm type field from non-descrete CMIS alarm recovery notifications";
        reference " 0.17.3.";
    }

    revision "2023-04-11" {
        description "Blocked load balance command for tomahaw3 ";
        reference " 0.17.2.";
    }

    revision "2023-03-28" {
        description "Adding new attr cfm-continuity-check-message for DNX";
        reference " 0.17.1.";
    }

    revision "2023-03-17" {
        description "Enabling RTAG7 MPLS option in DC IP BASE";
        reference " 0.17.0.";
    }

    revision "2023-03-15" {
        description "Replaced QSFP-DD laser grid config related WHEN condition for media lane laser channel to a DB trigger";
        reference " 0.16.10.";
    }

    revision "2023-03-11" {
        description "Removed autoPopulate-custom for micro-bfd CLI";
        reference " 0.16.9.";
    }

    revision "2023-03-06" {
        description "Fixed cmis-module list child nodes that were not compliant with the current CMIS XPath sheet";
        reference " 0.16.8.";
    }

    revision "2023-03-04" {
        description "filter group support for BGP Flowspec";
        reference " 0.16.7.";
    }

    revision "2023-03-03" {
        description "Enclosed the objectlist with container";
        reference " 0.16.6.";
    }

    revision "2023-03-02" {
        description "Removed micro-bfd profile cli for DNX boards";
        reference " 0.16.5.";
    }

    revision "2023-02-27" {
        description "Updated attribute egress-ipv6-dnx datatype from CML_ENABLE_DISABLE_T to CML_EMPTY_T";
        reference " 0.16.4.";
    }

    revision "2023-02-15" {
        description "Added CLI command to disable coherent license per QSFP-DD port";
        reference " 0.16.3.";
    }

    revision "2023-02-13" {
        description "Per host lane QSFP-DD configuration mode";
        reference " 0.16.2.";
    }

    revision "2023-02-11" {
        description "EDFA Operation configurations";
        reference " 0.16.1.";
    }

    revision "2023-01-24" {
        description "Per media lane QSFP-DD laser configurations";
        reference " 0.16.0.";
    }

    revision "2023-01-12" {
        description "Removed forwarding profile config support for HR4";
        reference " 0.15.9.";
    }

    revision "2023-01-11" {
        description "Added WHEN tag to prevent commit of empty QSFP-DD config (empty list)";
        reference " 0.15.8.";
    }

    revision "2023-01-05" {
        description "Leafref correction for config container";
        reference " 0.15.7.";
    }

    revision "2023-01-03" {
        description "Added basic CMIS transceiver module, host side and media side monitors";
        reference " 0.15.6.";
    }

    revision "2022-12-21" {
        description "Adding netconf notifications for transceiver critical/alert low/high warning thresholds attributes";
        reference " 0.15.5.";
    }

    revision "2022-12-20" {
        description "Blocking forwarding-ipv4";
        reference " 0.15.4.";
    }

    revision "2022-12-16" {
        description "Help String updation for fine tune freq config and target output power config CLIs";
        reference " 0.15.3.";
    }

    revision "2022-12-14" {
        description "Added support for hardware-profile port mode for UFIS9600-56dx mode";
        reference " 0.15.3.";
    }

    revision "2022-12-09" {
        description "hardware-filter bfd-group CLI disabled for HURRICANE4";
        reference " 0.15.2.";
    }

    revision "2022-12-08" {
        description "Added if-feature HAVE_BROADCOM AND HAVE_DUNE to the datatype PLATFORM_VOQ_SCALE_TYPE_T";
        reference " 0.15.1.";
    }

    revision "2022-12-07" {
        description "Added the cliprependstr to the prependstr alarm";
        reference " 0.15.0.";
    }

    revision "2022-12-01" {
        description "implementation of hardware profile statistics egress-policer|voq-scale CLI";
        reference " 0.14.9.";
    }

    revision "2022-11-29" {
        description "Addressed make cmlgen warnings";
        reference " 0.14.8.";
    }

    revision "2022-11-28" {
        description "New SOC type Hurriane 4 added";
        reference " 0.14.7.";
    }

    revision "2022-11-16" {
        description "Added profile filter ingress-ipv6-ext-vlan";
        reference " 0.14.6.";
    }

    revision "2022-11-09" {
        description "Added profile filter ingress-ipv6-ext";
        reference " 0.14.5.";
    }

    revision "2022-11-07" {
        description "Adding transceiver critical/alert low/high warning thresholds attributes";
        reference " 0.14.4.";
    }

    revision "2022-11-04" {
        description "Added unset CLI for QSFP-DD config mode and implicit_delete/autoPopulate where is needed to avoid DB sync";
        reference " 0.14.3.";
    }

    revision "2022-11-03" {
        description "Fixed DB sync issues related to laser grid spacing config for QSFP-DD";
        reference " 0.14.2.";
    }

    revision "2022-10-31" {
        description "Added cfm-slm attr for DNX statistics ipi-platform-profile submodule";
        reference " 0.14.1.";
    }

    revision "2022-10-27" {
        description "Fixed DB sync issues for QSFP-DD configs";
        reference " 0.14.0.";
    }

    revision "2022-10-24" {
        description "Added TX laser grid spacing, fine tune frequency and output power configs for QSFP-DD transceivers";
        reference " 0.13.13.";
    }

    revision "2022-10-21" {
        description "Updated ingress-ipv4 attr name in ipi-platform-profile submodule";
        reference " 0.13.12.";
    }

    revision "2022-10-19" {
        description "Updated ipi-platform-profile submodule";
        reference " 0.13.11.";
    }

    revision "2022-10-17" {
        description "Fixed olt compilation err for voq stats";
        reference " 0.13.10.";
    }

    revision "2022-10-12" {
        description "Updated datatype for VOQ stats";
        reference " 0.13.9.";
    }

    revision "2022-09-27" {
        description "Addressing CMIS datamodel XPath review comments";
        reference " 0.13.8.";
    }

    revision "2022-09-22" {
        description "Added CLI to configure QSFP-DD TX laser channel";
        reference " 0.13.7.";
    }

    revision "2022-09-15" {
        description "Updated ipi-platform-profile submodule";
        reference " 0.13.6.";
    }

    revision "2022-08-25" {
        description "Added CMIS QSFP-DD configuration attributes and respective CLI";
        reference " 0.13.5.";
    }

    revision "2022-08-10" {
        description "Debug hierarchy change";
        reference " 0.13.4.";
    }

    revision "2022-08-05" {
        description "Updated revision ref for OcNOS 6.1";
        reference " 0.13.3.";
    }

    revision "2022-07-29" {
        description "Updated RAON data types";
        reference " 0.13.2.";
    }

    revision "2022-07-22" {
        description "Updated ipi-platform-profile submodule";
        reference " 0.13.1.";
    }

    revision "2022-07-21" {
        description "Add Tibit specific data and control for Tibit OLT MicroPlug transceiver";
        reference " 0.13.0.";
    }

    revision "2022-07-20" {
        description "Updated submodules platform-profile and platform-profile-extended";
        reference " 0.12.20.";
    }

    revision "2022-07-12" {
        description "New notifications added for FAN rpm changes";
        reference " 0.12.19.";
    }

    revision "2022-07-07" {
        description "Added datamodel file for SFF-8024 type definitions";
        reference " 0.12.18.";
    }

    revision "2022-06-28" {
        description "Initial version for CMIS transceivers attributes";
        reference " 0.12.17.";
    }

    revision "2022-06-27" {
        description "Added new attribute for hardware-profile seamless-bfd (enable|disable)";
        reference " 0.12.16.";
    }

    revision "2022-06-01" {
        description "Updated the yang file with feature";
        reference " 0.12.15.";
    }

    revision "2022-05-02" {
        description "Added new attribute for hardware-profile port mode for UFIS9600-64X and UFIS9600-32X mode";
        reference " 0.12.14.";
    }

    revision "2022-03-08" {
        description "Initial version for Ceragon board CPLD attributes and merged POE xml";
        reference " 0.12.13.";
    }

    revision "2022-02-10" {
        description "Updated ipi-platform-transceiver submodule";
        reference " 0.12.12.";
    }

    revision "2022-01-26" {
        description "Moved disk activity monitoring config attributes to a separate container. Also changed some attribute names";
        reference " 0.12.11.";
    }

    revision "2022-01-21" {
        description "Added when tag to all load-balance child containers on ipi-platfomr-extended sumodule";
        reference " 0.12.10.";
    }

    revision "2022-01-11" {
        description "Added when tag to inner-ipv4 non-symmetric on ipi-platform-profile-extended submodule";
        reference " 0.12.9.";
    }

    revision "2022-01-07" {
        description "Changed cpu-q-default from attribute to rpc on platform-profile";
        reference " 0.12.8.";
    }

    revision "2022-01-06" {
        description "Added new attribute hardware-profile port-config";
        reference " 0.12.7.";
    }

    revision "2022-01-03" {
        description "Added implicit-delete to load-balance config on ipi-platform-profile";
        reference " 0.12.6.";
    }

    revision "2021-12-30" {
        description "Removed autoPopulate tag from platform container on ipi-platform-profile-extended";
        reference " 0.12.5.";
    }

    revision "2021-12-27" {
        description "Added when tag to mpls-ler container on ipi-platform-profile-extended";
        reference " 0.12.4.";
    }

    revision "2021-12-20" {
        description "Introduced new sub-module ipi-platform-poe.";
        reference " 0.12.3.";
    }

    revision "2021-12-10" {
        description "Changed datatype of system status attributes";
        reference " 0.12.2.";
    }

    revision "2021-11-22" {
        description "Updated ipi-platform-profile submodule with DNX Broadcom platform hardware profiles";
        reference " 0.12.1.";
    }

    revision "2021-11-16" {
        description "Added new attributes for disk activity monitoring ";
        reference " 0.12.0.";
    }

    revision "2021-10-12" {
        description "Updated ipi-platform-profile submodule";
        reference " 0.11.1.";
    }

    revision "2021-09-06" {
        description "Updated ipi-platform-profile submodule";
        reference " 0.11.0.";
    }

    revision "2021-08-19" {
        description "Updated ipi-platform-transceiver submodule";
        reference " 0.10.9.";
    }

    revision "2021-08-16" {
        description "Updated submodule ipi-platform-transceiver with new attributes and notifications";
        reference " 0.10.8.";
    }

    revision "2021-08-13" {
        description "Notifications added for submodules ipi-platform-transceiver and ipi-platform-storage.";
        reference " 0.10.7.";
    }

    revision "2021-07-29" {
        description "Updated submodule ipi-platform-profile with new filter type ipsg and ipsg-ipv6 group.";
        reference " 0.10.6.";
    }

    revision "2021-07-28" {
        description "Updated submodule ipi-platform-profile for non-DNX Broadcom platform.";
        reference " 0.10.5.";
    }

    revision "2021-07-21" {
        description "New attributes added for submodule ipi-platform-power-rail";
        reference " 0.10.4.";
    }

    revision "2021-07-07" {
        description "Removed pattern from string attributes for submodule ipi-platform-transceiver";
        reference " 0.10.3.";
    }

    revision "2021-06-29" {
        description "Updated submodule ipi-platform-profile for new attribute ingress-ipv6-acl.";
        reference " 0.10.2.";
    }

    revision "2021-06-25" {
        description "Updated submodule ipi-platform-profile with new filter type dhcp-snoop and dhcp-snoop-ipv6 group.";
        reference " 0.10.1.";
    }

    revision "2021-06-24" {
        description "New Types added, submodule ipi-platform-port added and submodules ipi-platform-storage, ipi-platform-temperature, ipi-platform-transceiver, ipi-platform-transceiver-types, ipi-platform-types, ipi-transport-line-common changed.";
        reference " 0.10.0.";
    }

    revision "2021-06-23" {
        description "Updated submodule ipi-platform-profile for attribute ingress-bfd datatype changed.";
        reference " 0.9.2.";
    }

    revision "2021-06-17" {
        description "Updated submodule ipi-platform-profile for non-DNX Broadcom platform.";
        reference " 0.9.1.";
    }

    revision "2021-06-11" {
        description "Some BMC sensor attributes had the type changes from two decimal places to three.";
        reference " 0.9.0.";
    }

    revision "2021-05-31" {
        description "New attributes added for submodule ipi-platform-storage";
        reference " 0.8.0.";
    }

    revision "2021-04-28" {
        description "Submodule ipi-platform-cpu changed.";
        reference " 0.7.0.";
    }

    revision "2021-03-30" {
        description "Introduced new sub-modules ipi-platform-profile.";
        reference " 0.6.0.";
    }

    revision "2021-03-18" {
        description "Updated ipi-platform-power-supply sub-module. Removed pattern from string attributes.";
        reference " 0.5.0.";
    }

    revision "2021-01-25" {
        description "Introduced new sub-modules ipi-platform-temperature, ipi-platform-power-supply, ipi-fan, ipi-fan-tray, ipi-chassis, ipi-linecard, and ipi-power-rail. Fixed attribute transceiver-code typo.";
        reference " 0.4.0.";
    }

    revision "2021-01-18" {
        description "Introduced new ipi-platform-cpu sub-module";
        reference " 0.3.0.";
    }

    revision "2020-12-15" {
        description "Change to have data-types in lower case instead of camel case";
        reference " 0.2.0.";
    }

    revision "2018-06-21" {
        description "Initial Version";
        reference " 0.1.0.";
    }

    grouping component-memory-state-detail {
        description
            "Per-component memory statistics detail";
        leaf available  {
            type  uint64;
            units "Mbytes";
            description "The available memory physically installed, or logically allocated to
                        the component.";
        } // END of available definition.

        leaf utilized  {
            type  uint64;
            units "Mbytes";
            description "utilized memory.";
        } // END of utilized definition.

    } // END of component-memory-state-detail definition.
    grouping component-board-state-detail {
        description
            "Per-component board detail";
        leaf board-name  {
            type  string {
                length "1..1965";
            }
            description "Name of the Board";
        } // END of board-name definition.

        leaf board-serial-no  {
            type  string {
                length "1..1965";
            }
            description "Serial No of the device";
        } // END of board-serial-no definition.

        leaf board-mfg-name  {
            type  string {
                length "1..1965";
            }
            description "Device's manufacturer name";
        } // END of board-mfg-name definition.

        leaf board-mfg-date  {
            type  yang:date-and-time {
                pattern "\\d{4}-\\d{2}-\\d{2}T\\d{2}:\\d{2}:\\d{2}(\\.\\d+)?(Z|[\\+\\-]\\d{2}:\\d{2})";
                }
                description "Device's manufacturing date.";
            } // END of board-mfg-date definition.

    } // END of component-board-state-detail definition.
    grouping system-load {
        description
            "System load group";
        leaf system-1min-load-avg-warning-threshold  {
            type  uint8 {
                 range "41..100"  {
                    description "41..100: Supported range 41 - 100";
                 }
            }
            description "System 1min average load threshold for warning";
        } // END of system-1min-load-avg-warning-threshold definition.

        leaf system-1min-load-avg-alarm  {
            type  uint8 {
                 range "51..100"  {
                    description "51..100: Supported range 51 - 100";
                 }
            }
            description "System 1min average load for alarm";
        } // END of system-1min-load-avg-alarm definition.

        leaf system-5min-load-avg-alarm  {
            type  uint8 {
                 range "51..100"  {
                    description "51..100: Supported range 51 - 100";
                 }
            }
            description "System 5min average load for alarm";
        } // END of system-5min-load-avg-alarm definition.

        leaf system-15min-load-avg-alarm  {
            type  uint8 {
                 range "51..100"  {
                    description "51..100: Supported range 51 - 100";
                 }
            }
            description "System 15min average load for alarm";
        } // END of system-15min-load-avg-alarm definition.

    } // END of system-load definition.
    grouping cpu-threshold {
        description
            "cpu threshold group";
        leaf warning-threshold  {
            type  uint8 {
                 range "51..100"  {
                    description "51..100: Supported range 51 - 100";
                 }
            }
            description "Cpu threshold for warning";
        } // END of warning-threshold definition.

        leaf alarm-threshold  {
            type  uint8 {
                 range "91..100"  {
                    description "91..100: Supported range 91 - 100";
                 }
            }
            description "Cpu threshold for alarm";
        } // END of alarm-threshold definition.

    } // END of cpu-threshold definition.
    grouping component-generic-global {
        description
            "Generic platform global configuration";
        leaf warning-repeat  {
            type  empty;
            description "To enable cmm warning level logs to repeat.";
        } // END of warning-repeat definition.

    } // END of component-generic-global definition.
    grouping system-load-cpu-usage-global {
        description
            "System load and CPU usage global group";
        container system-load-average-thresholds {
            description
                "Container for Global system load average thresolds";

            list system-load-average-threshold {
                key "system-1min-load-avg-warning-threshold system-1min-load-avg-alarm system-5min-load-avg-alarm system-15min-load-avg-alarm";
                max-elements 1;
                description
                    "Global system load average";
                leaf system-1min-load-avg-warning-threshold  {
                    type  leafref {
                        path  "../config/system-1min-load-avg-warning-threshold";
                    }
                    description "System 1min average load threshold for warning";
                } // END of system-1min-load-avg-warning-threshold definition.

                leaf system-1min-load-avg-alarm  {
                    type  leafref {
                        path  "../config/system-1min-load-avg-alarm";
                    }
                    description "System 1min average load for alarm";
                } // END of system-1min-load-avg-alarm definition.

                leaf system-5min-load-avg-alarm  {
                    type  leafref {
                        path  "../config/system-5min-load-avg-alarm";
                    }
                    description "System 5min average load for alarm";
                } // END of system-5min-load-avg-alarm definition.

                leaf system-15min-load-avg-alarm  {
                    type  leafref {
                        path  "../config/system-15min-load-avg-alarm";
                    }
                    description "System 15min average load for alarm";
                } // END of system-15min-load-avg-alarm definition.

                container config {
                    description
                        "system level load configuration";
                    uses system-load;
                } // END of config-container definition.
                container state {
                    config false;
                    description
                        "system level load operational data";
                    uses system-load;
                } // END of state-container definition.
            } // End of system-load-average-threshold-list
        } // END of system-load-average-thresholds-container definition.
        container cpu-core-usage-thresholds {
            description
                "Container for Global level CPU usage thresholds";

            list cpu-core-usage-threshold {
                key "warning-threshold alarm-threshold";
                max-elements 1;
                description
                    "Global level cpu usage threshold";
                leaf warning-threshold  {
                    type  leafref {
                        path  "../config/warning-threshold";
                    }
                    description "Cpu threshold for warning";
                } // END of warning-threshold definition.

                leaf alarm-threshold  {
                    type  leafref {
                        path  "../config/alarm-threshold";
                    }
                    description "Cpu threshold for alarm";
                } // END of alarm-threshold definition.

                container config {
                    description
                        "Global level cpu threshold configuration";
                    uses cpu-threshold;
                } // END of config-container definition.
                container state {
                    config false;
                    description
                        "system level load operational data";
                    uses cpu-threshold;
                } // END of state-container definition.
            } // End of cpu-core-usage-threshold-list
        } // END of cpu-core-usage-thresholds-container definition.
    } // END of system-load-cpu-usage-global definition.
    grouping component-interface {
        description
            "interface configuration group";
        leaf interface-name  {
            type  leafref {
                path  "/ipi-interface:interfaces/ipi-interface:interface/ipi-interface:name";
            }
            description "Use this attribute to perform platform's interface related
                        configurations";
        } // END of interface-name definition.

        leaf monitor-port  {
            type  ipi-platform-types:cmm_monitor_state;
            description "To enable DDM monitor for current transceiver.";
        } // END of monitor-port definition.

        leaf poe-enable  {
            type  empty;
            description "To enable PoE for current interface.";
        } // END of poe-enable definition.

        leaf videopiu-port  {
            if-feature feature-list:HAVE_VPIU_EMULATION;
            type  ipi-platform-types:cmm_videopiu_state;
            description "To enable VIDEO PIU for current transceiver.";
        } // END of videopiu-port definition.

        leaf transceiver-code  {
            type  ipi-platform-transceiver-types:ddm_transceiver_t;
            description "To set transceiver code for current transceiver.";
        } // END of transceiver-code definition.

        leaf wavelength  {
            type  ipi-platform-types:cml_wavelength_t;
            description "wavelength";
        } // END of wavelength definition.

        leaf tx-disable  {
            type  empty;
            description "To disable laser tx for current transceiver.";
        } // END of tx-disable definition.

        leaf edfa-operating-mode  {
            type  ipi-platform-types:edfa_operating_mode_t;
            description "To set the EDFA operating mode";
        } // END of edfa-operating-mode definition.

        leaf edfa-target-output-power  {
            type  decimal64 {
                 fraction-digits 3;            }
            units "dBm";
            description "To configure the target output power value in dBm";
        } // END of edfa-target-output-power definition.

        leaf edfa-target-gain  {
            type  decimal64 {
                 fraction-digits 3;            }
            units "dBm";
            description "To set the target-gain";
        } // END of edfa-target-gain definition.

        leaf tx-cdr-bypass  {
            type  empty;
            description "Bypass the TX CDR control";
        } // END of tx-cdr-bypass definition.

        leaf rx-cdr-bypass  {
            type  empty;
            description "Bypass the CDR control";
        } // END of rx-cdr-bypass definition.

    } // END of component-interface definition.
    grouping platform-component-interface-list {
        description
            "global interface configuration list group";

        list interface {
            key "interface-name";
            description
                "Platform interface related operations";
            leaf interface-name  {
                type  leafref {
                    path  "../config/interface-name";
                }
                description "Use this attribute to perform platform's interface related
                            configurations";
            } // END of interface-name definition.

            container config {
                description
                    "interface related configurations";
                uses component-interface;
            } // END of config-container definition.
            container state {
                config false;
                description
                    "Operational data for interface";
                uses component-interface;
            } // END of state-container definition.
        } // End of interface-list
    } // END of platform-component-interface-list definition.
    grouping component-generic-debug {
        description
            "Grouping debug info for generic platform";
        leaf enable-cmm  {
            type  empty;
            description "Use this attribute to turn on debugging for chassis monitoring";
        } // END of enable-cmm definition.

    } // END of component-generic-debug definition.
    grouping component-generic-terminal-debug {
        description
            "Grouping terminal debug info for generic platform";
        leaf terminal-debug-status-cmm  {
            type  cml-data-types:cml_on_off_t;
            description "Use this attribute to see the terminal debugging state for chassis
                        monitoring";
        } // END of terminal-debug-status-cmm definition.

    } // END of component-generic-terminal-debug definition.
    grouping component-bmc-sensor-record-state {
        description
            "component-bmc-sensor-record-state";
        container state {
            config false;
            description
                "Operational data for bmc-sensor";
            leaf sensor-name  {
                type  string {
                    length "1..1965";
                }
                description "sensor name";
            } // END of sensor-name definition.

            leaf value  {
                type  ipi-platform-types:cmm_bmc_value_t;
                description "sensor record value.Value -100002 represents not applicable";
            } // END of value definition.

            leaf units  {
                type  string {
                    length "1..1965";
                }
                description "unit of sensor record";
            } // END of units definition.

            leaf lower-non-recoverable  {
                type  decimal64 {
                     fraction-digits 3;                }
                description "lower non recoverable sensor threshold.-100002 represents not
                            applicable";
            } // END of lower-non-recoverable definition.

            leaf lower-non-critical  {
                type  decimal64 {
                     fraction-digits 3;                }
                description "lower non critical sensor threshold.-100002 represents not applicable";
            } // END of lower-non-critical definition.

            leaf lower-critical  {
                type  decimal64 {
                     fraction-digits 3;                }
                description "lower non critical sensor threshold.-100002 represents not applicable";
            } // END of lower-critical definition.

            leaf upper-non-critical  {
                type  decimal64 {
                     fraction-digits 3;                }
                description "upper non critical sensor threshold.-100002 represents not applicable";
            } // END of upper-non-critical definition.

            leaf upper-critical  {
                type  decimal64 {
                     fraction-digits 3;                }
                description "upper critical sensor threshold.-100002 represents not applicable";
            } // END of upper-critical definition.

            leaf upper-non-recoverable  {
                type  decimal64 {
                     fraction-digits 3;                }
                description "upper critical sensor threshold.-100002 represents not applicable";
            } // END of upper-non-recoverable definition.

            leaf operational-status  {
                type  string {
                    length "1..1965";
                }
                description "Sensor's operational state";
            } // END of operational-status definition.

            leaf threshold  {
                type  decimal64 {
                     fraction-digits 3;                }
                description "threshold for sensor notification";
            } // END of threshold definition.

            leaf event-type  {
                type  ipi-platform-types:cmm_bmc_event_type_t;
                description "Type of event for sensor notification";
            } // END of event-type definition.

        } // END of state-container definition.
    } // END of component-bmc-sensor-record-state definition.
    grouping component-hardware-debug {
        description
            "Grouping debug info for hardware related debug";
        leaf enable-ddm  {
            if-feature feature-list:NOT_HAVE_TIBIT;
            type  empty;
            description "Use this attribute to turn on debugging for digital diagnostic
                        monitoring";
        } // END of enable-ddm definition.

    } // END of component-hardware-debug definition.
    grouping component-hardware-terminal-debug {
        description
            "Grouping terminal hardware related debug";
        leaf terminal-debug-status-ddm  {
            if-feature feature-list:NOT_HAVE_TIBIT;
            type  cml-data-types:cml_on_off_t;
            description "Use this attribute to see the debugging state for digital diagnostic
                        monitoring";
        } // END of terminal-debug-status-ddm definition.

    } // END of component-hardware-terminal-debug definition.
    grouping platform-component-state {
        description
            "Operational state data for device components";
        leaf type  {
            if-feature feature-list:NOT_HAVE_TIBIT;
            type  ipi-platform-types:cmm_component_type_t;
            description "Type of component as identified by the system";
        } // END of type definition.

        leaf location  {
            if-feature feature-list:NOT_HAVE_TIBIT;
            type  string {
                length "1..1965";
            }
            description "System-supplied description of the location of the
                        component within the system. This could be a bay position,
                        slot number, socket location, etc. For component types that
                        have an explicit slot-id attribute, such as linecards, the
                        system should populate the more specific slot-id.";
        } // END of location definition.

        leaf mfg-name  {
            if-feature feature-list:NOT_HAVE_TIBIT;
            type  string {
                length "1..1965";
            }
            description "System-supplied identifier for the manufacturer of the component.This
                        data is particularly useful when a component manufacturer is different
                        than the overall device vendor.";
        } // END of mfg-name definition.

        leaf mfg-date  {
            if-feature feature-list:NOT_HAVE_TIBIT;
            type  yang:date-and-time {
                pattern "\\d{4}-\\d{2}-\\d{2}T\\d{2}:\\d{2}:\\d{2}(\\.\\d+)?(Z|[\\+\\-]\\d{2}:\\d{2})";
                }
                description "System-supplied representation of the component's manufacturing date.";
            } // END of mfg-date definition.

            leaf description  {
                if-feature feature-list:NOT_HAVE_TIBIT;
                type  string {
                    length "1..1965";
                }
                description "System-supplied description of the component.";
            } // END of description definition.

            leaf hardware-version  {
                if-feature feature-list:NOT_HAVE_TIBIT;
                type  string {
                    length "1..1965";
                }
                description "For hardware components, this is the hardware revision of the
                            component.";
            } // END of hardware-version definition.

            leaf firmware-version  {
                if-feature feature-list:NOT_HAVE_TIBIT;
                type  string {
                    length "1..1965";
                }
                description "For hardware components, this is the version of associated firmware
                            that is running on the component, if applicable.";
            } // END of firmware-version definition.

            leaf software-version  {
                if-feature feature-list:NOT_HAVE_TIBIT;
                type  string {
                    length "1..1965";
                }
                description "For software components such as operating system or other software
                            module,this is the version of the currently running software.";
            } // END of software-version definition.

            leaf serial-no  {
                if-feature feature-list:NOT_HAVE_TIBIT;
                type  string {
                    length "1..1965";
                }
                description "System-assigned serial number of the component.";
            } // END of serial-no definition.

            leaf part-no  {
                if-feature feature-list:NOT_HAVE_TIBIT;
                type  string {
                    length "1..1965";
                }
                description "System-assigned part number for the component.This should be present
                            in particular if the component is also an FRU(field replaceable unit).";
            } // END of part-no definition.

            leaf removable  {
                if-feature feature-list:NOT_HAVE_TIBIT;
                type  boolean;
                description "If true,this component is removable or is a field replaceable unit";
            } // END of removable definition.

            leaf oper-status  {
                if-feature feature-list:NOT_HAVE_TIBIT;
                type  ipi-platform-types:cmm_component_oper_status_t;
                description "If applicable,this reports the current operational status of the
                            component.";
            } // END of oper-status definition.

            leaf product-name  {
                if-feature feature-list:NOT_HAVE_TIBIT;
                type  string {
                    length "1..1965";
                }
                description "Component's product name";
            } // END of product-name definition.

            leaf asset-tag  {
                if-feature feature-list:NOT_HAVE_TIBIT;
                type  string {
                    length "1..1965";
                }
                description "Component's asset tag";
            } // END of asset-tag definition.

            leaf-list component-additional-details  {
                if-feature feature-list:NOT_HAVE_TIBIT;
                type  string {
                    length "1..1965";
                    pattern "[^?' =,>|]+";
                }
                description "Component's extra details";
            } // END of component-additional-details definition.

            leaf parent  {
                if-feature feature-list:NOT_HAVE_TIBIT;
                type  leafref {
                    path  "/components/component/state/name";
                }
                description "Reference to the name of the parent component.";
            } // END of parent definition.

            leaf empty  {
                if-feature feature-list:NOT_HAVE_TIBIT;
                type  boolean;
                description "If true indicates that a component position (slot) is not populated";
            } // END of empty definition.

    } // END of platform-component-state definition.
    grouping platform-component-memory-state {
        description
            "Per-component memory statistics";
        container memory {
            if-feature feature-list:NOT_HAVE_TIBIT;
            config false;
            description
                "For components that have associated memory, these values
                        report information about available and utilized memory";
            uses component-memory-state-detail;
        } // END of memory-container definition.
    } // END of platform-component-memory-state definition.
    grouping platform-component-board-state {
        description
            "Per-component board state";
        container board-fru {
            if-feature feature-list:NOT_HAVE_TIBIT;
            config false;
            description
                "For components that have associated board fru details";
            uses component-board-state-detail;
        } // END of board-fru-container definition.
    } // END of platform-component-board-state definition.
    grouping component-hardware-global {
        description
            "Platform hardware global states";
        leaf locator-led-enable  {
            if-feature feature-list:NOT_HAVE_TIBIT;
            type  empty;
            description "To set the locator-led on or off.";
        } // END of locator-led-enable definition.

        leaf ddm-monitor-time-interval  {
            if-feature feature-list:NOT_HAVE_TIBIT;
            type  uint16 {
                 range "60..3600"  {
                    description "60..3600: Supported range 60 - 3600";
                 }
            }
            description "To set DDM Monitor interval time.";
        } // END of ddm-monitor-time-interval definition.

        leaf cpu-core-usage-monitor-interval  {
            if-feature feature-list:NOT_HAVE_TIBIT;
            type  uint16 {
                 range "60..600"  {
                    description "60..600: Supported range 60 - 600";
                 }
            }
            description "To set CPU core usage monitor interval time";
        } // END of cpu-core-usage-monitor-interval definition.

        leaf vpiu-control-vlan  {
            if-feature feature-list:HAVE_VPIU_EMULATION;
            type  uint16 {
                 range "2..4094"  {
                    description "2..4094: Supported range 2 - 4094";
                 }
            }
            description "To set Video PIU Command VLAN.";
        } // END of vpiu-control-vlan definition.

        leaf enable-ddm-monitor  {
            if-feature feature-list:NOT_HAVE_TIBIT;
            type  empty;
            description "To enable DDM monitor for all transceivers.";
        } // END of enable-ddm-monitor definition.

        leaf gps-satellite  {
            if-feature feature-list:HAVE_PTP_HW_OFFLOAD_CUSTOM1;
            type  ipi-platform-types:gps_satellite_system_t;
            description "Configure satellite system";
        } // END of gps-satellite definition.

    } // END of component-hardware-global definition.
    grouping gps-position-config {
        description
            "Grouping for gps position";
        choice gps-position-option {
            description
                "Use this attribute to choose between position option";
            case gps-position-disable {

                description
                    "Use this attribute to choose position disable.";

                leaf gps-position-disable  {
                    type  empty;
                    description "gps postion disable";
                } // END of gps-position-disable definition.

            }
            case gps-survey-in-observation-time {

                description
                    "Use this attribute to choose survey-in.";

                leaf gps-survey-in-observation-time  {
                    // when " ../gps-survey-in-position-accuracy ";
                    type  uint32 {
                         range "1..1440"  {
                            description "1..1440: Supported range 1 - 1440";
                         }
                    }
                    description "GPS observation time";
                } // END of gps-survey-in-observation-time definition.

                leaf gps-survey-in-position-accuracy  {
                    // when " ../gps-survey-in-observation-time ";
                    type  uint32 {
                         range "1..10000"  {
                            description "1..10000: Supported range 1 - 10000";
                         }
                    }
                    description "GPS position accuracy";
                } // END of gps-survey-in-position-accuracy definition.

            }
            case gps-fixed-latitude {

                description
                    "Use this attribute to choose fixed mode.";

                leaf gps-fixed-latitude  {
                    // when " ../gps-fixed-longitude + ../gps-fixed-altitude ";
                    type  decimal64 {
                         fraction-digits 6;                    }
                    description "gps fixed latitude in decimal degree format";
                } // END of gps-fixed-latitude definition.

                leaf gps-fixed-longitude  {
                    // when " ../gps-fixed-latitude + ../gps-fixed-altitude ";
                    type  decimal64 {
                         fraction-digits 6;                    }
                    description "GPS fixed longitude in decimal degree format";
                } // END of gps-fixed-longitude definition.

                leaf gps-fixed-altitude  {
                    // when " ../gps-fixed-latitude + ../gps-fixed-longitude ";
                    type  decimal64 {
                         fraction-digits 6;                    }
                    description "GPS fixed altitude in meters";
                } // END of gps-fixed-altitude definition.

            }
        } // END of gps-position-option-choice definition.
    } // END of gps-position-config definition.
    grouping platform-sensor-record {
        description
            "Grouping sensor states";
        container bmc-sensor-data-record {
            if-feature feature-list:NOT_HAVE_TIBIT;
            config false;
            description
                "container enclosing bmc sensor data";
            uses component-bmc-sensor-record-state;
        } // END of bmc-sensor-data-record-container definition.
    } // END of platform-sensor-record definition.
    grouping platform-component-interface {
        description
            "Global interface configuration group";
        container interfaces {
            if-feature feature-list:NOT_HAVE_TIBIT;
            description
                "platform interface properties";
            uses platform-component-interface-list;
        } // END of interfaces-container definition.
    } // END of platform-component-interface definition.
    grouping gps-position-top {
        description
            "gps position configuration parameters";
        container gps-position {
            if-feature feature-list:HAVE_PTP_HW_OFFLOAD;
            description
                "container enclosing gps position parameters";
            container config {
                description
                    "configuration data for gps position";
                uses gps-position-config;
            } // END of config-container definition.
            container state {
                config false;
                description
                    "Global operational data";
                uses gps-position-config;
            } // END of state-container definition.
        } // END of gps-position-container definition.
    } // END of gps-position-top definition.
    grouping platform-component-global {
        description
            "Global configuration group for the platform";
        container global {
            description
                "container enclosing global configuration";
            container config {
                description
                    "configuration data for platform  global configuration";
                uses component-generic-global;
                uses component-hardware-global;
            } // END of config-container definition.
            container state {
                config false;
                description
                    "Global operational data";
                uses component-generic-global;
                uses component-hardware-global;
            } // END of state-container definition.
            uses system-load-cpu-usage-global;
            uses gps-position-top;
            uses gps-state;
            uses dpll-state;
        } // END of global-container definition.
    } // END of platform-component-global definition.
    grouping platform-subcomponent-state {
        description
            "platform-subcomponent-state";
        leaf subcomponent-name  {
            type  leafref {
                path  "/components/component/state/name";
            }
            description "Reference to the name of the subcomponent";
        } // END of subcomponent-name definition.

    } // END of platform-subcomponent-state definition.
    grouping platform-subcomponent-top {
        description
            "platform-subcomponent-top";
        container subcomponents {
            config false;
            description
                "Enclosing container for subcomponent references";

            list subcomponent {
                key "subcomponent-name";
                config false;
                description
                    "List of subcomponent references";
                leaf subcomponent-name  {
                    type  leafref {
                        path  "../state/subcomponent-name";
                    }
                    description "References the component name";
                } // END of subcomponent-name definition.

                container state {
                    config false;
                    description
                        "Operational state data for the subcomponent";
                    uses platform-subcomponent-state;
                } // END of state-container definition.
            } // End of subcomponent-list
        } // END of subcomponents-container definition.
    } // END of platform-subcomponent-top definition.
    grouping platform-component-debug {
        description
            "Global debug configuration group";
        container debug {
            description
                "configuration data for debug configuration";
            container config {
                description
                    "configuration data for cmm debug configuration";
                uses component-generic-debug;
                uses component-hardware-debug;
            } // END of config-container definition.
            container state {
                config false;
                description
                    "Operational data for debug";
                uses component-generic-debug;
                uses component-hardware-debug;
                uses component-generic-terminal-debug;
                uses component-hardware-terminal-debug;
            } // END of state-container definition.
        } // END of debug-container definition.
    } // END of platform-component-debug definition.
    grouping disk-activity-attributes {
        description
            "Grouping for disk activity attributes";
        leaf interval  {
            type  uint16 {
                 range "30..1200"  {
                    description "30..1200: Supported range 30 - 1200";
                 }
            }
            description "To set disk activity sampling window interval time.";
        } // END of interval definition.

        leaf read-threshold  {
            type  uint32 {
                 range "1..20000"  {
                    description "1..20000: Supported range 1 - 20000";
                 }
            }
            description "To set disk read activity alarm threshold.";
        } // END of read-threshold definition.

        leaf write-threshold  {
            type  uint32 {
                 range "1..20000"  {
                    description "1..20000: Supported range 1 - 20000";
                 }
            }
            description "To set disk write activity alarm threshold.";
        } // END of write-threshold definition.

    } // END of disk-activity-attributes definition.
    grouping fan-duty-cycle-config {
        description
            "Grouping for fan-duty-cycle";
        leaf fan-duty  {
            type  uint8 {
                 range "0..100"  {
                    description "0..100: Supported range 0 - 100";
                 }
            }
            description "To configure the fan duty cycle";
        } // END of fan-duty definition.

    } // END of fan-duty-cycle-config definition.
    grouping platform-component-fan-duty-cyle {
        description
            "Grouping for fan-duty-cyle";
        container fan-duty-cycle {
            description
                "fan duty cycle container";
            container config {
                description
                    "Configuration data for fan duty cycle";
                uses fan-duty-cycle-config;
            } // END of config-container definition.
            container state {
                config false;
                description
                    "Operational state data for fan-duty-cycle";
                uses fan-duty-cycle-config;
            } // END of state-container definition.
        } // END of fan-duty-cycle-container definition.
    } // END of platform-component-fan-duty-cyle definition.
    grouping platform-component-disk-activity {
        description
            "Grouping for disk activity component";
        container disk-activity-monitoring {
            description
                "Enclosing container for disk activity monitoring attributes";
            container config {
                description
                    "configuration data";
                uses disk-activity-attributes;
            } // END of config-container definition.
            container state {
                config false;
                description
                    "operational data";
                uses disk-activity-attributes;
            } // END of state-container definition.
        } // END of disk-activity-monitoring-container definition.
    } // END of platform-component-disk-activity definition.
    grouping platform-component-temperature-config {
        description
            "Grouping for temperature config attributes";
        leaf temperature-policy  {
            type  ipi-platform-types:cml_temp_policy_t;
            description "Set temperature policy";
        } // END of temperature-policy definition.

    } // END of platform-component-temperature-config definition.
    grouping platform-temperature-severity-config {
        description
            "Config level grouping for temperature severity";
        leaf severity  {
            type  ipi-platform-types:cml_temp_threshold_t;
            description "Temperature threshold severity";
        } // END of severity definition.

        leaf value  {
            type  int16 {
                 range "-50..150"  {
                    description "-50..150: Supported range -50 - 150";
                 }
            }
            description "Value to over-write temperature sensor threshold";
        } // END of value definition.

    } // END of platform-temperature-severity-config definition.
    grouping platform-temperature-severities-top {
        description
            "Top level grouping for temperature severities";
        container severities {
            description
                "Top level container for temperature severities list";

            list severity {
                key "severity";
                description
                    "Temperature severities list";
                leaf severity  {
                    type  leafref {
                        path  "../config/severity";
                    }
                    description "Temperature threshold severity";
                } // END of severity definition.

                container config {
                    description
                        "Configuration data";
                    uses platform-temperature-severity-config;
                } // END of config-container definition.
                container state {
                    config false;
                    description
                        "Operational data";
                    uses platform-temperature-severity-config;
                } // END of state-container definition.
            } // End of severity-list
        } // END of severities-container definition.
    } // END of platform-temperature-severities-top definition.
    grouping platform-temperature-threshold-config {
        description
            "Config level grouping for temperature threshold";
        leaf sensor-id  {
            type  uint8 {
                 range "1..15"  {
                    description "1..15: Supported range 1 - 15";
                 }
            }
            description "Temperature sensor ID";
        } // END of sensor-id definition.

    } // END of platform-temperature-threshold-config definition.
    grouping platform-temperature-thresholds-top {
        description
            "Top level grouping for temperature thresholds";
        container thresholds {
            description
                "Top level container for temperature thresholds list";

            list threshold {
            // when "                  ipi-platform:components/temperature/thresholds/threshold/severities/severity/config/value ";
                key "sensor-id";
                description
                    "Temperature thresholds list";
                leaf sensor-id  {
                    type  leafref {
                        path  "../config/sensor-id";
                    }
                    description "Sensor ID";
                } // END of sensor-id definition.

                container config {
                    description
                        "Configuration data";
                    uses platform-temperature-threshold-config;
                } // END of config-container definition.
                container state {
                    config false;
                    description
                        "Operational data";
                    uses platform-temperature-threshold-config;
                } // END of state-container definition.
                uses platform-temperature-severities-top;
            } // End of threshold-list
        } // END of thresholds-container definition.
    } // END of platform-temperature-thresholds-top definition.
    grouping platform-component-temperature {
        description
            "Grouping for temperature sensor component";
        container temperature {
            description
                "Set temperature threshold";
            container config {
                description
                    "configuration data";
                uses platform-component-temperature-config;
            } // END of config-container definition.
            container state {
                config false;
                description
                    "Operational data";
                uses platform-component-temperature-config;
            } // END of state-container definition.
            uses platform-temperature-thresholds-top;
        } // END of temperature-container definition.
    } // END of platform-component-temperature definition.
    grouping platform-component-phyport-config {
        description
            "Config level grouping for phyport configuration";
        leaf ifname  {
            type  string {
                length "1..1965";
                pattern "[^?' =,>|]+";
            }
            description "Phy port interface name";
        } // END of ifname definition.

        leaf disable  {
            type  empty;
            description "Disable the phy port";
        } // END of disable definition.

    } // END of platform-component-phyport-config definition.
    grouping platform-component-phyport {
        description
            "Global phyport configuration group";
        container phyports {
            description
                "platform phyport properties";

            list phyport {
            // when " ipi-platform:components/phyports/phyport/config/disable ";
                key "ifname";
                description
                    "platform phyport list";
                leaf ifname  {
                    type  leafref {
                        path  "../config/ifname";
                    }
                    description "Phy port interface name";
                } // END of ifname definition.

                container config {
                    description
                        "Configuration data";
                    uses platform-component-phyport-config;
                } // END of config-container definition.
                container state {
                    config false;
                    description
                        "Operational data";
                    uses platform-component-phyport-config;
                } // END of state-container definition.
            } // End of phyport-list
        } // END of phyports-container definition.
    } // END of platform-component-phyport definition.

    grouping  components-grouping {
    description
        "Enclosing container for the components in the system.";
    container components {
        if-feature feature-list:HAVE_CMMD;
        description
            "Enclosing container for the components in the system.";

        list component {
            key "name";
            config false;
            description
                "List of components, keyed by component name.";
            leaf name  {
                type  leafref {
                    path  "../state/name";
                }
                description "References the component name";
            } // END of name definition.

            container state {
                config false;
                description
                    "Operational state data for each component";
                leaf name  {
                    type  string {
                        length "1..1965";
                    }
                    description "References the component name";
                } // END of name definition.

                uses platform-component-state;
                uses platform-component-memory-state;
                uses platform-component-board-state;
                uses temperature-grouping;
            } // END of state-container definition.
            uses platform-sensor-record;
            uses platform-subcomponent-top;
            uses cpu-grouping;
            uses storage-grouping;
            uses ram-grouping;
            uses transceiver-grouping;
            uses power-supply-grouping;
            uses fan-grouping;
            uses fan-tray-grouping;
            uses chassis-grouping;
            uses linecard-grouping;
            uses power-rail-grouping;
            uses ceragon-grouping;
            uses edfas-grouping;
            uses remote-sfps-grouping;
        } // End of component-list
        uses platform-component-debug;
        uses platform-component-global;
        uses platform-component-interface;
        uses platform-component-disk-activity;
        uses platform-component-temperature;
        uses platform-component-fan-duty-cyle;
        uses platform-component-phyport;
    } // END of components-container definition.
    } // END of components-grouping definition.

    uses components-grouping;
    uses forwarding-profile-route-modes-grouping;
    uses profiles-grouping;
    uses hardware-grouping;
    uses mvl-hardware-grouping;
    uses qsfp-dds-grouping;
    uses xcvrs-grouping;
    uses remote-xcvrs-grouping;
    uses xcvr-global-grouping;

    rpc transceiver-cmis-write {
        if-feature feature-list:HAVE_CMMD;
        if-feature feature-list:NOT_HAVE_TIBIT;
        description "Use this RPC to make a netconf write operation to set custom pages
                    data";
        input  {
            leaf component-name  {
                type string;
                mandatory true;
                description "Component name";
            }
            leaf bank  {
                type uint8;
                mandatory true;
                description "Bank number";
            }
            leaf page  {
                type uint8;
                mandatory true;
                description "Memory page identifier";
            }
            leaf offset  {
                type uint8;
                mandatory true;
                description "Memory page offset";
            }
            leaf size  {
                type int16 {
                    range "1..256";
                }
                mandatory true;
                description "Memory page size";
            }
            leaf value  {
                type string {
                    length "2..512";
                }
                mandatory true;
                description "";
            }
        }
    }

    rpc transceiver-cmis-read {
        if-feature feature-list:HAVE_CMMD;
        if-feature feature-list:NOT_HAVE_TIBIT;
        description "Use this RPC to make a netconf read operation that will fetch data
                    from custom pages";
        input  {
            leaf component-name  {
                type string;
                mandatory true;
                description "Component name";
            }
            leaf bank  {
                type uint8;
                mandatory true;
                description "Bank number";
            }
            leaf page  {
                type uint8;
                mandatory true;
                description "Memory page identifier";
            }
            leaf offset  {
                type uint8;
                mandatory true;
                description "Memory page offset";
            }
            leaf size  {
                type int16 {
                    range "1..256";
                }
                mandatory true;
                description "Memory page size";
            }
        }
        output  {
            leaf result  {
                type string {
                    length "2..512";
                }
                mandatory true;
                description "";
            }
        }
    }

    rpc clear-xcvr-alarm-all {
        if-feature feature-list:HAVE_XCVR_MODEL;
        if-feature feature-list:HAVE_CMMD;
        if-feature feature-list:NOT_HAVE_TIBIT;
        description "Use clear-xcvr-alarm-all to clear alarms from all transceivers";
    }

    rpc clear-xcvr-alarm {
        if-feature feature-list:HAVE_XCVR_MODEL;
        if-feature feature-list:HAVE_CMMD;
        if-feature feature-list:NOT_HAVE_TIBIT;
        description "Use clear-xcvr-alarm to clear alarm from a specific transceiver";
        input  {
            leaf port  {
                type uint8 {
                    range "1..255";
                }
                mandatory true;
                description "Internal port number";
            }
        }
    }

    rpc tibit-olt-microplug-set-management-vlan-tpid {
        if-feature feature-list:NOT_HAVE_TIBIT;
        if-feature feature-list:HAVE_CMMD;
        description "Use this command to set the management VLAN TPID for the Tibit OLT
                    MicroPlug. The OLT will use this management VLAN TPID after rebooting";
        input  {
            leaf interface-name  {
                type string;
                mandatory true;
                description "The Tibit OLT interface name";
            }
            leaf vlan-tpid  {
                type ipi-platform-transceiver-tibit-types:trans_tibit_cmm_tpid_t;
                mandatory true;
                description "The Tibit OLT management VLAN TPID. The OLT will use this management
                            VLAN TPID after rebooting";
            }
        }
    }

    rpc tibit-olt-microplug-set-management-vlan-id {
        if-feature feature-list:NOT_HAVE_TIBIT;
        if-feature feature-list:HAVE_CMMD;
        description "Use this command to set the management VLAN ID for the Tibit OLT
                    MicroPlug. The OLT will use this management VLAN ID after rebooting";
        input  {
            leaf interface-name  {
                type string;
                mandatory true;
                description "The Tibit OLT interface name";
            }
            leaf vlan-id  {
                type uint16 {
                    range "1..4094";
                }
                mandatory true;
                description "The Tibit OLT management VLAN ID. The OLT will use this management
                            VLAN ID after rebooting";
            }
        }
    }

    rpc tibit-olt-microplug-set-ethernet-mac-address {
        if-feature feature-list:NOT_HAVE_TIBIT;
        if-feature feature-list:HAVE_CMMD;
        description "Use this command to set the Ethernet side MAC address for the Tibit
                    OLT MicroPlug";
        input  {
            leaf interface-name  {
                type string;
                mandatory true;
                description "Tibit OLT interface name";
            }
            leaf mac-address  {
                type yang:mac-address;
                mandatory true;
                description "The Tibit OLT ethernet MAC address";
            }
        }
    }

    rpc tibit-olt-microplug-set-next-active-firmware-bank {
        if-feature feature-list:NOT_HAVE_TIBIT;
        if-feature feature-list:HAVE_CMMD;
        description "Use this command to set the next active firmwate bank for the Tibit
                    OLT MicroPlug after rebooting";
        input  {
            leaf interface-name  {
                type string;
                mandatory true;
                description "The Tibit OLT interface name";
            }
            leaf bank-id  {
                type uint8 {
                    range "0..3";
                }
                mandatory true;
                description "The Tibit OLT firmware bank ID. The OLT will use the firmware in this
                            bank after rebooting";
            }
        }
    }

    rpc tibit-olt-microplug-reboot {
        if-feature feature-list:NOT_HAVE_TIBIT;
        if-feature feature-list:HAVE_CMMD;
        description "Use this command to reboot Tibit OLT MicroPlug";
        input  {
            leaf interface-name  {
                type string;
                mandatory true;
                description "The Tibit OLT interface name";
            }
        }
    }

    rpc ddm-clear-transceiver-alarm-all {
        if-feature feature-list:NOT_HAVE_TIBIT;
        if-feature feature-list:HAVE_CMMD;
        description "Use ddm-clear-transceiver-alarm-all to clear alarms from all
                    transceivers";
    }

    rpc ddm-clear-transceiver-alarm {
        if-feature feature-list:NOT_HAVE_TIBIT;
        if-feature feature-list:HAVE_CMMD;
        description "Use ddm-clear-transceiver-alarm-all to clear alarm from transceiver";
        input  {
            leaf name  {
                type string;
                mandatory true;
                description "Use this rpc attribute to clear transceiver alarm";
            }
        }
    }

    rpc cmm-terminal-debug-ddm-on {
        if-feature feature-list:NOT_HAVE_TIBIT;
        if-feature feature-list:HAVE_CMMD;
        description "Use debug-ddm-on to enable debug for digital diagnostic monitoring";
    }

    rpc cmm-terminal-debug-ddm-off {
        if-feature feature-list:NOT_HAVE_TIBIT;
        if-feature feature-list:HAVE_CMMD;
        description "Use debug-ddm-off to disable debug for digital diagnostic monitoring";
    }

    rpc cmm-terminal-debug-cmm-on {
        if-feature feature-list:HAVE_CMMD;
        description "Use debug-cmm-on to enable debug for chassis monitoring";
    }

    rpc cmm-terminal-debug-cmm-off {
        if-feature feature-list:HAVE_CMMD;
        description "Use debug-cmm-off to disable debug for chassis monitoring";
    }

    rpc gps-survey-restart {
        if-feature feature-list:HAVE_PTP_HW_OFFLOAD;
        if-feature feature-list:HAVE_CMMD;
        description "use this command to restart the gps survey";
    }

    notification bmc-lower-non-critical-low-threshold-notification {
        if-feature feature-list:HAVE_CMMD;
        if-feature feature-list:NOT_HAVE_TIBIT;

        description "Notification for lower non critical low event.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf lower-non-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-non-critical-high-threshold-notification {
        if-feature feature-list:HAVE_CMMD;
        if-feature feature-list:NOT_HAVE_TIBIT;

        description "Notification for lower non critical high event.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf lower-non-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-critical-low-threshold-notification {
        if-feature feature-list:HAVE_CMMD;
        if-feature feature-list:NOT_HAVE_TIBIT;

        description "Notification for lower critical low event.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf lower-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-critical-high-threshold-notification {
        if-feature feature-list:HAVE_CMMD;
        if-feature feature-list:NOT_HAVE_TIBIT;

        description "Notification for lower critical high event.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf lower-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-non-recoverable-low-threshold-notification {
        if-feature feature-list:HAVE_CMMD;
        if-feature feature-list:NOT_HAVE_TIBIT;

        description "Notification for lower non recoverable low event.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf lower-non-recoverable {
            type  decimal64 {
                 fraction-digits 3;            }
        description
            "lower non recoverable sensor threshold.-100002 represents not
                    applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-non-recoverable-high-threshold-notification {
        if-feature feature-list:HAVE_CMMD;
        if-feature feature-list:NOT_HAVE_TIBIT;

        description "Notification for lower non recoverable high event.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf lower-non-recoverable {
            type  decimal64 {
                 fraction-digits 3;            }
        description
            "lower non recoverable sensor threshold.-100002 represents not
                    applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-critical-low-threshold-notification {
        if-feature feature-list:HAVE_CMMD;
        if-feature feature-list:NOT_HAVE_TIBIT;

        description "Notification for upper non critical low event.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf upper-non-critical {
            type  decimal64 {
                 fraction-digits 3;            }
        description
            "upper non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-critical-high-threshold-notification {
        if-feature feature-list:HAVE_CMMD;
        if-feature feature-list:NOT_HAVE_TIBIT;

        description "Notification for upper non critical high event.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf upper-non-critical {
            type  decimal64 {
                 fraction-digits 3;            }
        description
            "upper non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-critical-low-threshold-notification {
        if-feature feature-list:HAVE_CMMD;
        if-feature feature-list:NOT_HAVE_TIBIT;

        description "Notification for upper critical low event.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf upper-critical {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-critical-high-threshold-notification {
        if-feature feature-list:HAVE_CMMD;
        if-feature feature-list:NOT_HAVE_TIBIT;

        description "Notification for upper critical high event.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf upper-critical {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-recoverable-low-threshold-notification {
        if-feature feature-list:HAVE_CMMD;
        if-feature feature-list:NOT_HAVE_TIBIT;

        description "Notification for upper non recoverable low event.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf upper-non-recoverable {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-recoverable-high-threshold-notification {
        if-feature feature-list:HAVE_CMMD;
        if-feature feature-list:NOT_HAVE_TIBIT;

        description "Notification for upper non recoverable high threshold high event.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf upper-non-recoverable {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-device-state-notification {
        if-feature feature-list:HAVE_CMMD;
        if-feature feature-list:NOT_HAVE_TIBIT;

        description "Notification for operational state of the device.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf operational-status {
            type  string;
        description
            "Sensor's operational state";
        }
    }

    notification cpu-load-15min-alert {
        if-feature feature-list:HAVE_CMMD;

        description "This notification is sent when CPU utilization average during 15 minutes exceeds the alert threshold.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf cpu-15min-load-percentage {
            type  decimal64 {
                 fraction-digits 2;            }
        description
            "The arithmetic mean value of the percentage measure of the CPU load
                    over 15 minutes interval";
        }

        leaf cpu-15min-alert-threshold {
            type  uint8;
        description
            "CPU load threshold during 15 minutes interval for alert level";
        }
    }

    notification cpu-load-15min-alert-recovery {
        if-feature feature-list:HAVE_CMMD;

        description "This notification is sent when CPU utilization average during 15 minutes falls bellow the alert threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf cpu-15min-load-percentage {
            type  decimal64 {
                 fraction-digits 2;            }
        description
            "The arithmetic mean value of the percentage measure of the CPU load
                    over 15 minutes interval";
        }

        leaf cpu-15min-alert-threshold {
            type  uint8;
        description
            "CPU load threshold during 15 minutes interval for alert level";
        }
    }

    notification cpu-load-5min-alert {
        if-feature feature-list:HAVE_CMMD;

        description "This notification is sent when CPU utilization average during 5 minutes exceeds the alert threshold.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf cpu-5min-load-percentage {
            type  decimal64 {
                 fraction-digits 2;            }
        description
            "The arithmetic mean value of the percentage measure of the CPU load
                    over 5 minutes interval";
        }

        leaf cpu-5min-alert-threshold {
            type  uint8;
        description
            "CPU load threshold during 5 minutes interval for alert level";
        }
    }

    notification cpu-load-5min-alert-recovery {
        if-feature feature-list:HAVE_CMMD;

        description "This notification is sent when CPU utilization average during 5 minutes falls bellow the alert threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf cpu-5min-load-percentage {
            type  decimal64 {
                 fraction-digits 2;            }
        description
            "The arithmetic mean value of the percentage measure of the CPU load
                    over 5 minutes interval";
        }

        leaf cpu-5min-alert-threshold {
            type  uint8;
        description
            "CPU load threshold during 5 minutes interval for alert level";
        }
    }

    notification cpu-load-1min-critical {
        if-feature feature-list:HAVE_CMMD;

        description "This notification is sent when CPU utilization average during 1 minute exceeds the critical threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf cpu-1min-load-percentage {
            type  decimal64 {
                 fraction-digits 2;            }
        description
            "The arithmetic mean value of the percentage measure of the CPU load
                    over 1 minute interval";
        }

        leaf cpu-1min-critical-threshold {
            type  uint8;
        description
            "CPU load threshold during 1 minute interval for critical level";
        }
    }

    notification cpu-load-1min-critical-recovery {
        if-feature feature-list:HAVE_CMMD;

        description "This notification is sent when CPU utilization average during 1 minute falls bellow the critical threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf cpu-1min-load-percentage {
            type  decimal64 {
                 fraction-digits 2;            }
        description
            "The arithmetic mean value of the percentage measure of the CPU load
                    over 1 minute interval";
        }

        leaf cpu-1min-critical-threshold {
            type  uint8;
        description
            "CPU load threshold during 1 minute interval for critical level";
        }
    }

    notification cpu-load-1min-alert {
        if-feature feature-list:HAVE_CMMD;

        description "This notification is sent when CPU utilization average during 1 minute falls bellow the alert threshold.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf cpu-1min-load-percentage {
            type  decimal64 {
                 fraction-digits 2;            }
        description
            "The arithmetic mean value of the percentage measure of the CPU load
                    over 1 minute interval";
        }

        leaf cpu-1min-alert-threshold {
            type  uint8;
        description
            "CPU load threshold during 1 minute interval for alert level";
        }
    }

    notification cpu-load-1min-alert-recovery {
        if-feature feature-list:HAVE_CMMD;

        description "This notification is sent when CPU utilization average during 1 minute falls bellow the alert threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf cpu-1min-load-percentage {
            type  decimal64 {
                 fraction-digits 2;            }
        description
            "The arithmetic mean value of the percentage measure of the CPU load
                    over 1 minute interval";
        }

        leaf cpu-1min-alert-threshold {
            type  uint8;
        description
            "CPU load threshold during 1 minute interval for alert level";
        }
    }

    notification storage-usage-rising-alert {
        if-feature feature-list:HAVE_CMMD;

        description "Notification for storage when it exceeds alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf used-memory {
            type  uint64;
        description
            "Used memory of the Hard storage.";
        }

        leaf usage-alert-threshold {
            type  int32;
        description
            "Hard disk's usage threshold %  for Alert Level.";
        }

        leaf mount-point {
            type  string;
        description
            "A unique value for each mounted filesystem.";
        }
    }

    notification storage-usage-critical-alert {
        if-feature feature-list:HAVE_CMMD;

        description "Notification for storage when it exceeds critical threshold.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf used-memory {
            type  uint64;
        description
            "Used memory of the Hard storage.";
        }

        leaf usage-critical-threshold {
            type  int32;
        description
            "Hard disk's usage threshold %  for critical level.";
        }

        leaf mount-point {
            type  string;
        description
            "A unique value for each mounted filesystem.";
        }
    }

    notification storage-usage-recovery-from-alert-level {
        if-feature feature-list:HAVE_CMMD;

        description "Notification for storage usage recovery from alert level.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf used-memory {
            type  uint64;
        description
            "Used memory of the Hard storage.";
        }

        leaf usage-alert-threshold {
            type  int32;
        description
            "Hard disk's usage threshold %  for Alert Level.";
        }

        leaf mount-point {
            type  string;
        description
            "A unique value for each mounted filesystem.";
        }
    }

    notification storage-usage-recovery-from-critical-level {
        if-feature feature-list:HAVE_CMMD;

        description "Notification for storage usage recovery from critical level.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf used-memory {
            type  uint64;
        description
            "Used memory of the Hard storage.";
        }

        leaf usage-critical-threshold {
            type  int32;
        description
            "Hard disk's usage threshold %  for critical level.";
        }

        leaf mount-point {
            type  string;
        description
            "A unique value for each mounted filesystem.";
        }
    }

    notification storage-remaining-life-rising-alert {
        if-feature feature-list:HAVE_CMMD;

        description "Notification for storage disk remaining life when it exceeds alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf remaining-life {
            type  int32;
        description
            "Hard disk's Remain life % Values.";
        }

        leaf remain-life-alert-threshold {
            type  int32;
        description
            "Hard disk's Remain Life threshold % for Alert Level.";
        }
    }

    notification storage-remaining-life-rising-critical {
        if-feature feature-list:HAVE_CMMD;

        description "Notification for storage disk remaining life when it exceeds critical threshold.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf remaining-life {
            type  int32;
        description
            "Hard disk's Remain life % Values.";
        }

        leaf remain-life-critical-threshold {
            type  int32;
        description
            "Hard disk's Remain Life threshold % for Critical Level.";
        }
    }

    notification storage-available-reserved-space-rising-alert {
        if-feature feature-list:HAVE_CMMD;

        description "Notification for storage available reserved space when it exceeds alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf available-reserved-space {
            type  int32;
        description
            "Hard disk's Available Reserved Space % values";
        }

        leaf available-reserved-space-alert-threshold {
            type  int32;
        description
            "Hard disk's Available Reserved Space threshold % values for Alert
                    Level.";
        }
    }

    notification storage-available-reserved-space-rising-critical {
        if-feature feature-list:HAVE_CMMD;

        description "Notification for storage available reserved space when it exceeds critical threshold.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf available-reserved-space {
            type  int32;
        description
            "Hard disk's Available Reserved Space % values";
        }

        leaf available-reserved-space-critical-threshold {
            type  int32;
        description
            "Hard disk's Available Reserved Space threshold % values for critical
                    Level.";
        }
    }

    notification storage-reallocated-sector-count-rising-alert {
        if-feature feature-list:HAVE_CMMD;

        description "Notification for storage reallocated-sector-count when it increments by 1%.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf reallocated-sector-count {
            type  int32;
        description
            "Hard disk's Reallocated Sectors Count Percentage.";
        }
    }

    notification storage-uncorrectable-sector-count-rising-critical {
        if-feature feature-list:HAVE_CMMD;

        description "Notification for storage uncorrectable-sector-count when it count increments by 1..";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf uncorrectable-sector-count {
            type  int32;
        description
            "Hard disk's Uncorrectable Sectors Count.";
        }
    }

    notification storage-harddisk-monitoring-read-alert {
        if-feature feature-list:HAVE_CMMD;

        description "Notification for storage harddisk read activity when it exceeds alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf read-average {
            type  int32;
        description
            "Hard disk's average read activity in KBps.";
        }

        leaf read-threshold {
            type  int32;
        description
            "Hard disk's read activity threshold in KBps.";
        }
    }

    notification storage-harddisk-recovery-from-read-alert-level {
        if-feature feature-list:HAVE_CMMD;

        description "Notification for storage harddisk read activity when it recovers from alert level.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf read-average {
            type  int32;
        description
            "Hard disk's average read activity in KBps.";
        }

        leaf read-threshold {
            type  int32;
        description
            "Hard disk's read activity threshold in KBps.";
        }
    }

    notification storage-harddisk-monitoring-write-alert {
        if-feature feature-list:HAVE_CMMD;

        description "Notification for storage harddisk write activity when it exceeds alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf write-average {
            type  int32;
        description
            "Hard disk's average write activity in KBps.";
        }

        leaf write-threshold {
            type  int32;
        description
            "Hard disk's write activity threshold in KBps.";
        }
    }

    notification storage-harddisk-recovery-from-write-alert-level {
        if-feature feature-list:HAVE_CMMD;

        description "Notification for storage harddisk write activity when it recovers from alert level.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf write-average {
            type  int32;
        description
            "Hard disk's average write activity in KBps.";
        }

        leaf write-threshold {
            type  int32;
        description
            "Hard disk's write activity threshold in KBps.";
        }
    }

    notification storage-storage-status-alert {
        if-feature feature-list:HAVE_CMMD;

        description "Notification for storage disk eol status is in alert level.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf storage-status {
            type ipi-platform-types:cml_cmm_storage_status_t;
        description
            "Hard disk's eol status.";
        }
    }

    notification storage-storage-status-critical {
        if-feature feature-list:HAVE_CMMD;

        description "Notification for storage disk eol status is in critical level.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf storage-status {
            type ipi-platform-types:cml_cmm_storage_status_t;
        description
            "Hard disk's eol status.";
        }
    }

    notification ram-usage-rising-critical {
        if-feature feature-list:HAVE_CMMD;

        description "Notification for RAM usage rising critical threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf used-memory {
            type  uint64;
        description
            "CPU RAM's used memory available for utilisation in MBytes.";
        }

        leaf usage-critical-threshold {
            type  uint32;
        description
            "RAM usage threshold % for critical level.";
        }
    }

    notification ram-usage-rising-alert {
        if-feature feature-list:HAVE_CMMD;

        description "Notification for RAM usage rising alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf used-memory {
            type  uint64;
        description
            "CPU RAM's used memory available for utilisation in MBytes.";
        }

        leaf usage-alert-threshold {
            type  uint32;
        description
            "RAM usage threshold % for alert level.";
        }
    }

    notification ram-usage-recovery-from-critical-level {
        if-feature feature-list:HAVE_CMMD;

        description "Notification for RAM usage recovery from critical threshold.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf used-memory {
            type  uint64;
        description
            "CPU RAM's used memory available for utilisation in MBytes.";
        }

        leaf usage-critical-threshold {
            type  uint32;
        description
            "RAM usage threshold % for critical level.";
        }
    }

    notification ram-usage-recovery-from-alert-level {
        if-feature feature-list:HAVE_CMMD;

        description "Notification for RAM usage recovery from alert threshold.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf used-memory {
            type  uint64;
        description
            "CPU RAM's used memory available for utilisation in MBytes.";
        }

        leaf usage-alert-threshold {
            type  uint32;
        description
            "RAM usage threshold % for alert level.";
        }
    }

    notification transceiver-inserted {
        if-feature feature-list:HAVE_CMMD;
        if-feature feature-list:NOT_HAVE_TIBIT;

        description "Notification triggered when a transceiver is inserted..";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf port-no {
            type  uint8;
        description
            "Transceiver port number";
        }

        leaf type {
            type ipi-platform-transceiver-types:ddm_cmm_trans_type_t;
        description
            "Type of the transceiver SFP/QSFP.";
        }

        leaf vendor-name {
            type  string;
        description
            "Transceiver vendor name.";
        }

        leaf vendor-serial-number {
            type  string;
        description
            "Serial number provided by vendor.";
        }

        leaf connector-type {
            type ipi-platform-sff8024-types:cmm_sff8024_connector_type_t;
        description
            "Connector type for the transceiver.";
        }
    }

    notification transceiver-removed {
        if-feature feature-list:HAVE_CMMD;
        if-feature feature-list:NOT_HAVE_TIBIT;

        description "Notification triggered when a transceiver is removed..";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf port-no {
            type  uint8;
        description
            "Transceiver port number";
        }

        leaf type {
            type ipi-platform-transceiver-types:ddm_cmm_trans_type_t;
        description
            "Type of the transceiver SFP/QSFP.";
        }

        leaf vendor-name {
            type  string;
        description
            "Transceiver vendor name.";
        }

        leaf vendor-serial-number {
            type  string;
        description
            "Serial number provided by vendor.";
        }

        leaf connector-type {
            type ipi-platform-sff8024-types:cmm_sff8024_connector_type_t;
        description
            "Connector type for the transceiver.";
        }
    }

    notification faulty-transceiver-inserted {
        if-feature feature-list:HAVE_CMMD;
        if-feature feature-list:NOT_HAVE_TIBIT;

        description "Notification triggered when a faulty transceiver is inserted..";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf port-no {
            type  uint8;
        description
            "Transceiver port number";
        }

        leaf type {
            type ipi-platform-transceiver-types:ddm_cmm_trans_type_t;
        description
            "Type of the transceiver SFP/QSFP.";
        }
    }

    notification incompatible-transceiver-inserted {
        if-feature feature-list:HAVE_CMMD;
        if-feature feature-list:NOT_HAVE_TIBIT;

        description "Notification triggered when an incompatible transceiver is inserted..";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf port-no {
            type  uint8;
        description
            "Transceiver port number";
        }
    }

    notification incompatible-transceiver-removed {
        if-feature feature-list:HAVE_CMMD;
        if-feature feature-list:NOT_HAVE_TIBIT;

        description "Notification triggered when an incompatible transceiver is removed..";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf port-no {
            type  uint8;
        description
            "Transceiver port number";
        }
    }

    notification frequency-error-high-critical {
        if-feature feature-list:HAVE_CMMD;
        if-feature feature-list:NOT_HAVE_TIBIT;

        description "This notification is sent when frequency-error register exceeds the high-critical threshold.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf frequency-error {
            type  decimal64 {
                 fraction-digits 2;            }
        description
            "Transceiver frequency error";
        }

        leaf frequency-error-critical-min-threshold {
            type  decimal64 {
                 fraction-digits 2;            }
        description
            "The minimum critical threshold for transceiver frequency-error";
        }

        leaf frequency-error-critical-max-threshold {
            type  decimal64 {
                 fraction-digits 2;            }
        description
            "The maximum critical threshold for transceiver frequency-error";
        }
    }

    notification frequency-error-low-critical {
        if-feature feature-list:HAVE_CMMD;
        if-feature feature-list:NOT_HAVE_TIBIT;

        description "This notification is sent when frequency-error register exceeds the low-critical threshold.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf frequency-error {
            type  decimal64 {
                 fraction-digits 2;            }
        description
            "Transceiver frequency error";
        }

        leaf frequency-error-critical-min-threshold {
            type  decimal64 {
                 fraction-digits 2;            }
        description
            "The minimum critical threshold for transceiver frequency-error";
        }

        leaf frequency-error-critical-max-threshold {
            type  decimal64 {
                 fraction-digits 2;            }
        description
            "The maximum critical threshold for transceiver frequency-error";
        }
    }

    notification frequency-error-high-alert {
        if-feature feature-list:HAVE_CMMD;
        if-feature feature-list:NOT_HAVE_TIBIT;

        description "This notification is sent when frequency-error register exceeds the high-alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf frequency-error {
            type  decimal64 {
                 fraction-digits 2;            }
        description
            "Transceiver frequency error";
        }

        leaf frequency-error-alert-min-threshold {
            type  decimal64 {
                 fraction-digits 2;            }
        description
            "The minimum alert threshold for transceiver frequency-error";
        }

        leaf frequency-error-alert-max-threshold {
            type  decimal64 {
                 fraction-digits 2;            }
        description
            "The maximum alert threshold for transceiver frequency-error";
        }
    }

    notification frequency-error-low-alert {
        if-feature feature-list:HAVE_CMMD;
        if-feature feature-list:NOT_HAVE_TIBIT;

        description "This notification is sent when frequency-error register exceeds the low-alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf frequency-error {
            type  decimal64 {
                 fraction-digits 2;            }
        description
            "Transceiver frequency error";
        }

        leaf frequency-error-alert-min-threshold {
            type  decimal64 {
                 fraction-digits 2;            }
        description
            "The minimum alert threshold for transceiver frequency-error";
        }

        leaf frequency-error-alert-max-threshold {
            type  decimal64 {
                 fraction-digits 2;            }
        description
            "The maximum alert threshold for transceiver frequency-error";
        }
    }

    notification frequency-error-recovery {
        if-feature feature-list:HAVE_CMMD;
        if-feature feature-list:NOT_HAVE_TIBIT;

        description "This notification is sent when frequency-error register exceeds threshold.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf frequency-error {
            type  decimal64 {
                 fraction-digits 2;            }
        description
            "Transceiver frequency error";
        }
    }

    notification wavelength-error-high-critical {
        if-feature feature-list:HAVE_CMMD;
        if-feature feature-list:NOT_HAVE_TIBIT;

        description "This notification is sent when wavelength-error register exceeds the high-critical threshold.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf wavelength-error {
            type  decimal64 {
                 fraction-digits 4;            }
        description
            "Transceiver wavelength error";
        }

        leaf wavelength-error-critical-min-threshold {
            type  decimal64 {
                 fraction-digits 4;            }
        description
            "The minimum critical threshold for transceiver wavelength-error";
        }

        leaf wavelength-error-critical-max-threshold {
            type  decimal64 {
                 fraction-digits 4;            }
        description
            "The maximum critical threshold for transceiver wavelength-error";
        }
    }

    notification wavelength-error-low-critical {
        if-feature feature-list:HAVE_CMMD;
        if-feature feature-list:NOT_HAVE_TIBIT;

        description "This notification is sent when wavelength-error register exceeds the low-critical threshold.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf wavelength-error {
            type  decimal64 {
                 fraction-digits 4;            }
        description
            "Transceiver wavelength error";
        }

        leaf wavelength-error-critical-min-threshold {
            type  decimal64 {
                 fraction-digits 4;            }
        description
            "The minimum critical threshold for transceiver wavelength-error";
        }

        leaf wavelength-error-critical-max-threshold {
            type  decimal64 {
                 fraction-digits 4;            }
        description
            "The maximum critical threshold for transceiver wavelength-error";
        }
    }

    notification wavelength-error-high-alert {
        if-feature feature-list:HAVE_CMMD;
        if-feature feature-list:NOT_HAVE_TIBIT;

        description "This notification is sent when wavelength-error register exceeds the high-alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf wavelength-error {
            type  decimal64 {
                 fraction-digits 4;            }
        description
            "Transceiver wavelength error";
        }

        leaf wavelength-error-alert-min-threshold {
            type  decimal64 {
                 fraction-digits 4;            }
        description
            "The minimum alert threshold for transceiver wavelength-error";
        }

        leaf wavelength-error-alert-max-threshold {
            type  decimal64 {
                 fraction-digits 4;            }
        description
            "The maximum alert threshold for transceiver wavelength-error";
        }
    }

    notification wavelength-error-low-alert {
        if-feature feature-list:HAVE_CMMD;
        if-feature feature-list:NOT_HAVE_TIBIT;

        description "This notification is sent when wavelength-error register exceeds the low-alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf wavelength-error {
            type  decimal64 {
                 fraction-digits 4;            }
        description
            "Transceiver wavelength error";
        }

        leaf wavelength-error-alert-min-threshold {
            type  decimal64 {
                 fraction-digits 4;            }
        description
            "The minimum alert threshold for transceiver wavelength-error";
        }

        leaf wavelength-error-alert-max-threshold {
            type  decimal64 {
                 fraction-digits 4;            }
        description
            "The maximum alert threshold for transceiver wavelength-error";
        }
    }

    notification wavelength-error-recovery {
        if-feature feature-list:HAVE_CMMD;
        if-feature feature-list:NOT_HAVE_TIBIT;

        description "This notification is sent when wavelength-error register exceeds threshold.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf wavelength-error {
            type  decimal64 {
                 fraction-digits 4;            }
        description
            "Transceiver wavelength error";
        }
    }

    notification thermoelectric-cooler-fault-alert {
        if-feature feature-list:HAVE_CMMD;
        if-feature feature-list:NOT_HAVE_TIBIT;

        description "This notification is sent when transceiver is on error thermoelectric-cooler-fault.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf thermoelectric-cooler-fault {
            type  boolean;
        description
            "Thermo-electric cooler fault indication";
        }
    }

    notification thermoelectric-cooler-fault-recovery {
        if-feature feature-list:HAVE_CMMD;
        if-feature feature-list:NOT_HAVE_TIBIT;

        description "This notification is sent when transceiver is recovered from error thermoelectric-cooler-fault.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf thermoelectric-cooler-fault {
            type  boolean;
        description
            "Thermo-electric cooler fault indication";
        }
    }

    notification rx-loss-of-signal {
        if-feature feature-list:HAVE_CMMD;
        if-feature feature-list:NOT_HAVE_TIBIT;

        description "This notification is sent when rx_loss is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }
    }

    notification rx-loss-of-signal-recovery {
        if-feature feature-list:HAVE_CMMD;
        if-feature feature-list:NOT_HAVE_TIBIT;

        description "This notification is sent when rx_loss is recovery on qspf/sfp/xfp port.";

        leaf severity {
            type cml-data-types:cml_notif_severity_t;
            description "Notification severity level (value: INFO)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }
    }

    notification input-power-error-high-critical {
        if-feature feature-list:HAVE_CMMD;
        if-feature feature-list:NOT_HAVE_TIBIT;

        description "This notification is sent when critical high input power error is detected on qspf/sfp/xfp port.";

        leaf severity {
            type cml-data-types:cml_notif_severity_t;
            description "Notification severity level (value: MAJOR)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf input-power {
            type  decimal64 {
                 fraction-digits 3;            }
        description
            "Measured RX input power in Channel of transceiver.";
        }

        leaf input-power-critical-min-threshold {
            type  decimal64 {
                 fraction-digits 3;            }
        description
            "The minimum Rx critical threshold in Channel of transceiver.";
        }

        leaf input-power-critical-max-threshold {
            type  decimal64 {
                 fraction-digits 3;            }
        description
            "The maximum Rx critical threshold in Channel of transceiver.";
        }
    }

    notification input-power-error-low-critical {
        if-feature feature-list:HAVE_CMMD;
        if-feature feature-list:NOT_HAVE_TIBIT;

        description "This notification is sent when critical low input power error is detected on qspf/sfp/xfp port.";

        leaf severity {
            type cml-data-types:cml_notif_severity_t;
            description "Notification severity level (value: MAJOR)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf input-power {
            type  decimal64 {
                 fraction-digits 3;            }
        description
            "Measured RX input power in Channel of transceiver.";
        }

        leaf input-power-critical-min-threshold {
            type  decimal64 {
                 fraction-digits 3;            }
        description
            "The minimum Rx critical threshold in Channel of transceiver.";
        }

        leaf input-power-critical-max-threshold {
            type  decimal64 {
                 fraction-digits 3;            }
        description
            "The maximum Rx critical threshold in Channel of transceiver.";
        }
    }

    notification input-power-error-high-alert {
        if-feature feature-list:HAVE_CMMD;
        if-feature feature-list:NOT_HAVE_TIBIT;

        description "This notification is sent when alert high input power error is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf input-power {
            type  decimal64 {
                 fraction-digits 3;            }
        description
            "Measured RX input power in Channel of transceiver.";
        }

        leaf input-power-alert-min-threshold {
            type  decimal64 {
                 fraction-digits 3;            }
        description
            "The minimum Rx alert threshold in Channel of transceiver.";
        }

        leaf input-power-alert-max-threshold {
            type  decimal64 {
                 fraction-digits 3;            }
        description
            "The maximum Rx alert threshold in Channel of transceiver.";
        }
    }

    notification input-power-error-low-alert {
        if-feature feature-list:HAVE_CMMD;
        if-feature feature-list:NOT_HAVE_TIBIT;

        description "This notification is sent when alert low input power error is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf input-power {
            type  decimal64 {
                 fraction-digits 3;            }
        description
            "Measured RX input power in Channel of transceiver.";
        }

        leaf input-power-alert-min-threshold {
            type  decimal64 {
                 fraction-digits 3;            }
        description
            "The minimum Rx alert threshold in Channel of transceiver.";
        }

        leaf input-power-alert-max-threshold {
            type  decimal64 {
                 fraction-digits 3;            }
        description
            "The maximum Rx alert threshold in Channel of transceiver.";
        }
    }

    notification input-power-error-recovery {
        if-feature feature-list:HAVE_CMMD;
        if-feature feature-list:NOT_HAVE_TIBIT;

        description "This notification is sent when input power is recovered on qspf/sfp/xfp port.";

        leaf severity {
            type cml-data-types:cml_notif_severity_t;
            description "Notification severity level (value: WARNING)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf input-power {
            type  decimal64 {
                 fraction-digits 3;            }
        description
            "Measured RX input power in Channel of transceiver.";
        }
    }

    notification output-power-error-high-critical {
        if-feature feature-list:HAVE_CMMD;
        if-feature feature-list:NOT_HAVE_TIBIT;

        description "This notification is sent when critical high output power error is detected on qspf/sfp/xfp port.";

        leaf severity {
            type cml-data-types:cml_notif_severity_t;
            description "Notification severity level (value: MAJOR)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf output-power {
            type  decimal64 {
                 fraction-digits 3;            }
        description
            "Measured TX output power in Channel of transceiver.";
        }

        leaf output-power-critical-min-threshold {
            type  decimal64 {
                 fraction-digits 3;            }
        description
            "The minimum Tx critical threshold in Channel of transceiver.";
        }

        leaf output-power-critical-max-threshold {
            type  decimal64 {
                 fraction-digits 3;            }
        description
            "The maximum Tx critical threshold in Channel of transceiver.";
        }
    }

    notification output-power-error-low-critical {
        if-feature feature-list:HAVE_CMMD;
        if-feature feature-list:NOT_HAVE_TIBIT;

        description "This notification is sent when critical low output power error is detected on qspf/sfp/xfp port.";

        leaf severity {
            type cml-data-types:cml_notif_severity_t;
            description "Notification severity level (value: MAJOR)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf output-power {
            type  decimal64 {
                 fraction-digits 3;            }
        description
            "Measured TX output power in Channel of transceiver.";
        }

        leaf output-power-critical-min-threshold {
            type  decimal64 {
                 fraction-digits 3;            }
        description
            "The minimum Tx critical threshold in Channel of transceiver.";
        }

        leaf output-power-critical-max-threshold {
            type  decimal64 {
                 fraction-digits 3;            }
        description
            "The maximum Tx critical threshold in Channel of transceiver.";
        }
    }

    notification output-power-error-high-alert {
        if-feature feature-list:HAVE_CMMD;
        if-feature feature-list:NOT_HAVE_TIBIT;

        description "This notification is sent when alert high output power error is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf output-power {
            type  decimal64 {
                 fraction-digits 3;            }
        description
            "Measured TX output power in Channel of transceiver.";
        }

        leaf output-power-alert-min-threshold {
            type  decimal64 {
                 fraction-digits 3;            }
        description
            "The minimum Tx alert threshold in Channel of transceiver.";
        }

        leaf output-power-alert-max-threshold {
            type  decimal64 {
                 fraction-digits 3;            }
        description
            "The maximum Tx alert threshold in Channel of transceiver.";
        }
    }

    notification output-power-error-low-alert {
        if-feature feature-list:HAVE_CMMD;
        if-feature feature-list:NOT_HAVE_TIBIT;

        description "This notification is sent when alert low output power error is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf output-power {
            type  decimal64 {
                 fraction-digits 3;            }
        description
            "Measured TX output power in Channel of transceiver.";
        }

        leaf output-power-alert-min-threshold {
            type  decimal64 {
                 fraction-digits 3;            }
        description
            "The minimum Tx alert threshold in Channel of transceiver.";
        }

        leaf output-power-alert-max-threshold {
            type  decimal64 {
                 fraction-digits 3;            }
        description
            "The maximum Tx alert threshold in Channel of transceiver.";
        }
    }

    notification output-power-error-recovery {
        if-feature feature-list:HAVE_CMMD;
        if-feature feature-list:NOT_HAVE_TIBIT;

        description "This notification is sent when output power is recovered on qspf/sfp/xfp port.";

        leaf severity {
            type cml-data-types:cml_notif_severity_t;
            description "Notification severity level (value: WARNING)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf output-power {
            type  decimal64 {
                 fraction-digits 3;            }
        description
            "Measured TX output power in Channel of transceiver.";
        }
    }

    notification laser-bias-current-error-high-critical {
        if-feature feature-list:HAVE_CMMD;
        if-feature feature-list:NOT_HAVE_TIBIT;

        description "This notification is sent when critical high laser bias current error is detected on qspf/sfp/xfp port.";

        leaf severity {
            type cml-data-types:cml_notif_severity_t;
            description "Notification severity level (value: MAJOR)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf laser-bias-current {
            type  decimal64 {
                 fraction-digits 3;            }
        description
            "Internally measured TX Bias Current in Channel of transceiver.";
        }

        leaf laser-bias-current-critical-min-threshold {
            type  decimal64 {
                 fraction-digits 3;            }
        description
            "The minimum current critical threshold in Channel of transceiver.";
        }

        leaf laser-bias-current-critical-max-threshold {
            type  decimal64 {
                 fraction-digits 3;            }
        description
            "The maximum current critical threshold in Channel of transceiver.";
        }
    }

    notification laser-bias-current-error-low-critical {
        if-feature feature-list:HAVE_CMMD;
        if-feature feature-list:NOT_HAVE_TIBIT;

        description "This notification is sent when critical low laser bias current error is detected on qspf/sfp/xfp port.";

        leaf severity {
            type cml-data-types:cml_notif_severity_t;
            description "Notification severity level (value: MAJOR)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf laser-bias-current {
            type  decimal64 {
                 fraction-digits 3;            }
        description
            "Internally measured TX Bias Current in Channel of transceiver.";
        }

        leaf laser-bias-current-critical-min-threshold {
            type  decimal64 {
                 fraction-digits 3;            }
        description
            "The minimum current critical threshold in Channel of transceiver.";
        }

        leaf laser-bias-current-critical-max-threshold {
            type  decimal64 {
                 fraction-digits 3;            }
        description
            "The maximum current critical threshold in Channel of transceiver.";
        }
    }

    notification laser-bias-current-error-high-alert {
        if-feature feature-list:HAVE_CMMD;
        if-feature feature-list:NOT_HAVE_TIBIT;

        description "This notification is sent when alert high laser bias current error is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf laser-bias-current {
            type  decimal64 {
                 fraction-digits 3;            }
        description
            "Internally measured TX Bias Current in Channel of transceiver.";
        }

        leaf laser-bias-current-alert-min-threshold {
            type  decimal64 {
                 fraction-digits 3;            }
        description
            "The minimum current alert threshold in Channel of transceiver.";
        }

        leaf laser-bias-current-alert-max-threshold {
            type  decimal64 {
                 fraction-digits 3;            }
        description
            "The maximum current alert threshold in Channel of transceiver.";
        }
    }

    notification laser-bias-current-error-low-alert {
        if-feature feature-list:HAVE_CMMD;
        if-feature feature-list:NOT_HAVE_TIBIT;

        description "This notification is sent when alert low laser bias current error is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf laser-bias-current {
            type  decimal64 {
                 fraction-digits 3;            }
        description
            "Internally measured TX Bias Current in Channel of transceiver.";
        }

        leaf laser-bias-current-alert-min-threshold {
            type  decimal64 {
                 fraction-digits 3;            }
        description
            "The minimum current alert threshold in Channel of transceiver.";
        }

        leaf laser-bias-current-alert-max-threshold {
            type  decimal64 {
                 fraction-digits 3;            }
        description
            "The maximum current alert threshold in Channel of transceiver.";
        }
    }

    notification laser-bias-current-error-recovery {
        if-feature feature-list:HAVE_CMMD;
        if-feature feature-list:NOT_HAVE_TIBIT;

        description "This notification is sent when laser bias current is recovered on qspf/sfp/xfp port.";

        leaf severity {
            type cml-data-types:cml_notif_severity_t;
            description "Notification severity level (value: WARNING)";
        }

        leaf eventClass {
            type cml-data-types:cml_notif_class_t;
            description "Notification event class (value: STATE)";
        }

        leaf index {
            type  uint8;
        description
            "A unique value, greater than zero, for each channel in the transceiver
                    within the unit.";
        }

        leaf name {
            type  string;
        description
            "References the component name";
        }

        leaf laser-bias-current {
            type  decimal64 {
                 fraction-digits 3;            }
        description
            "Internally measured TX Bias Current in Channel of transceiver.";
        }
    }

    notification transceiver-temperature-error-high-critical {
        if-feature feature-list:HAVE_CMMD;
        if-feature feature-list:NOT_HAVE_TIBIT;

        description "This notification is sent when critical high transceiver temperature error is detected on qspf/sfp/xfp port.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf transceiver-temperature {
            type  decimal64 {
                 fraction-digits 3;            }
        description
            "Internally measured Temperature in Channel of transceiver.";
        }

        leaf temperature-critical-min-threshold {
            type  decimal64 {
                 fraction-digits 3;            }
        description
            "The minimum temperature critical threshold in Channel of transceiver.";
        }

        leaf temperature-critical-max-threshold {
            type  decimal64 {
                 fraction-digits 3;            }
        description
            "The maximum temperature critical threshold in Channel of transceiver.";
        }
    }

    notification transceiver-temperature-error-low-critical {
        if-feature feature-list:HAVE_CMMD;
        if-feature feature-list:NOT_HAVE_TIBIT;

        description "This notification is sent when critical low transceiver temperature error is detected on qspf/sfp/xfp port.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf transceiver-temperature {
            type  decimal64 {
                 fraction-digits 3;            }
        description
            "Internally measured Temperature in Channel of transceiver.";
        }

        leaf temperature-critical-min-threshold {
            type  decimal64 {
                 fraction-digits 3;            }
        description
            "The minimum temperature critical threshold in Channel of transceiver.";
        }

        leaf temperature-critical-max-threshold {
            type  decimal64 {
                 fraction-digits 3;            }
        description
            "The maximum temperature critical threshold in Channel of transceiver.";
        }
    }

    notification transceiver-temperature-error-high-alert {
        if-feature feature-list:HAVE_CMMD;
        if-feature feature-list:NOT_HAVE_TIBIT;

        description "This notification is sent when alert high transceiver temperature error is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf transceiver-temperature {
            type  decimal64 {
                 fraction-digits 3;            }
        description
            "Internally measured Temperature in Channel of transceiver.";
        }

        leaf temperature-alert-min-threshold {
            type  decimal64 {
                 fraction-digits 3;            }
        description
            "The minimum temperature alert threshold in Channel of transceiver.";
        }

        leaf temperature-alert-max-threshold {
            type  decimal64 {
                 fraction-digits 3;            }
        description
            "The maximum temperature alert threshold in Channel of transceiver.";
        }
    }

    notification transceiver-temperature-error-low-alert {
        if-feature feature-list:HAVE_CMMD;
        if-feature feature-list:NOT_HAVE_TIBIT;

        description "This notification is sent when alert low transceiver temperature error is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf transceiver-temperature {
            type  decimal64 {
                 fraction-digits 3;            }
        description
            "Internally measured Temperature in Channel of transceiver.";
        }

        leaf temperature-alert-min-threshold {
            type  decimal64 {
                 fraction-digits 3;            }
        description
            "The minimum temperature alert threshold in Channel of transceiver.";
        }

        leaf temperature-alert-max-threshold {
            type  decimal64 {
                 fraction-digits 3;            }
        description
            "The maximum temperature alert threshold in Channel of transceiver.";
        }
    }

    notification transceiver-temperature-error-recovery {
        if-feature feature-list:HAVE_CMMD;
        if-feature feature-list:NOT_HAVE_TIBIT;

        description "This notification is sent when transceiver temperature is recovered on qspf/sfp/xfp port.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf transceiver-temperature {
            type  decimal64 {
                 fraction-digits 3;            }
        description
            "Internally measured Temperature in Channel of transceiver.";
        }
    }

    notification transceiver-voltage-error-high-critical {
        if-feature feature-list:HAVE_CMMD;
        if-feature feature-list:NOT_HAVE_TIBIT;

        description "This notification is sent when critical high transceiver voltage error is detected on qspf/sfp/xfp port.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf transceiver-voltage {
            type  decimal64 {
                 fraction-digits 3;            }
        description
            "Measured Voltage in Channel of transceiver.";
        }

        leaf voltage-critical-min-threshold {
            type  decimal64 {
                 fraction-digits 3;            }
        description
            "The minimum voltage critical threshold in Channel of transceiver.";
        }

        leaf voltage-critical-max-threshold {
            type  decimal64 {
                 fraction-digits 3;            }
        description
            "The maximum voltage critical threshold in Channel of transceiver.";
        }
    }

    notification transceiver-voltage-error-low-critical {
        if-feature feature-list:HAVE_CMMD;
        if-feature feature-list:NOT_HAVE_TIBIT;

        description "This notification is sent when critical low transceiver voltage error is detected on qspf/sfp/xfp port.";

        leaf severity {
            type cml-data-types:cml_notif_severity_t;
            description "Notification severity level (value: MAJOR)";
        }

        leaf eventClass {
            type cml-data-types:cml_notif_class_t;
            description "Notification event class (value: STATE)";
        }

        leaf name {
            type  string;
        description
            "References the component name";
        }

        leaf transceiver-voltage {
            type  decimal64 {
                 fraction-digits 3;            }
        description
            "Measured Voltage in Channel of transceiver.";
        }

        leaf voltage-critical-min-threshold {
            type  decimal64 {
                 fraction-digits 3;            }
        description
            "The minimum voltage critical threshold in Channel of transceiver.";
        }

        leaf voltage-critical-max-threshold {
            type  decimal64 {
                 fraction-digits 3;            }
        description
            "The maximum voltage critical threshold in Channel of transceiver.";
        }
    }

    notification transceiver-voltage-error-high-alert {
        if-feature feature-list:HAVE_CMMD;
        if-feature feature-list:NOT_HAVE_TIBIT;

        description "This notification is sent when alert high transceiver voltage error is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf transceiver-voltage {
            type  decimal64 {
                 fraction-digits 3;            }
        description
            "Measured Voltage in Channel of transceiver.";
        }

        leaf voltage-alert-min-threshold {
            type  decimal64 {
                 fraction-digits 3;            }
        description
            "The minimum voltage alert threshold in Channel of transceiver.";
        }

        leaf voltage-alert-max-threshold {
            type  decimal64 {
                 fraction-digits 3;            }
        description
            "The maximum voltage alert threshold in Channel of transceiver.";
        }
    }

    notification transceiver-voltage-error-low-alert {
        if-feature feature-list:HAVE_CMMD;
        if-feature feature-list:NOT_HAVE_TIBIT;

        description "This notification is sent when alert low transceiver voltage error is detected on qspf/sfp/xfp port.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf transceiver-voltage {
            type  decimal64 {
                 fraction-digits 3;            }
        description
            "Measured Voltage in Channel of transceiver.";
        }

        leaf voltage-alert-min-threshold {
            type  decimal64 {
                 fraction-digits 3;            }
        description
            "The minimum voltage alert threshold in Channel of transceiver.";
        }

        leaf voltage-alert-max-threshold {
            type  decimal64 {
                 fraction-digits 3;            }
        description
            "The maximum voltage alert threshold in Channel of transceiver.";
        }
    }

    notification transceiver-voltage-error-recovery {
        if-feature feature-list:HAVE_CMMD;
        if-feature feature-list:NOT_HAVE_TIBIT;

        description "This notification is sent when transceiver voltage is recovered on qspf/sfp/xfp port.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }

        leaf transceiver-voltage {
            type  decimal64 {
                 fraction-digits 3;            }
        description
            "Measured Voltage in Channel of transceiver.";
        }
    }

    notification temperature-high {
        if-feature feature-list:HAVE_CMMD;

        description "This notification is sent when temperature sensor exceeds a given threshold.";

        leaf severity {
            type cml-data-types:cml_notif_severity_t;
            description "Notification severity level";
        }

        leaf eventClass {
            type cml-data-types:cml_notif_class_t;
            description "Notification event class (value: STATE)";
        }

        leaf name {
            type  string;
        description
            "References the component name";
        }

        leaf alarm-status {
            type  boolean;
        description
            "A value of true indicates the alarm has been raised or asserted. The
                    value should be false when the alarm is cleared.";
        }

        leaf alarm-threshold {
            type  decimal64 {
                 fraction-digits 2;            }
        description
            "The threshold value that was crossed for this alarm.";
        }

        leaf instant {
            type  decimal64 {
                 fraction-digits 2;            }
        description
            "The instantaneous temperature value.";
        }
    }

    notification temperature-low {
        if-feature feature-list:HAVE_CMMD;

        description "This notification is sent when temperature sensor falls below a given threshold.";

        leaf severity {
            type cml-data-types:cml_notif_severity_t;
            description "Notification severity level";
        }

        leaf eventClass {
            type cml-data-types:cml_notif_class_t;
            description "Notification event class (value: STATE)";
        }

        leaf name {
            type  string;
        description
            "References the component name";
        }

        leaf alarm-status {
            type  boolean;
        description
            "A value of true indicates the alarm has been raised or asserted. The
                    value should be false when the alarm is cleared.";
        }

        leaf alarm-threshold {
            type  decimal64 {
                 fraction-digits 2;            }
        description
            "The threshold value that was crossed for this alarm.";
        }

        leaf instant {
            type  decimal64 {
                 fraction-digits 2;            }
        description
            "The instantaneous temperature value.";
        }
    }

    notification power-supply-inserted {
        if-feature feature-list:HAVE_CMMD;

        description "This notification is sent when power supply unit is inserted.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }
    }

    notification power-supply-absent {
        if-feature feature-list:HAVE_CMMD;

        description "This notification is sent when power supply unit is removed or not present during bootup.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }
    }

    notification power-supply-ac-failed {
        if-feature feature-list:HAVE_CMMD;

        description "This notification is sent when power supply unit has no input power.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }
    }

    notification power-supply-ac-recovery {
        if-feature feature-list:HAVE_CMMD;

        description "This notification is sent when power supply unit input power is restored.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }
    }

    notification power-supply-12v-failed {
        if-feature feature-list:HAVE_CMMD;

        description "This notification is sent when power supply unit has no output power.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }
    }

    notification power-supply-12v-recovery {
        if-feature feature-list:HAVE_CMMD;

        description "This notification is sent when power supply unit output power is restored..";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }
    }

    notification psu-vin-low-alert {
        if-feature feature-list:HAVE_CMMD;

        description "This notification is sent when input voltage of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-voltage {
            type  decimal64 {
                 fraction-digits 2;            }
        description
            "Input voltage of power supply";
        }

        leaf vin-alert-threshold-min {
            type  decimal64 {
                 fraction-digits 2;            }
        description
            "Psu input volatge alert threshold minimum value";
        }

        leaf vin-alert-threshold-max {
            type  decimal64 {
                 fraction-digits 2;            }
        description
            "Psu input volatge alert threshold maximum value";
        }
    }

    notification psu-vin-high-alert {
        if-feature feature-list:HAVE_CMMD;

        description "This notification is sent when input voltage of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-voltage {
            type  decimal64 {
                 fraction-digits 2;            }
        description
            "Input voltage of power supply";
        }

        leaf vin-alert-threshold-min {
            type  decimal64 {
                 fraction-digits 2;            }
        description
            "Psu input volatge alert threshold minimum value";
        }

        leaf vin-alert-threshold-max {
            type  decimal64 {
                 fraction-digits 2;            }
        description
            "Psu input volatge alert threshold maximum value";
        }
    }

    notification psu-vin-low-critical {
        if-feature feature-list:HAVE_CMMD;

        description "This notification is sent when input voltage of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-voltage {
            type  decimal64 {
                 fraction-digits 2;            }
        description
            "Input voltage of power supply";
        }

        leaf vin-critical-threshold-min {
            type  decimal64 {
                 fraction-digits 2;            }
        description
            "Psu input volatge critical threshold minimun value";
        }

        leaf vin-critical-threshold-max {
            type  decimal64 {
                 fraction-digits 2;            }
        description
            "Psu input volatge critical threshold maximum value";
        }
    }

    notification psu-vin-high-critical {
        if-feature feature-list:HAVE_CMMD;

        description "This notification is sent when input voltage of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-voltage {
            type  decimal64 {
                 fraction-digits 2;            }
        description
            "Input voltage of power supply";
        }

        leaf vin-critical-threshold-min {
            type  decimal64 {
                 fraction-digits 2;            }
        description
            "Psu input volatge critical threshold minimun value";
        }

        leaf vin-critical-threshold-max {
            type  decimal64 {
                 fraction-digits 2;            }
        description
            "Psu input volatge critical threshold maximum value";
        }
    }

    notification psu-vin-low-alert-recovery {
        if-feature feature-list:HAVE_CMMD;

        description "This notification is sent when input voltage of PSU exceeds a given threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-voltage {
            type  decimal64 {
                 fraction-digits 2;            }
        description
            "Input voltage of power supply";
        }

        leaf vin-alert-threshold-min {
            type  decimal64 {
                 fraction-digits 2;            }
        description
            "Psu input volatge alert threshold minimum value";
        }

        leaf vin-alert-threshold-max {
            type  decimal64 {
                 fraction-digits 2;            }
        description
            "Psu input volatge alert threshold maximum value";
        }
    }

    notification psu-vin-high-alert-recovery {
        if-feature feature-list:HAVE_CMMD;

        description "This notification is sent when input voltage of PSU exceeds a given threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-voltage {
            type  decimal64 {
                 fraction-digits 2;            }
        description
            "Input voltage of power supply";
        }

        leaf vin-alert-threshold-min {
            type  decimal64 {
                 fraction-digits 2;            }
        description
            "Psu input volatge alert threshold minimum value";
        }

        leaf vin-alert-threshold-max {
            type  decimal64 {
                 fraction-digits 2;            }
        description
            "Psu input volatge alert threshold maximum value";
        }
    }

    notification psu-vin-low-critical-recovery {
        if-feature feature-list:HAVE_CMMD;

        description "This notification is sent when input voltage of PSU exceeds a given threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-voltage {
            type  decimal64 {
                 fraction-digits 2;            }
        description
            "Input voltage of power supply";
        }

        leaf vin-critical-threshold-min {
            type  decimal64 {
                 fraction-digits 2;            }
        description
            "Psu input volatge critical threshold minimun value";
        }

        leaf vin-critical-threshold-max {
            type  decimal64 {
                 fraction-digits 2;            }
        description
            "Psu input volatge critical threshold maximum value";
        }
    }

    notification psu-vin-high-critical-recovery {
        if-feature feature-list:HAVE_CMMD;

        description "This notification is sent when input voltage of PSU exceeds a given threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-voltage {
            type  decimal64 {
                 fraction-digits 2;            }
        description
            "Input voltage of power supply";
        }

        leaf vin-critical-threshold-min {
            type  decimal64 {
                 fraction-digits 2;            }
        description
            "Psu input volatge critical threshold minimun value";
        }

        leaf vin-critical-threshold-max {
            type  decimal64 {
                 fraction-digits 2;            }
        description
            "Psu input volatge critical threshold maximum value";
        }
    }

    notification psu-vout-low-alert {
        if-feature feature-list:HAVE_CMMD;

        description "This notification is sent when output voltage of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf output-voltage {
            type  decimal64 {
                 fraction-digits 2;            }
        description
            "Output voltage of power supply";
        }

        leaf vout-alert-threshold-min {
            type  decimal64 {
                 fraction-digits 2;            }
        description
            "Psu output volatge alert threshold minimum value";
        }

        leaf vout-alert-threshold-max {
            type  decimal64 {
                 fraction-digits 2;            }
        description
            "Psu output volatge alert threshold maximum value";
        }
    }

    notification psu-vout-high-alert {
        if-feature feature-list:HAVE_CMMD;

        description "This notification is sent when output voltage of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf output-voltage {
            type  decimal64 {
                 fraction-digits 2;            }
        description
            "Output voltage of power supply";
        }

        leaf vout-alert-threshold-min {
            type  decimal64 {
                 fraction-digits 2;            }
        description
            "Psu output volatge alert threshold minimum value";
        }

        leaf vout-alert-threshold-max {
            type  decimal64 {
                 fraction-digits 2;            }
        description
            "Psu output volatge alert threshold maximum value";
        }
    }

    notification psu-vout-low-critical {
        if-feature feature-list:HAVE_CMMD;

        description "This notification is sent when output voltage of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf output-voltage {
            type  decimal64 {
                 fraction-digits 2;            }
        description
            "Output voltage of power supply";
        }

        leaf vout-critical-threshold-min {
            type  decimal64 {
                 fraction-digits 2;            }
        description
            "Psu output volatge critical threshold minimum value";
        }

        leaf vout-critical-threshold-max {
            type  decimal64 {
                 fraction-digits 2;            }
        description
            "Psu output volatge critical threshold maximum value";
        }
    }

    notification psu-vout-high-critical {
        if-feature feature-list:HAVE_CMMD;

        description "This notification is sent when output voltage of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf output-voltage {
            type  decimal64 {
                 fraction-digits 2;            }
        description
            "Output voltage of power supply";
        }

        leaf vout-critical-threshold-min {
            type  decimal64 {
                 fraction-digits 2;            }
        description
            "Psu output volatge critical threshold minimum value";
        }

        leaf vout-critical-threshold-max {
            type  decimal64 {
                 fraction-digits 2;            }
        description
            "Psu output volatge critical threshold maximum value";
        }
    }

    notification psu-vout-low-alert-recovery {
        if-feature feature-list:HAVE_CMMD;

        description "This notification is sent when output voltage of PSU exceeds a given threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf output-voltage {
            type  decimal64 {
                 fraction-digits 2;            }
        description
            "Output voltage of power supply";
        }

        leaf vout-alert-threshold-min {
            type  decimal64 {
                 fraction-digits 2;            }
        description
            "Psu output volatge alert threshold minimum value";
        }

        leaf vout-alert-threshold-max {
            type  decimal64 {
                 fraction-digits 2;            }
        description
            "Psu output volatge alert threshold maximum value";
        }
    }

    notification psu-vout-high-alert-recovery {
        if-feature feature-list:HAVE_CMMD;

        description "This notification is sent when output voltage violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf output-voltage {
            type  decimal64 {
                 fraction-digits 2;            }
        description
            "Output voltage of power supply";
        }

        leaf vout-alert-threshold-min {
            type  decimal64 {
                 fraction-digits 2;            }
        description
            "Psu output volatge alert threshold minimum value";
        }

        leaf vout-alert-threshold-max {
            type  decimal64 {
                 fraction-digits 2;            }
        description
            "Psu output volatge alert threshold maximum value";
        }
    }

    notification psu-vout-low-critical-recovery {
        if-feature feature-list:HAVE_CMMD;

        description "This notification is sent when output voltage violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf output-voltage {
            type  decimal64 {
                 fraction-digits 2;            }
        description
            "Output voltage of power supply";
        }

        leaf vout-critical-threshold-min {
            type  decimal64 {
                 fraction-digits 2;            }
        description
            "Psu output volatge critical threshold minimum value";
        }

        leaf vout-critical-threshold-max {
            type  decimal64 {
                 fraction-digits 2;            }
        description
            "Psu output volatge critical threshold maximum value";
        }
    }

    notification psu-vout-high-critical-recovery {
        if-feature feature-list:HAVE_CMMD;

        description "This notification is sent when output voltage violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf output-voltage {
            type  decimal64 {
                 fraction-digits 2;            }
        description
            "Output voltage of power supply";
        }

        leaf vout-critical-threshold-min {
            type  decimal64 {
                 fraction-digits 2;            }
        description
            "Psu output volatge critical threshold minimum value";
        }

        leaf vout-critical-threshold-max {
            type  decimal64 {
                 fraction-digits 2;            }
        description
            "Psu output volatge critical threshold maximum value";
        }
    }

    notification psu-pin-low-alert {
        if-feature feature-list:HAVE_CMMD;

        description "This notification is sent when input power of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-power {
            type  decimal64 {
                 fraction-digits 2;            }
        description
            "Input power of power supply";
        }

        leaf pin-alert-threshold-min {
            type  decimal64 {
                 fraction-digits 2;            }
        description
            "Psu input power alert threshold minimum value";
        }

        leaf pin-alert-threshold-max {
            type  decimal64 {
                 fraction-digits 2;            }
        description
            "Psu input power alert threshold maximum value";
        }
    }

    notification psu-pin-high-alert {
        if-feature feature-list:HAVE_CMMD;

        description "This notification is sent when input power of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-power {
            type  decimal64 {
                 fraction-digits 2;            }
        description
            "Input power of power supply";
        }

        leaf pin-alert-threshold-min {
            type  decimal64 {
                 fraction-digits 2;            }
        description
            "Psu input power alert threshold minimum value";
        }

        leaf pin-alert-threshold-max {
            type  decimal64 {
                 fraction-digits 2;            }
        description
            "Psu input power alert threshold maximum value";
        }
    }

    notification psu-pin-low-critical {
        if-feature feature-list:HAVE_CMMD;

        description "This notification is sent when input power of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-power {
            type  decimal64 {
                 fraction-digits 2;            }
        description
            "Input power of power supply";
        }

        leaf pin-critical-threshold-min {
            type  decimal64 {
                 fraction-digits 2;            }
        description
            "Psu input power critical threshold minimum value";
        }

        leaf pin-critical-threshold-max {
            type  decimal64 {
                 fraction-digits 2;            }
        description
            "Psu input power critical threshold maximum value";
        }
    }

    notification psu-pin-high-critical {
        if-feature feature-list:HAVE_CMMD;

        description "This notification is sent when input power of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-power {
            type  decimal64 {
                 fraction-digits 2;            }
        description
            "Input power of power supply";
        }

        leaf pin-critical-threshold-min {
            type  decimal64 {
                 fraction-digits 2;            }
        description
            "Psu input power critical threshold minimum value";
        }

        leaf pin-critical-threshold-max {
            type  decimal64 {
                 fraction-digits 2;            }
        description
            "Psu input power critical threshold maximum value";
        }
    }

    notification psu-pin-low-alert-recovery {
        if-feature feature-list:HAVE_CMMD;

        description "This notification is sent when input power of PSU exceeds a given threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-power {
            type  decimal64 {
                 fraction-digits 2;            }
        description
            "Input power of power supply";
        }

        leaf pin-alert-threshold-min {
            type  decimal64 {
                 fraction-digits 2;            }
        description
            "Psu input power alert threshold minimum value";
        }

        leaf pin-alert-threshold-max {
            type  decimal64 {
                 fraction-digits 2;            }
        description
            "Psu input power alert threshold maximum value";
        }
    }

    notification psu-pin-high-alert-recovery {
        if-feature feature-list:HAVE_CMMD;

        description "This notification is sent when input power violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-power {
            type  decimal64 {
                 fraction-digits 2;            }
        description
            "Input power of power supply";
        }

        leaf pin-alert-threshold-min {
            type  decimal64 {
                 fraction-digits 2;            }
        description
            "Psu input power alert threshold minimum value";
        }

        leaf pin-alert-threshold-max {
            type  decimal64 {
                 fraction-digits 2;            }
        description
            "Psu input power alert threshold maximum value";
        }
    }

    notification psu-pin-low-critical-recovery {
        if-feature feature-list:HAVE_CMMD;

        description "This notification is sent when input power violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-power {
            type  decimal64 {
                 fraction-digits 2;            }
        description
            "Input power of power supply";
        }

        leaf pin-critical-threshold-min {
            type  decimal64 {
                 fraction-digits 2;            }
        description
            "Psu input power critical threshold minimum value";
        }

        leaf pin-critical-threshold-max {
            type  decimal64 {
                 fraction-digits 2;            }
        description
            "Psu input power critical threshold maximum value";
        }
    }

    notification psu-pin-high-critical-recovery {
        if-feature feature-list:HAVE_CMMD;

        description "This notification is sent when input power violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-power {
            type  decimal64 {
                 fraction-digits 2;            }
        description
            "Input power of power supply";
        }

        leaf pin-critical-threshold-min {
            type  decimal64 {
                 fraction-digits 2;            }
        description
            "Psu input power critical threshold minimum value";
        }

        leaf pin-critical-threshold-max {
            type  decimal64 {
                 fraction-digits 2;            }
        description
            "Psu input power critical threshold maximum value";
        }
    }

    notification psu-pout-low-alert {
        if-feature feature-list:HAVE_CMMD;

        description "This notification is sent when output power of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf power-consumption {
            type  decimal64 {
                 fraction-digits 2;            }
        description
            "Output power of power supply";
        }

        leaf pout-alert-threshold-min {
            type  decimal64 {
                 fraction-digits 2;            }
        description
            "Psu output power alert threshold minimum value";
        }

        leaf pout-alert-threshold-max {
            type  decimal64 {
                 fraction-digits 2;            }
        description
            "Psu output power alert threshold maximum value";
        }
    }

    notification psu-pout-high-alert {
        if-feature feature-list:HAVE_CMMD;

        description "This notification is sent when output power of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf power-consumption {
            type  decimal64 {
                 fraction-digits 2;            }
        description
            "Output power of power supply";
        }

        leaf pout-alert-threshold-min {
            type  decimal64 {
                 fraction-digits 2;            }
        description
            "Psu output power alert threshold minimum value";
        }

        leaf pout-alert-threshold-max {
            type  decimal64 {
                 fraction-digits 2;            }
        description
            "Psu output power alert threshold maximum value";
        }
    }

    notification psu-pout-low-critical {
        if-feature feature-list:HAVE_CMMD;

        description "This notification is sent when output power of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf power-consumption {
            type  decimal64 {
                 fraction-digits 2;            }
        description
            "Output power of power supply";
        }

        leaf pout-critical-threshold-min {
            type  decimal64 {
                 fraction-digits 2;            }
        description
            "Psu output power critical threshold minimum value";
        }

        leaf pout-critical-threshold-max {
            type  decimal64 {
                 fraction-digits 2;            }
        description
            "Psu output power critical threshold maximum value";
        }
    }

    notification psu-pout-high-critical {
        if-feature feature-list:HAVE_CMMD;

        description "This notification is sent when output power of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf power-consumption {
            type  decimal64 {
                 fraction-digits 2;            }
        description
            "Output power of power supply";
        }

        leaf pout-critical-threshold-min {
            type  decimal64 {
                 fraction-digits 2;            }
        description
            "Psu output power critical threshold minimum value";
        }

        leaf pout-critical-threshold-max {
            type  decimal64 {
                 fraction-digits 2;            }
        description
            "Psu output power critical threshold maximum value";
        }
    }

    notification psu-pout-low-alert-recovery {
        if-feature feature-list:HAVE_CMMD;

        description "This notification is sent when output power of PSU exceeds a given threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf power-consumption {
            type  decimal64 {
                 fraction-digits 2;            }
        description
            "Output power of power supply";
        }

        leaf pout-alert-threshold-min {
            type  decimal64 {
                 fraction-digits 2;            }
        description
            "Psu output power alert threshold minimum value";
        }

        leaf pout-alert-threshold-max {
            type  decimal64 {
                 fraction-digits 2;            }
        description
            "Psu output power alert threshold maximum value";
        }
    }

    notification psu-pout-high-alert-recovery {
        if-feature feature-list:HAVE_CMMD;

        description "This notification is sent when output power violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf power-consumption {
            type  decimal64 {
                 fraction-digits 2;            }
        description
            "Output power of power supply";
        }

        leaf pout-alert-threshold-min {
            type  decimal64 {
                 fraction-digits 2;            }
        description
            "Psu output power alert threshold minimum value";
        }

        leaf pout-alert-threshold-max {
            type  decimal64 {
                 fraction-digits 2;            }
        description
            "Psu output power alert threshold maximum value";
        }
    }

    notification psu-pout-low-critical-recovery {
        if-feature feature-list:HAVE_CMMD;

        description "This notification is sent when output power violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf power-consumption {
            type  decimal64 {
                 fraction-digits 2;            }
        description
            "Output power of power supply";
        }

        leaf pout-critical-threshold-min {
            type  decimal64 {
                 fraction-digits 2;            }
        description
            "Psu output power critical threshold minimum value";
        }

        leaf pout-critical-threshold-max {
            type  decimal64 {
                 fraction-digits 2;            }
        description
            "Psu output power critical threshold maximum value";
        }
    }

    notification psu-pout-high-critical-recovery {
        if-feature feature-list:HAVE_CMMD;

        description "This notification is sent when output power violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf power-consumption {
            type  decimal64 {
                 fraction-digits 2;            }
        description
            "Output power of power supply";
        }

        leaf pout-critical-threshold-min {
            type  decimal64 {
                 fraction-digits 2;            }
        description
            "Psu output power critical threshold minimum value";
        }

        leaf pout-critical-threshold-max {
            type  decimal64 {
                 fraction-digits 2;            }
        description
            "Psu output power critical threshold maximum value";
        }
    }

    notification psu-iout-low-alert {
        if-feature feature-list:HAVE_CMMD;

        description "This notification is sent when output current of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf output-current {
            type  decimal64 {
                 fraction-digits 2;            }
        description
            "Output current of power supply";
        }

        leaf iout-alert-threshold-min {
            type  decimal64 {
                 fraction-digits 2;            }
        description
            "Psu output current alert threshold minimum value";
        }

        leaf iout-alert-threshold-max {
            type  decimal64 {
                 fraction-digits 2;            }
        description
            "Psu output current alert threshold maximum value";
        }
    }

    notification psu-iout-high-alert {
        if-feature feature-list:HAVE_CMMD;

        description "This notification is sent when output current of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf output-current {
            type  decimal64 {
                 fraction-digits 2;            }
        description
            "Output current of power supply";
        }

        leaf iout-alert-threshold-min {
            type  decimal64 {
                 fraction-digits 2;            }
        description
            "Psu output current alert threshold minimum value";
        }

        leaf iout-alert-threshold-max {
            type  decimal64 {
                 fraction-digits 2;            }
        description
            "Psu output current alert threshold maximum value";
        }
    }

    notification psu-iout-low-critical {
        if-feature feature-list:HAVE_CMMD;

        description "This notification is sent when output current of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf output-current {
            type  decimal64 {
                 fraction-digits 2;            }
        description
            "Output current of power supply";
        }

        leaf iout-critical-threshold-min {
            type  decimal64 {
                 fraction-digits 2;            }
        description
            "Psu output current critical threshold minimum value";
        }

        leaf iout-critical-threshold-max {
            type  decimal64 {
                 fraction-digits 2;            }
        description
            "Psu output current critical threshold maximum value";
        }
    }

    notification psu-iout-high-critical {
        if-feature feature-list:HAVE_CMMD;

        description "This notification is sent when output current of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf output-current {
            type  decimal64 {
                 fraction-digits 2;            }
        description
            "Output current of power supply";
        }

        leaf iout-critical-threshold-min {
            type  decimal64 {
                 fraction-digits 2;            }
        description
            "Psu output current critical threshold minimum value";
        }

        leaf iout-critical-threshold-max {
            type  decimal64 {
                 fraction-digits 2;            }
        description
            "Psu output current critical threshold maximum value";
        }
    }

    notification psu-iout-low-alert-recovery {
        if-feature feature-list:HAVE_CMMD;

        description "This notification is sent when output current of PSU exceeds a given threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf output-current {
            type  decimal64 {
                 fraction-digits 2;            }
        description
            "Output current of power supply";
        }

        leaf iout-alert-threshold-min {
            type  decimal64 {
                 fraction-digits 2;            }
        description
            "Psu output current alert threshold minimum value";
        }

        leaf iout-alert-threshold-max {
            type  decimal64 {
                 fraction-digits 2;            }
        description
            "Psu output current alert threshold maximum value";
        }
    }

    notification psu-iout-high-alert-recovery {
        if-feature feature-list:HAVE_CMMD;

        description "This notification is sent when output current violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf output-current {
            type  decimal64 {
                 fraction-digits 2;            }
        description
            "Output current of power supply";
        }

        leaf iout-alert-threshold-min {
            type  decimal64 {
                 fraction-digits 2;            }
        description
            "Psu output current alert threshold minimum value";
        }

        leaf iout-alert-threshold-max {
            type  decimal64 {
                 fraction-digits 2;            }
        description
            "Psu output current alert threshold maximum value";
        }
    }

    notification psu-iout-low-critical-recovery {
        if-feature feature-list:HAVE_CMMD;

        description "This notification is sent when output current violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf output-current {
            type  decimal64 {
                 fraction-digits 2;            }
        description
            "Output current of power supply";
        }

        leaf iout-critical-threshold-min {
            type  decimal64 {
                 fraction-digits 2;            }
        description
            "Psu output current critical threshold minimum value";
        }

        leaf iout-critical-threshold-max {
            type  decimal64 {
                 fraction-digits 2;            }
        description
            "Psu output current critical threshold maximum value";
        }
    }

    notification psu-iout-high-critical-recovery {
        if-feature feature-list:HAVE_CMMD;

        description "This notification is sent when output current violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf output-current {
            type  decimal64 {
                 fraction-digits 2;            }
        description
            "Output current of power supply";
        }

        leaf iout-critical-threshold-min {
            type  decimal64 {
                 fraction-digits 2;            }
        description
            "Psu output current critical threshold minimum value";
        }

        leaf iout-critical-threshold-max {
            type  decimal64 {
                 fraction-digits 2;            }
        description
            "Psu output current critical threshold maximum value";
        }
    }

    notification psu-iin-low-alert {
        if-feature feature-list:HAVE_CMMD;

        description "This notification is sent when input current of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-current {
            type  decimal64 {
                 fraction-digits 2;            }
        description
            "Input current of power supply";
        }

        leaf iin-alert-threshold-min {
            type  decimal64 {
                 fraction-digits 2;            }
        description
            "Psu input current alert threshold minimum value";
        }

        leaf iin-alert-threshold-max {
            type  decimal64 {
                 fraction-digits 2;            }
        description
            "Psu input current alert threshold maximum value";
        }
    }

    notification psu-iin-high-alert {
        if-feature feature-list:HAVE_CMMD;

        description "This notification is sent when input current of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-current {
            type  decimal64 {
                 fraction-digits 2;            }
        description
            "Input current of power supply";
        }

        leaf iin-alert-threshold-min {
            type  decimal64 {
                 fraction-digits 2;            }
        description
            "Psu input current alert threshold minimum value";
        }

        leaf iin-alert-threshold-max {
            type  decimal64 {
                 fraction-digits 2;            }
        description
            "Psu input current alert threshold maximum value";
        }
    }

    notification psu-iin-low-critical {
        if-feature feature-list:HAVE_CMMD;

        description "This notification is sent when input current of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-current {
            type  decimal64 {
                 fraction-digits 2;            }
        description
            "Input current of power supply";
        }

        leaf iin-critical-threshold-min {
            type  decimal64 {
                 fraction-digits 2;            }
        description
            "Psu input current critical threshold minimum value";
        }

        leaf iin-critical-threshold-max {
            type  decimal64 {
                 fraction-digits 2;            }
        description
            "Psu input current critical threshold maximum value";
        }
    }

    notification psu-iin-high-critical {
        if-feature feature-list:HAVE_CMMD;

        description "This notification is sent when input current of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf input-current {
            type  decimal64 {
                 fraction-digits 2;            }
        description
            "Input current of power supply";
        }

        leaf iin-critical-threshold-min {
            type  decimal64 {
                 fraction-digits 2;            }
        description
            "Psu input current critical threshold minimum value";
        }

        leaf iin-critical-threshold-max {
            type  decimal64 {
                 fraction-digits 2;            }
        description
            "Psu input current critical threshold maximum value";
        }
    }

    notification psu-iin-low-alert-recovery {
        if-feature feature-list:HAVE_CMMD;

        description "This notification is sent when input current of PSU exceeds a given threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-current {
            type  decimal64 {
                 fraction-digits 2;            }
        description
            "Input current of power supply";
        }

        leaf iin-alert-threshold-min {
            type  decimal64 {
                 fraction-digits 2;            }
        description
            "Psu input current alert threshold minimum value";
        }

        leaf iin-alert-threshold-max {
            type  decimal64 {
                 fraction-digits 2;            }
        description
            "Psu input current alert threshold maximum value";
        }
    }

    notification psu-iin-high-alert-recovery {
        if-feature feature-list:HAVE_CMMD;

        description "This notification is sent when input current violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-current {
            type  decimal64 {
                 fraction-digits 2;            }
        description
            "Input current of power supply";
        }

        leaf iin-alert-threshold-min {
            type  decimal64 {
                 fraction-digits 2;            }
        description
            "Psu input current alert threshold minimum value";
        }

        leaf iin-alert-threshold-max {
            type  decimal64 {
                 fraction-digits 2;            }
        description
            "Psu input current alert threshold maximum value";
        }
    }

    notification psu-iin-low-critical-recovery {
        if-feature feature-list:HAVE_CMMD;

        description "This notification is sent when input current violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-current {
            type  decimal64 {
                 fraction-digits 2;            }
        description
            "Input current of power supply";
        }

        leaf iin-critical-threshold-min {
            type  decimal64 {
                 fraction-digits 2;            }
        description
            "Psu input current critical threshold minimum value";
        }

        leaf iin-critical-threshold-max {
            type  decimal64 {
                 fraction-digits 2;            }
        description
            "Psu input current critical threshold maximum value";
        }
    }

    notification psu-iin-high-critical-recovery {
        if-feature feature-list:HAVE_CMMD;

        description "This notification is sent when input current violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf input-current {
            type  decimal64 {
                 fraction-digits 2;            }
        description
            "Input current of power supply";
        }

        leaf iin-critical-threshold-min {
            type  decimal64 {
                 fraction-digits 2;            }
        description
            "Psu input current critical threshold minimum value";
        }

        leaf iin-critical-threshold-max {
            type  decimal64 {
                 fraction-digits 2;            }
        description
            "Psu input current critical threshold maximum value";
        }
    }

    notification psu-temp1-low-alert {
        if-feature feature-list:HAVE_CMMD;

        description "This notification is sent when temp1 of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor1 {
            type  decimal64 {
                 fraction-digits 2;            }
        description
            "Temperature of power supply sensor 1";
        }

        leaf temp1-alert-threshold-min {
            type  decimal64 {
                 fraction-digits 2;            }
        description
            "Psu temperature 1 alert threshold minimum value";
        }

        leaf temp1-alert-threshold-max {
            type  decimal64 {
                 fraction-digits 2;            }
        description
            "Psu temperature 1 alert threshold maximum value";
        }
    }

    notification psu-temp1-high-alert {
        if-feature feature-list:HAVE_CMMD;

        description "This notification is sent when temp1 of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor1 {
            type  decimal64 {
                 fraction-digits 2;            }
        description
            "Temperature of power supply sensor 1";
        }

        leaf temp1-alert-threshold-min {
            type  decimal64 {
                 fraction-digits 2;            }
        description
            "Psu temperature 1 alert threshold minimum value";
        }

        leaf temp1-alert-threshold-max {
            type  decimal64 {
                 fraction-digits 2;            }
        description
            "Psu temperature 1 alert threshold maximum value";
        }
    }

    notification psu-temp1-low-critical {
        if-feature feature-list:HAVE_CMMD;

        description "This notification is sent when temp1 of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor1 {
            type  decimal64 {
                 fraction-digits 2;            }
        description
            "Temperature of power supply sensor 1";
        }

        leaf temp1-critical-threshold-min {
            type  decimal64 {
                 fraction-digits 2;            }
        description
            "Psu temperature 1 critical threshold minimum value";
        }

        leaf temp1-critical-threshold-max {
            type  decimal64 {
                 fraction-digits 2;            }
        description
            "Psu temperature 1 critical threshold maximum value";
        }
    }

    notification psu-temp1-high-critical {
        if-feature feature-list:HAVE_CMMD;

        description "This notification is sent when temp1 of PSU exceeds a given threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor1 {
            type  decimal64 {
                 fraction-digits 2;            }
        description
            "Temperature of power supply sensor 1";
        }

        leaf temp1-critical-threshold-min {
            type  decimal64 {
                 fraction-digits 2;            }
        description
            "Psu temperature 1 critical threshold minimum value";
        }

        leaf temp1-critical-threshold-max {
            type  decimal64 {
                 fraction-digits 2;            }
        description
            "Psu temperature 1 critical threshold maximum value";
        }
    }

    notification psu-temp1-low-alert-recovery {
        if-feature feature-list:HAVE_CMMD;

        description "This notification is sent when temp1 of PSU exceeds a given threshold.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor1 {
            type  decimal64 {
                 fraction-digits 2;            }
        description
            "Temperature of power supply sensor 1";
        }

        leaf temp1-alert-threshold-min {
            type  decimal64 {
                 fraction-digits 2;            }
        description
            "Psu temperature 1 alert threshold minimum value";
        }

        leaf temp1-alert-threshold-max {
            type  decimal64 {
                 fraction-digits 2;            }
        description
            "Psu temperature 1 alert threshold maximum value";
        }
    }

    notification psu-temp1-high-alert-recovery {
        if-feature feature-list:HAVE_CMMD;

        description "This notification is sent when temp1 violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor1 {
            type  decimal64 {
                 fraction-digits 2;            }
        description
            "Temperature of power supply sensor 1";
        }

        leaf temp1-alert-threshold-min {
            type  decimal64 {
                 fraction-digits 2;            }
        description
            "Psu temperature 1 alert threshold minimum value";
        }

        leaf temp1-alert-threshold-max {
            type  decimal64 {
                 fraction-digits 2;            }
        description
            "Psu temperature 1 alert threshold maximum value";
        }
    }

    notification psu-temp1-low-critical-recovery {
        if-feature feature-list:HAVE_CMMD;

        description "This notification is sent when temp1 violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor1 {
            type  decimal64 {
                 fraction-digits 2;            }
        description
            "Temperature of power supply sensor 1";
        }

        leaf temp1-critical-threshold-min {
            type  decimal64 {
                 fraction-digits 2;            }
        description
            "Psu temperature 1 critical threshold minimum value";
        }

        leaf temp1-critical-threshold-max {
            type  decimal64 {
                 fraction-digits 2;            }
        description
            "Psu temperature 1 critical threshold maximum value";
        }
    }

    notification psu-temp1-high-critical-recovery {
        if-feature feature-list:HAVE_CMMD;

        description "This notification is sent when temp1 violation is recovered.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor1 {
            type  decimal64 {
                 fraction-digits 2;            }
        description
            "Temperature of power supply sensor 1";
        }

        leaf temp1-critical-threshold-min {
            type  decimal64 {
                 fraction-digits 2;            }
        description
            "Psu temperature 1 critical threshold minimum value";
        }

        leaf temp1-critical-threshold-max {
            type  decimal64 {
                 fraction-digits 2;            }
        description
            "Psu temperature 1 critical threshold maximum value";
        }
    }

    notification psu-temp2-low-alert {
        if-feature feature-list:HAVE_CMMD;

        description "This notification is sent when the TEMP2 sensor of the PSU exceeds a the low alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor2 {
            type  decimal64 {
                 fraction-digits 2;            }
        description
            "Temperature of power supply sensor 2";
        }

        leaf temp2-alert-threshold-min {
            type  decimal64 {
                 fraction-digits 2;            }
        description
            "Psu temperature 2 alert threshold minimum value";
        }

        leaf temp2-alert-threshold-max {
            type  decimal64 {
                 fraction-digits 2;            }
        description
            "Psu temperature 2 alert threshold maximum value";
        }
    }

    notification psu-temp2-high-alert {
        if-feature feature-list:HAVE_CMMD;

        description "This notification is sent when the TEMP2 sensor of the PSU exceeds a the high alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor2 {
            type  decimal64 {
                 fraction-digits 2;            }
        description
            "Temperature of power supply sensor 2";
        }

        leaf temp2-alert-threshold-min {
            type  decimal64 {
                 fraction-digits 2;            }
        description
            "Psu temperature 2 alert threshold minimum value";
        }

        leaf temp2-alert-threshold-max {
            type  decimal64 {
                 fraction-digits 2;            }
        description
            "Psu temperature 2 alert threshold maximum value";
        }
    }

    notification psu-temp2-low-critical {
        if-feature feature-list:HAVE_CMMD;

        description "This notification is sent when the TEMP2 sensor of the PSU exceeds a the low critical threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor2 {
            type  decimal64 {
                 fraction-digits 2;            }
        description
            "Temperature of power supply sensor 2";
        }

        leaf temp2-critical-threshold-min {
            type  decimal64 {
                 fraction-digits 2;            }
        description
            "Psu temperature 2 critical threshold minimum value";
        }

        leaf temp2-critical-threshold-max {
            type  decimal64 {
                 fraction-digits 2;            }
        description
            "Psu temperature 2 critical threshold maximum value";
        }
    }

    notification psu-temp2-high-critical {
        if-feature feature-list:HAVE_CMMD;

        description "This notification is sent when the TEMP2 sensor of the PSU exceeds a the high critical threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor2 {
            type  decimal64 {
                 fraction-digits 2;            }
        description
            "Temperature of power supply sensor 2";
        }

        leaf temp2-critical-threshold-min {
            type  decimal64 {
                 fraction-digits 2;            }
        description
            "Psu temperature 2 critical threshold minimum value";
        }

        leaf temp2-critical-threshold-max {
            type  decimal64 {
                 fraction-digits 2;            }
        description
            "Psu temperature 2 critical threshold maximum value";
        }
    }

    notification psu-temp2-low-alert-recovery {
        if-feature feature-list:HAVE_CMMD;

        description "This notification is sent when the TEMP2 sensor of the PSU recovers from a low alert threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor2 {
            type  decimal64 {
                 fraction-digits 2;            }
        description
            "Temperature of power supply sensor 2";
        }

        leaf temp2-alert-threshold-min {
            type  decimal64 {
                 fraction-digits 2;            }
        description
            "Psu temperature 2 alert threshold minimum value";
        }

        leaf temp2-alert-threshold-max {
            type  decimal64 {
                 fraction-digits 2;            }
        description
            "Psu temperature 2 alert threshold maximum value";
        }
    }

    notification psu-temp2-high-alert-recovery {
        if-feature feature-list:HAVE_CMMD;

        description "This notification is sent when the TEMP2 sensor of the PSU recovers from a high alert threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor2 {
            type  decimal64 {
                 fraction-digits 2;            }
        description
            "Temperature of power supply sensor 2";
        }

        leaf temp2-alert-threshold-min {
            type  decimal64 {
                 fraction-digits 2;            }
        description
            "Psu temperature 2 alert threshold minimum value";
        }

        leaf temp2-alert-threshold-max {
            type  decimal64 {
                 fraction-digits 2;            }
        description
            "Psu temperature 2 alert threshold maximum value";
        }
    }

    notification psu-temp2-low-critical-recovery {
        if-feature feature-list:HAVE_CMMD;

        description "This notification is sent when the TEMP2 sensor of the PSU recovers from a low critical threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor2 {
            type  decimal64 {
                 fraction-digits 2;            }
        description
            "Temperature of power supply sensor 2";
        }

        leaf temp2-critical-threshold-min {
            type  decimal64 {
                 fraction-digits 2;            }
        description
            "Psu temperature 2 critical threshold minimum value";
        }

        leaf temp2-critical-threshold-max {
            type  decimal64 {
                 fraction-digits 2;            }
        description
            "Psu temperature 2 critical threshold maximum value";
        }
    }

    notification psu-temp2-high-critical-recovery {
        if-feature feature-list:HAVE_CMMD;

        description "This notification is sent when the TEMP2 sensor of the PSU recovers from a high critical threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor2 {
            type  decimal64 {
                 fraction-digits 2;            }
        description
            "Temperature of power supply sensor 2";
        }

        leaf temp2-critical-threshold-min {
            type  decimal64 {
                 fraction-digits 2;            }
        description
            "Psu temperature 2 critical threshold minimum value";
        }

        leaf temp2-critical-threshold-max {
            type  decimal64 {
                 fraction-digits 2;            }
        description
            "Psu temperature 2 critical threshold maximum value";
        }
    }

    notification psu-temp3-low-alert {
        if-feature feature-list:HAVE_CMMD;

        description "This notification is sent when the TEMP3 sensor of the PSU exceeds a the low alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor3 {
            type  decimal64 {
                 fraction-digits 2;            }
        description
            "Temperature of power supply sensor 3";
        }

        leaf temp3-alert-threshold-min {
            type  decimal64 {
                 fraction-digits 2;            }
        description
            "Psu temperature 3 alert threshold minimum value";
        }

        leaf temp3-alert-threshold-max {
            type  decimal64 {
                 fraction-digits 2;            }
        description
            "Psu temperature 3 alert threshold maximum value";
        }
    }

    notification psu-temp3-high-alert {
        if-feature feature-list:HAVE_CMMD;

        description "This notification is sent when the TEMP3 sensor of the PSU exceeds a the high alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor3 {
            type  decimal64 {
                 fraction-digits 2;            }
        description
            "Temperature of power supply sensor 3";
        }

        leaf temp3-alert-threshold-min {
            type  decimal64 {
                 fraction-digits 2;            }
        description
            "Psu temperature 3 alert threshold minimum value";
        }

        leaf temp3-alert-threshold-max {
            type  decimal64 {
                 fraction-digits 2;            }
        description
            "Psu temperature 3 alert threshold maximum value";
        }
    }

    notification psu-temp3-low-critical {
        if-feature feature-list:HAVE_CMMD;

        description "This notification is sent when the TEMP3 sensor of the PSU exceeds a the low critical threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor3 {
            type  decimal64 {
                 fraction-digits 2;            }
        description
            "Temperature of power supply sensor 3";
        }

        leaf temp3-critical-threshold-min {
            type  decimal64 {
                 fraction-digits 2;            }
        description
            "Psu temperature 3 critical threshold minimum value";
        }

        leaf temp3-critical-threshold-max {
            type  decimal64 {
                 fraction-digits 2;            }
        description
            "Psu temperature 3 critical threshold maximum value";
        }
    }

    notification psu-temp3-high-critical {
        if-feature feature-list:HAVE_CMMD;

        description "This notification is sent when the TEMP3 sensor of the PSU exceeds a the high critical threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor3 {
            type  decimal64 {
                 fraction-digits 2;            }
        description
            "Temperature of power supply sensor 3";
        }

        leaf temp3-critical-threshold-min {
            type  decimal64 {
                 fraction-digits 2;            }
        description
            "Psu temperature 3 critical threshold minimum value";
        }

        leaf temp3-critical-threshold-max {
            type  decimal64 {
                 fraction-digits 2;            }
        description
            "Psu temperature 3 critical threshold maximum value";
        }
    }

    notification psu-temp3-low-alert-recovery {
        if-feature feature-list:HAVE_CMMD;

        description "This notification is sent when the TEMP3 sensor of the PSU recovers from a low alert threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor3 {
            type  decimal64 {
                 fraction-digits 2;            }
        description
            "Temperature of power supply sensor 3";
        }

        leaf temp3-alert-threshold-min {
            type  decimal64 {
                 fraction-digits 2;            }
        description
            "Psu temperature 3 alert threshold minimum value";
        }

        leaf temp3-alert-threshold-max {
            type  decimal64 {
                 fraction-digits 2;            }
        description
            "Psu temperature 3 alert threshold maximum value";
        }
    }

    notification psu-temp3-high-alert-recovery {
        if-feature feature-list:HAVE_CMMD;

        description "This notification is sent when the TEMP3 sensor of the PSU recovers from a high alert threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor3 {
            type  decimal64 {
                 fraction-digits 2;            }
        description
            "Temperature of power supply sensor 3";
        }

        leaf temp3-alert-threshold-min {
            type  decimal64 {
                 fraction-digits 2;            }
        description
            "Psu temperature 3 alert threshold minimum value";
        }

        leaf temp3-alert-threshold-max {
            type  decimal64 {
                 fraction-digits 2;            }
        description
            "Psu temperature 3 alert threshold maximum value";
        }
    }

    notification psu-temp3-low-critical-recovery {
        if-feature feature-list:HAVE_CMMD;

        description "This notification is sent when the TEMP3 sensor of the PSU recovers from a low critical threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor3 {
            type  decimal64 {
                 fraction-digits 2;            }
        description
            "Temperature of power supply sensor 3";
        }

        leaf temp3-critical-threshold-min {
            type  decimal64 {
                 fraction-digits 2;            }
        description
            "Psu temperature 3 critical threshold minimum value";
        }

        leaf temp3-critical-threshold-max {
            type  decimal64 {
                 fraction-digits 2;            }
        description
            "Psu temperature 3 critical threshold maximum value";
        }
    }

    notification psu-temp3-high-critical-recovery {
        if-feature feature-list:HAVE_CMMD;

        description "This notification is sent when the TEMP3 sensor of the PSU recovers from a high critical threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor3 {
            type  decimal64 {
                 fraction-digits 2;            }
        description
            "Temperature of power supply sensor 3";
        }

        leaf temp3-critical-threshold-min {
            type  decimal64 {
                 fraction-digits 2;            }
        description
            "Psu temperature 3 critical threshold minimum value";
        }

        leaf temp3-critical-threshold-max {
            type  decimal64 {
                 fraction-digits 2;            }
        description
            "Psu temperature 3 critical threshold maximum value";
        }
    }

    notification psu-temp4-low-alert {
        if-feature feature-list:HAVE_CMMD;

        description "This notification is sent when the TEMP4 sensor of the PSU exceeds a the low alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor4 {
            type  decimal64 {
                 fraction-digits 2;            }
        description
            "Temperature of power supply sensor 4";
        }

        leaf temp4-alert-threshold-min {
            type  decimal64 {
                 fraction-digits 2;            }
        description
            "Psu temperature 4 alert threshold minimum value";
        }

        leaf temp4-alert-threshold-max {
            type  decimal64 {
                 fraction-digits 2;            }
        description
            "Psu temperature 4 alert threshold maximum value";
        }
    }

    notification psu-temp4-high-alert {
        if-feature feature-list:HAVE_CMMD;

        description "This notification is sent when the TEMP2 sensor of the PSU exceeds a the high alert threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor4 {
            type  decimal64 {
                 fraction-digits 2;            }
        description
            "Temperature of power supply sensor 4";
        }

        leaf temp4-alert-threshold-min {
            type  decimal64 {
                 fraction-digits 2;            }
        description
            "Psu temperature 4 alert threshold minimum value";
        }

        leaf temp4-alert-threshold-max {
            type  decimal64 {
                 fraction-digits 2;            }
        description
            "Psu temperature 4 alert threshold maximum value";
        }
    }

    notification psu-temp4-low-critical {
        if-feature feature-list:HAVE_CMMD;

        description "This notification is sent when the TEMP4 sensor of the PSU exceeds a the low critical threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor4 {
            type  decimal64 {
                 fraction-digits 2;            }
        description
            "Temperature of power supply sensor 4";
        }

        leaf temp4-critical-threshold-min {
            type  decimal64 {
                 fraction-digits 2;            }
        description
            "Psu temperature 4 critical threshold minimum value";
        }

        leaf temp4-critical-threshold-max {
            type  decimal64 {
                 fraction-digits 2;            }
        description
            "Psu temperature 4 critical threshold maximum value";
        }
    }

    notification psu-temp4-high-critical {
        if-feature feature-list:HAVE_CMMD;

        description "This notification is sent when the TEMP4 sensor of the PSU exceeds a the high critical threshold.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf temperature-sensor4 {
            type  decimal64 {
                 fraction-digits 2;            }
        description
            "Temperature of power supply sensor 4";
        }

        leaf temp4-critical-threshold-min {
            type  decimal64 {
                 fraction-digits 2;            }
        description
            "Psu temperature 4 critical threshold minimum value";
        }

        leaf temp4-critical-threshold-max {
            type  decimal64 {
                 fraction-digits 2;            }
        description
            "Psu temperature 4 critical threshold maximum value";
        }
    }

    notification psu-temp4-low-alert-recovery {
        if-feature feature-list:HAVE_CMMD;

        description "This notification is sent when the TEMP4 sensor of the PSU recovers from a low alert threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor4 {
            type  decimal64 {
                 fraction-digits 2;            }
        description
            "Temperature of power supply sensor 4";
        }

        leaf temp4-alert-threshold-min {
            type  decimal64 {
                 fraction-digits 2;            }
        description
            "Psu temperature 4 alert threshold minimum value";
        }

        leaf temp4-alert-threshold-max {
            type  decimal64 {
                 fraction-digits 2;            }
        description
            "Psu temperature 4 alert threshold maximum value";
        }
    }

    notification psu-temp4-high-alert-recovery {
        if-feature feature-list:HAVE_CMMD;

        description "This notification is sent when the TEMP4 sensor of the PSU recovers from a high alert threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor4 {
            type  decimal64 {
                 fraction-digits 2;            }
        description
            "Temperature of power supply sensor 4";
        }

        leaf temp4-alert-threshold-min {
            type  decimal64 {
                 fraction-digits 2;            }
        description
            "Psu temperature 4 alert threshold minimum value";
        }

        leaf temp4-alert-threshold-max {
            type  decimal64 {
                 fraction-digits 2;            }
        description
            "Psu temperature 4 alert threshold maximum value";
        }
    }

    notification psu-temp4-low-critical-recovery {
        if-feature feature-list:HAVE_CMMD;

        description "This notification is sent when the TEMP4 sensor of the PSU recovers from a low critical threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor4 {
            type  decimal64 {
                 fraction-digits 2;            }
        description
            "Temperature of power supply sensor 4";
        }

        leaf temp4-critical-threshold-min {
            type  decimal64 {
                 fraction-digits 2;            }
        description
            "Psu temperature 4 critical threshold minimum value";
        }

        leaf temp4-critical-threshold-max {
            type  decimal64 {
                 fraction-digits 2;            }
        description
            "Psu temperature 4 critical threshold maximum value";
        }
    }

    notification psu-temp4-high-critical-recovery {
        if-feature feature-list:HAVE_CMMD;

        description "This notification is sent when the TEMP4 sensor of the PSU recovers from a high critical threshold crossing.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf temperature-sensor4 {
            type  decimal64 {
                 fraction-digits 2;            }
        description
            "Temperature of power supply sensor 4";
        }

        leaf temp4-critical-threshold-min {
            type  decimal64 {
                 fraction-digits 2;            }
        description
            "Psu temperature 4 critical threshold minimum value";
        }

        leaf temp4-critical-threshold-max {
            type  decimal64 {
                 fraction-digits 2;            }
        description
            "Psu temperature 4 critical threshold maximum value";
        }
    }

    notification fan-status-alarm {
        if-feature feature-list:HAVE_CMMD;

        description "This notification is sent when fan is in alarm state.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf fan-index {
            type  uint8;
        description
            "Fan identifier index in the system";
        }

        leaf fan-status {
            type  cml_cmm_fan_status_t;
        description
            "The status of the fan";
        }
    }

    notification fan-status-alarm-recovery {
        if-feature feature-list:HAVE_CMMD;

        description "This notification is sent when fan recovers from an alarm state.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf fan-index {
            type  uint8;
        description
            "Fan identifier index in the system";
        }

        leaf fan-status {
            type  cml_cmm_fan_status_t;
        description
            "The status of the fan";
        }
    }

    notification fan-rpm-max-alert {
        if-feature feature-list:HAVE_CMMD;

        description "This notification is sent when fan RPM set to its maximum value..";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf maximum-rpm {
            type  uint32;
        description
            "Value represents the maximum supported RPM of fan";
        }
    }

    notification fan-rpm-decreased-notify {
        if-feature feature-list:HAVE_CMMD;

        description "This notification is sent when fan RPM decreased from previous RPM..";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf rpm {
            type  uint32;
        description
            "Fan speed expressed in Rotations Per Minute";
        }
    }

    notification fan-rpm-increased-notify {
        if-feature feature-list:HAVE_CMMD;

        description "This notification is sent when fan RPM increased from previous RPM..";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf rpm {
            type  uint32;
        description
            "Fan speed expressed in Rotations Per Minute";
        }
    }

    notification fan-tray-inserted {
        if-feature feature-list:HAVE_CMMD;

        description "This notification is sent when fan tray is inserted.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }
    }

    notification fan-tray-absent {
        if-feature feature-list:HAVE_CMMD;

        description "This notification is sent when fan tray is removed or not present during bootup.";

        leaf severity {
            type cml-data-types:cml_notif_severity_t;
            description "Notification severity level (value: WARNING)";
        }

        leaf eventClass {
            type cml-data-types:cml_notif_class_t;
            description "Notification event class (value: STATE)";
        }

        leaf name {
            type  string;
        description
            "References the component name";
        }
    }

    notification hardware-tcam-util-warning-notification {
        if-feature feature-list:HAVE_CMMD;
        if-feature feature-list:HAVE_BROADCOM;
        if-feature feature-list:HAVE_BROADCOM_OR_HAVE_MARVELL;

        description "This notification is generated when number of entries in TCAM group crosses the warning threshold limit..";

        leaf severity {
            type cml-data-types:cml_notif_severity_t;
            description "Notification severity level (value: MINOR)";
        }

        leaf eventClass {
            type cml-data-types:cml_notif_class_t;
            description "Notification event class (value: STATE)";
        }

        leaf group-id {
            type  uint32;
        description
            "A unique number corresponding to each TCAM group. This attribute is
                    used solely for defining the key for the TCAM utilization filter
                    groups object list. It's value shouldn't be interpreted.";
        }

        leaf unit {
            type  uint32;
        description
            "Unit ID";
        }

        leaf core {
            type  uint32;
        description
            "Core ID";
        }

        leaf group-name {
            type cml-data-types:cml_line_t;
        description
            "TCAM Utilization filter group name.";
        }

        leaf used-percentage {
            type  int32;
        description
            "Percentage of entries used in the TCAM group. Value of -1 means the
                    field is not applicable.";
        }

        leaf free-entries {
            type  int32;
        description
            "Count of free entries in the TCAM group. Value of -1 means the field
                    is not applicable.";
        }
    }

    notification hardware-tcam-util-recovery-warning-notification {
        if-feature feature-list:HAVE_CMMD;
        if-feature feature-list:HAVE_BROADCOM;
        if-feature feature-list:HAVE_BROADCOM_OR_HAVE_MARVELL;

        description "This notification is generated when number of entries in TCAM group recovers from warning threshold limit..";

        leaf severity {
            type cml-data-types:cml_notif_severity_t;
            description "Notification severity level (value: WARNING)";
        }

        leaf eventClass {
            type cml-data-types:cml_notif_class_t;
            description "Notification event class (value: STATE)";
        }

        leaf group-id {
            type  uint32;
        description
            "A unique number corresponding to each TCAM group. This attribute is
                    used solely for defining the key for the TCAM utilization filter
                    groups object list. It's value shouldn't be interpreted.";
        }

        leaf unit {
            type  uint32;
        description
            "Unit ID";
        }

        leaf core {
            type  uint32;
        description
            "Core ID";
        }

        leaf group-name {
            type cml-data-types:cml_line_t;
        description
            "TCAM Utilization filter group name.";
        }

        leaf used-percentage {
            type  int32;
        description
            "Percentage of entries used in the TCAM group. Value of -1 means the
                    field is not applicable.";
        }

        leaf free-entries {
            type  int32;
        description
            "Count of free entries in the TCAM group. Value of -1 means the field
                    is not applicable.";
        }
    }

    notification hardware-tcam-util-critical-notification {
        if-feature feature-list:HAVE_CMMD;
        if-feature feature-list:HAVE_BROADCOM;
        if-feature feature-list:HAVE_BROADCOM_OR_HAVE_MARVELL;

        description "This notification is generated when number of entries in TCAM group crosses the critical threshold limit..";

        leaf severity {
            type cml-data-types:cml_notif_severity_t;
            description "Notification severity level (value: MAJOR)";
        }

        leaf eventClass {
            type cml-data-types:cml_notif_class_t;
            description "Notification event class (value: STATE)";
        }

        leaf group-id {
            type  uint32;
        description
            "A unique number corresponding to each TCAM group. This attribute is
                    used solely for defining the key for the TCAM utilization filter
                    groups object list. It's value shouldn't be interpreted.";
        }

        leaf unit {
            type  uint32;
        description
            "Unit ID";
        }

        leaf core {
            type  uint32;
        description
            "Core ID";
        }

        leaf group-name {
            type cml-data-types:cml_line_t;
        description
            "TCAM Utilization filter group name.";
        }

        leaf used-percentage {
            type  int32;
        description
            "Percentage of entries used in the TCAM group. Value of -1 means the
                    field is not applicable.";
        }

        leaf free-entries {
            type  int32;
        description
            "Count of free entries in the TCAM group. Value of -1 means the field
                    is not applicable.";
        }
    }

    notification hardware-tcam-util-recovery-critical-notification {
        if-feature feature-list:HAVE_CMMD;
        if-feature feature-list:HAVE_BROADCOM;
        if-feature feature-list:HAVE_BROADCOM_OR_HAVE_MARVELL;

        description "This notification is generated when number of entries in TCAM group recovers from the critical threshold limit..";

        leaf severity {
            type cml-data-types:cml_notif_severity_t;
            description "Notification severity level (value: WARNING)";
        }

        leaf eventClass {
            type cml-data-types:cml_notif_class_t;
            description "Notification event class (value: STATE)";
        }

        leaf group-id {
            type  uint32;
        description
            "A unique number corresponding to each TCAM group. This attribute is
                    used solely for defining the key for the TCAM utilization filter
                    groups object list. It's value shouldn't be interpreted.";
        }

        leaf unit {
            type  uint32;
        description
            "Unit ID";
        }

        leaf core {
            type  uint32;
        description
            "Core ID";
        }

        leaf group-name {
            type cml-data-types:cml_line_t;
        description
            "TCAM Utilization filter group name.";
        }

        leaf used-percentage {
            type  int32;
        description
            "Percentage of entries used in the TCAM group. Value of -1 means the
                    field is not applicable.";
        }

        leaf free-entries {
            type  int32;
        description
            "Count of free entries in the TCAM group. Value of -1 means the field
                    is not applicable.";
        }
    }

    notification platform-interface-load-balance-update {
        if-feature feature-list:HAVE_CMMD;
        if-feature feature-list:HAVE_BROADCOM_OR_HAVE_MARVELL;
        if-feature feature-list:NOT_HAVE_DUNE;
        if-feature feature-list:NOT_HAVE_MARVELL;

        description "Notify load-balance update on a member interface.";

        leaf severity {
            type cml-data-types:cml_notif_severity_t;
            description "Notification severity level (value: INFO)";
        }

        leaf eventClass {
            type cml-data-types:cml_notif_class_t;
            description "Notification event class (value: CONFIG)";
        }

        leaf name {
            type  string;
        description
            "Interface name for which OSPFv3 is being configured.";
        }

        leaf type {
            type ipi-platform-profile-types:platform_lacp_psc_t;
        description
            "This Object is used to set LACP port-channel load-balancing and set
                    port selection criteria (PSC) on an interface";
        }
    }

    notification platform-interface-load-balance-unset {
        if-feature feature-list:HAVE_CMMD;
        if-feature feature-list:HAVE_BROADCOM_OR_HAVE_MARVELL;
        if-feature feature-list:NOT_HAVE_DUNE;
        if-feature feature-list:NOT_HAVE_MARVELL;

        description "Notify load-balance delete on a member interface.";

        leaf severity {
            type cml-data-types:cml_notif_severity_t;
            description "Notification severity level (value: INFO)";
        }

        leaf eventClass {
            type cml-data-types:cml_notif_class_t;
            description "Notification event class (value: CONFIG)";
        }

        leaf name {
            type  string;
        description
            "Interface name for which OSPFv3 is being configured.";
        }

        leaf type {
            type ipi-platform-profile-types:platform_lacp_psc_t;
        description
            "This Object is used to set LACP port-channel load-balancing and set
                    port selection criteria (PSC) on an interface";
        }
    }

    notification loss-of-input-clock {
        if-feature feature-list:HAVE_CMMD;
        if-feature feature-list:NOT_HAVE_ARM_ARCH;

        description "Notification for Loss of Input Clock event.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf loss-of-input-clock-status {
            type  uint8;
        description
            "CLU Input Clock loss Status";
        }
    }

    notification usb-over-current {
        if-feature feature-list:HAVE_CMMD;
        if-feature feature-list:NOT_HAVE_ARM_ARCH;

        description "Notification for USB Over Current event.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf usb-over-current-status {
            type  uint8;
        description
            "USB Over Current Status";
        }
    }

    notification cmis-module-monitor-alarm-notification {
        if-feature feature-list:HAVE_CMMD;
        if-feature feature-list:NOT_HAVE_TIBIT;

        description "This notification is sent when a module monitored parameter enters an abnormal condition.";

        leaf severity {
            type cml-data-types:cml_notif_severity_t;
            description "Notification severity level (value: CRITICAL)";
        }

        leaf eventClass {
            type cml-data-types:cml_notif_class_t;
            description "Notification event class (value: STATE)";
        }

        leaf name {
            type  string;
        description
            "References the component name";
        }

        leaf alarm-id {
            type ipi-platform-cmis-types:cmm_cmis_module_monitor_id_t;
        description
            "Threshold alarm ID";
        }

        leaf alarm-type {
            type ipi-platform-cmis-types:cmm_cmis_threshold_alarm_t;
        description
            "Threshold alarm type";
        }

        leaf current-value {
            type  decimal64 {
                 fraction-digits 2;            }
        description
            "Current monitor value";
        }

        leaf threshold-minimum {
            type  decimal64 {
                 fraction-digits 2;            }
        description
            "Threshold minimum value";
        }

        leaf threshold-maximum {
            type  decimal64 {
                 fraction-digits 2;            }
        description
            "Threshold maximum value";
        }
    }

    notification cmis-module-monitor-recovery-notification {
        if-feature feature-list:HAVE_CMMD;
        if-feature feature-list:NOT_HAVE_TIBIT;

        description "This notification is sent when a module monitored paramater returns to a normal condition.";

        leaf severity {
            type cml-data-types:cml_notif_severity_t;
            description "Notification severity level (value: INFO)";
        }

        leaf eventClass {
            type cml-data-types:cml_notif_class_t;
            description "Notification event class (value: STATE)";
        }

        leaf name {
            type  string;
        description
            "References the component name";
        }

        leaf alarm-id {
            type ipi-platform-cmis-types:cmm_cmis_module_monitor_id_t;
        description
            "Threshold alarm ID";
        }

        leaf alarm-type {
            type ipi-platform-cmis-types:cmm_cmis_threshold_alarm_t;
        description
            "Threshold alarm type";
        }

        leaf current-value {
            type  decimal64 {
                 fraction-digits 2;            }
        description
            "Current monitor value";
        }

        leaf threshold-minimum {
            type  decimal64 {
                 fraction-digits 2;            }
        description
            "Threshold minimum value";
        }

        leaf threshold-maximum {
            type  decimal64 {
                 fraction-digits 2;            }
        description
            "Threshold maximum value";
        }
    }

    notification cmis-module-host-monitor-alarm-notification {
        if-feature feature-list:HAVE_CMMD;
        if-feature feature-list:NOT_HAVE_TIBIT;

        description "This notification is sent when a host side monitored parameter enters an abnormal condition.";

        leaf severity {
            type cml-data-types:cml_notif_severity_t;
            description "Notification severity level (value: CRITICAL)";
        }

        leaf eventClass {
            type cml-data-types:cml_notif_class_t;
            description "Notification event class (value: STATE)";
        }

        leaf number {
            type  uint8;
        description
            "Host side lane number";
        }

        leaf name {
            type  string;
        description
            "References the component name";
        }

        leaf alarm-id {
            type ipi-platform-cmis-types:cmm_cmis_host_monitor_id_t;
        description
            "Threshold alarm ID";
        }

        leaf alarm-type {
            type ipi-platform-cmis-types:cmm_cmis_threshold_alarm_t;
        description
            "Threshold alarm type";
        }

        leaf current-value {
            type  decimal64 {
                 fraction-digits 2;            }
        description
            "Current monitor value";
        }

        leaf threshold-minimum {
            type  decimal64 {
                 fraction-digits 2;            }
        description
            "Threshold minimum value";
        }

        leaf threshold-maximum {
            type  decimal64 {
                 fraction-digits 2;            }
        description
            "Threshold maximum value";
        }
    }

    notification cmis-module-host-monitor-recovery-notification {
        if-feature feature-list:HAVE_CMMD;
        if-feature feature-list:NOT_HAVE_TIBIT;

        description "This notification is sent when a host side monitored paramater returns to a normal condition.";

        leaf severity {
            type cml-data-types:cml_notif_severity_t;
            description "Notification severity level (value: INFO)";
        }

        leaf eventClass {
            type cml-data-types:cml_notif_class_t;
            description "Notification event class (value: STATE)";
        }

        leaf number {
            type  uint8;
        description
            "Host side lane number";
        }

        leaf name {
            type  string;
        description
            "References the component name";
        }

        leaf alarm-id {
            type ipi-platform-cmis-types:cmm_cmis_host_monitor_id_t;
        description
            "Threshold alarm ID";
        }

        leaf alarm-type {
            type ipi-platform-cmis-types:cmm_cmis_threshold_alarm_t;
        description
            "Threshold alarm type";
        }

        leaf current-value {
            type  decimal64 {
                 fraction-digits 2;            }
        description
            "Current monitor value";
        }

        leaf threshold-minimum {
            type  decimal64 {
                 fraction-digits 2;            }
        description
            "Threshold minimum value";
        }

        leaf threshold-maximum {
            type  decimal64 {
                 fraction-digits 2;            }
        description
            "Threshold maximum value";
        }
    }

    notification cmis-module-host-flag-alarm-notification {
        if-feature feature-list:HAVE_CMMD;
        if-feature feature-list:NOT_HAVE_TIBIT;

        description "This notification is sent when a host side flag enters an abnormal condition.";

        leaf severity {
            type cml-data-types:cml_notif_severity_t;
            description "Notification severity level (value: CRITICAL)";
        }

        leaf eventClass {
            type cml-data-types:cml_notif_class_t;
            description "Notification event class (value: STATE)";
        }

        leaf number {
            type  uint8;
        description
            "Host side lane number";
        }

        leaf name {
            type  string;
        description
            "References the component name";
        }

        leaf alarm-id {
            type ipi-platform-cmis-types:cmm_cmis_host_flag_id_t;
        description
            "Flag alarm ID";
        }
    }

    notification cmis-module-host-flag-recovery-notification {
        if-feature feature-list:HAVE_CMMD;
        if-feature feature-list:NOT_HAVE_TIBIT;

        description "This notification is sent when a host side flag returns to a normal condition.";

        leaf severity {
            type cml-data-types:cml_notif_severity_t;
            description "Notification severity level (value: INFO)";
        }

        leaf eventClass {
            type cml-data-types:cml_notif_class_t;
            description "Notification event class (value: STATE)";
        }

        leaf number {
            type  uint8;
        description
            "Host side lane number";
        }

        leaf name {
            type  string;
        description
            "References the component name";
        }

        leaf alarm-id {
            type ipi-platform-cmis-types:cmm_cmis_host_flag_id_t;
        description
            "Flag alarm ID";
        }
    }

    notification cmis-module-media-monitor-alarm-notification {
        if-feature feature-list:HAVE_CMMD;
        if-feature feature-list:NOT_HAVE_TIBIT;

        description "This notification is sent when a media side monitored parameter enters an abnormal condition.";

        leaf severity {
            type cml-data-types:cml_notif_severity_t;
            description "Notification severity level (value: CRITICAL)";
        }

        leaf eventClass {
            type cml-data-types:cml_notif_class_t;
            description "Notification event class (value: STATE)";
        }

        leaf number {
            type  uint8;
        description
            "media side lane number";
        }

        leaf name {
            type  string;
        description
            "References the component name";
        }

        leaf alarm-id {
            type ipi-platform-cmis-types:cmm_cmis_media_monitor_id_t;
        description
            "Threshold alarm ID";
        }

        leaf alarm-type {
            type ipi-platform-cmis-types:cmm_cmis_threshold_alarm_t;
        description
            "Threshold alarm type";
        }

        leaf current-value {
            type  decimal64 {
                 fraction-digits 2;            }
        description
            "Current monitor value";
        }

        leaf threshold-minimum {
            type  decimal64 {
                 fraction-digits 2;            }
        description
            "Threshold minimum value";
        }

        leaf threshold-maximum {
            type  decimal64 {
                 fraction-digits 2;            }
        description
            "Threshold maximum value";
        }
    }

    notification cmis-module-media-monitor-recovery-notification {
        if-feature feature-list:HAVE_CMMD;
        if-feature feature-list:NOT_HAVE_TIBIT;

        description "This notification is sent when a media side monitored paramater returns to a normal condition.";

        leaf severity {
            type cml-data-types:cml_notif_severity_t;
            description "Notification severity level (value: INFO)";
        }

        leaf eventClass {
            type cml-data-types:cml_notif_class_t;
            description "Notification event class (value: STATE)";
        }

        leaf number {
            type  uint8;
        description
            "media side lane number";
        }

        leaf name {
            type  string;
        description
            "References the component name";
        }

        leaf alarm-id {
            type ipi-platform-cmis-types:cmm_cmis_media_monitor_id_t;
        description
            "Threshold alarm ID";
        }

        leaf alarm-type {
            type ipi-platform-cmis-types:cmm_cmis_threshold_alarm_t;
        description
            "Threshold alarm type";
        }

        leaf current-value {
            type  decimal64 {
                 fraction-digits 2;            }
        description
            "Current monitor value";
        }

        leaf threshold-minimum {
            type  decimal64 {
                 fraction-digits 2;            }
        description
            "Threshold minimum value";
        }

        leaf threshold-maximum {
            type  decimal64 {
                 fraction-digits 2;            }
        description
            "Threshold maximum value";
        }
    }

    notification cmis-module-media-flag-alarm-notification {
        if-feature feature-list:HAVE_CMMD;
        if-feature feature-list:NOT_HAVE_TIBIT;

        description "This notification is sent when a media side flag enters an abnormal condition.";

        leaf severity {
            type cml-data-types:cml_notif_severity_t;
            description "Notification severity level (value: CRITICAL)";
        }

        leaf eventClass {
            type cml-data-types:cml_notif_class_t;
            description "Notification event class (value: STATE)";
        }

        leaf number {
            type  uint8;
        description
            "media side lane number";
        }

        leaf name {
            type  string;
        description
            "References the component name";
        }

        leaf alarm-id {
            type ipi-platform-cmis-types:cmm_cmis_media_flag_id_t;
        description
            "Flag alarm ID";
        }
    }

    notification cmis-module-media-flag-recovery-notification {
        if-feature feature-list:HAVE_CMMD;
        if-feature feature-list:NOT_HAVE_TIBIT;

        description "This notification is sent when a media side flag returns to a normal condition.";

        leaf severity {
            type cml-data-types:cml_notif_severity_t;
            description "Notification severity level (value: INFO)";
        }

        leaf eventClass {
            type cml-data-types:cml_notif_class_t;
            description "Notification event class (value: STATE)";
        }

        leaf number {
            type  uint8;
        description
            "media side lane number";
        }

        leaf name {
            type  string;
        description
            "References the component name";
        }

        leaf alarm-id {
            type ipi-platform-cmis-types:cmm_cmis_media_flag_id_t;
        description
            "Flag alarm ID";
        }
    }

    notification edfa-alarm-notification {
        if-feature feature-list:HAVE_CMMD;

        description "This notification is sent when an EDFA monitored parameter enters an abnormal condition.";

        leaf severity {
            type cml-data-types:cml_notif_severity_t;
            description "Notification severity level (value: CRITICAL)";
        }

        leaf eventClass {
            type cml-data-types:cml_notif_class_t;
            description "Notification event class (value: STATE)";
        }

        leaf port {
            type  uint8;
        description
            "A value for each panel port within the unit";
        }

        leaf name {
            type  string;
        description
            "References the component name";
        }

        leaf alarm-id {
            type ipi-platform-transceiver-types:cmm_edfa_ddm_monitor_id_t;
        description
            "Threshold alarm ID";
        }

        leaf alarm-type {
            type ipi-platform-transceiver-types:cmm_ddm_threshold_alarm_t;
        description
            "Threshold alarm type";
        }

        leaf current-value {
            type  decimal64 {
                 fraction-digits 3;            }
        description
            "Current monitor value";
        }

        leaf threshold-minimum {
            type  decimal64 {
                 fraction-digits 3;            }
        description
            "Threshold minimum value";
        }

        leaf threshold-maximum {
            type  decimal64 {
                 fraction-digits 3;            }
        description
            "Threshold maximum value";
        }
    }

    notification edfa-alarm-recovery-notification {
        if-feature feature-list:HAVE_CMMD;

        description "This notification is sent when an EDFA monitored paramater returns to a normal condition.";

        leaf severity {
            type cml-data-types:cml_notif_severity_t;
            description "Notification severity level (value: INFO)";
        }

        leaf eventClass {
            type cml-data-types:cml_notif_class_t;
            description "Notification event class (value: STATE)";
        }

        leaf port {
            type  uint8;
        description
            "A value for each panel port within the unit";
        }

        leaf name {
            type  string;
        description
            "References the component name";
        }

        leaf alarm-id {
            type ipi-platform-transceiver-types:cmm_edfa_ddm_monitor_id_t;
        description
            "Threshold alarm ID";
        }

        leaf current-value {
            type  decimal64 {
                 fraction-digits 3;            }
        description
            "Current monitor value";
        }

        leaf threshold-minimum {
            type  decimal64 {
                 fraction-digits 3;            }
        description
            "Threshold minimum value";
        }

        leaf threshold-maximum {
            type  decimal64 {
                 fraction-digits 3;            }
        description
            "Threshold maximum value";
        }
    }

    notification smart-sfp-ddm-alarm-notification {
        if-feature feature-list:HAVE_CMMD;

        description "This notification is sent when a Smart SFP DDM monitored parameter enters an abnormal condition.";

        leaf severity {
            type cml-data-types:cml_notif_severity_t;
            description "Notification severity level (value: CRITICAL)";
        }

        leaf eventClass {
            type cml-data-types:cml_notif_class_t;
            description "Notification event class (value: STATE)";
        }

        leaf port {
            type  uint8;
        description
            "A value for each panel port within the unit";
        }

        leaf name {
            type  string;
        description
            "References the component name";
        }

        leaf alarm-id {
            type ipi-platform-transceiver-types:cmm_smart_sfp_ddm_monitor_id_t;
        description
            "Threshold alarm ID";
        }

        leaf alarm-type {
            type ipi-platform-transceiver-types:cmm_ddm_threshold_alarm_t;
        description
            "Threshold alarm type";
        }

        leaf current-value {
            type  decimal64 {
                 fraction-digits 3;            }
        description
            "Current monitor value";
        }

        leaf threshold-minimum {
            type  decimal64 {
                 fraction-digits 3;            }
        description
            "Threshold minimum value";
        }

        leaf threshold-maximum {
            type  decimal64 {
                 fraction-digits 3;            }
        description
            "Threshold maximum value";
        }
    }

    notification smart-sfp-ddm-alarm-recovery-notification {
        if-feature feature-list:HAVE_CMMD;

        description "This notification is sent when a Smart SFP DDM monitored paramater returns to a normal condition.";

        leaf severity {
            type cml-data-types:cml_notif_severity_t;
            description "Notification severity level (value: INFO)";
        }

        leaf eventClass {
            type cml-data-types:cml_notif_class_t;
            description "Notification event class (value: STATE)";
        }

        leaf port {
            type  uint8;
        description
            "A value for each panel port within the unit";
        }

        leaf name {
            type  string;
        description
            "References the component name";
        }

        leaf alarm-id {
            type ipi-platform-transceiver-types:cmm_smart_sfp_ddm_monitor_id_t;
        description
            "Threshold alarm ID";
        }

        leaf current-value {
            type  decimal64 {
                 fraction-digits 3;            }
        description
            "Current monitor value";
        }

        leaf threshold-minimum {
            type  decimal64 {
                 fraction-digits 3;            }
        description
            "Threshold minimum value";
        }

        leaf threshold-maximum {
            type  decimal64 {
                 fraction-digits 3;            }
        description
            "Threshold maximum value";
        }
    }

    notification smart-sfp-descrete-alarm-notification {
        if-feature feature-list:HAVE_CMMD;

        description "This notification is sent when a Smart SFP descrete monitored parameter enters an abnormal condition.";

        leaf severity {
            type cml-data-types:cml_notif_severity_t;
            description "Notification severity level (value: CRITICAL)";
        }

        leaf eventClass {
            type cml-data-types:cml_notif_class_t;
            description "Notification event class (value: STATE)";
        }

        leaf port {
            type  uint8;
        description
            "A value for each panel port within the unit";
        }

        leaf name {
            type  string;
        description
            "References the component name";
        }

        leaf alarm-id {
            type ipi-platform-transceiver-types:cmm_smart_sfp_protocol_alarm_id_t;
        description
            "Remote SFP protocol alarm ID";
        }

        leaf current-status {
            type ipi-platform-transceiver-types:cmm_smart_sfp_protocol_status_t;
        description
            "Remote SFP protocol alarm status";
        }
    }

    notification smart-sfp-descrete-alarm-recovery-notification {
        if-feature feature-list:HAVE_CMMD;

        description "This notification is sent when a Smart SFP descrete monitored paramater returns to a normal condition.";

        leaf severity {
            type cml-data-types:cml_notif_severity_t;
            description "Notification severity level (value: INFO)";
        }

        leaf eventClass {
            type cml-data-types:cml_notif_class_t;
            description "Notification event class (value: STATE)";
        }

        leaf port {
            type  uint8;
        description
            "A value for each panel port within the unit";
        }

        leaf name {
            type  string;
        description
            "References the component name";
        }

        leaf alarm-id {
            type ipi-platform-transceiver-types:cmm_smart_sfp_protocol_alarm_id_t;
        description
            "Remote SFP protocol alarm ID";
        }

        leaf current-status {
            type ipi-platform-transceiver-types:cmm_smart_sfp_protocol_status_t;
        description
            "Remote SFP protocol alarm status";
        }
    }

}
