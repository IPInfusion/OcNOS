/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-gps.yang
*
*/

submodule ipi-platform-gps {

    yang-version 1.1;

    belongs-to  ipi-platform { prefix ipi-platform; }

    import feature-list {
        prefix feature-list;
        revision-date 2026-09-15;
    }

    import ipi-platform-types {
        prefix ipi-platform-types;
        revision-date 2026-04-16;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for GPS information";


    revision "2024-07-01" {
        description "Add GPS GNSS status";
        reference " 0.1.0.";
    }

    grouping gps-gnss-status-state {
        description
            "Grouping for GPS GNSS status state";
        leaf gnss-fix  {
            type  string {
                length "1..1965";
            }
            description "Global navigation satellite system (GNSS)";
        } // END of gnss-fix definition.

        leaf latitude  {
            type  string {
                length "1..1965";
            }
            description "GNSS Latitude";
        } // END of latitude definition.

        leaf longitude  {
            type  string {
                length "1..1965";
            }
            description "GNSS Longitude";
        } // END of longitude definition.

        leaf altitude  {
            type  string {
                length "1..1965";
            }
            description "GNSS Altitude";
        } // END of altitude definition.

    } // END of gps-gnss-status-state definition.
    grouping gps-gnss-status {
        description
            "Grouping for GPS GNSS status";
        container gnss-status {
            config false;
            description
                "GNSS status";
            container state {
                config false;
                description
                    "Operational state data for GNSS status";
                uses gps-gnss-status-state;
            } // END of state-container definition.
        } // END of gnss-status-container definition.
    } // END of gps-gnss-status definition.
    grouping gps-gnss-satellite-status-state {
        description
            "Grouping for GPS GNSS satellite status state";
        leaf sat-index  {
            type  uint8;
            description "Satellite index";
        } // END of sat-index definition.

        leaf type  {
            type  string {
                length "1..1965";
            }
            description "GNSS type";
        } // END of type definition.

        leaf prn  {
            type  string {
                length "1..1965";
            }
            description "Pseudo-Random Noise (PRN)";
        } // END of prn definition.

        leaf snr  {
            type  string {
                length "1..1965";
            }
            description "Carrier-to-Noise Density Ratio (C/No)";
        } // END of snr definition.

        leaf status  {
            type  ipi-platform-types:cml_gps_gnss_status_t;
            description "Status";
        } // END of status definition.

        leaf azimuth  {
            type  string {
                length "1..1965";
            }
            description "Azimuth";
        } // END of azimuth definition.

        leaf elevation  {
            type  string {
                length "1..1965";
            }
            description "Elevation";
        } // END of elevation definition.

    } // END of gps-gnss-satellite-status-state definition.
    grouping gps-gnss-satellite-status {
        description
            "Grouping for GPS GNSS satellite status";
        container gnss-satellites-status {
            config false;
            description
                "GNSS Satellite status";

            list gnss-satellite-status {
                key "sat-index";
                config false;
                description
                    "List of GNSS satellites";
                leaf sat-index  {
                    type  leafref {
                        path  "../state/sat-index";
                    }
                    description "GNSS satellite status index.";
                } // END of sat-index definition.

                container state {
                    config false;
                    description
                        "Operational state data for GNSS Satellite status";
                    uses gps-gnss-satellite-status-state;
                } // END of state-container definition.
            } // End of gnss-satellite-status-list
        } // END of gnss-satellites-status-container definition.
    } // END of gps-gnss-satellite-status definition.
    grouping gps-gnss-survey-in-status-state {
        description
            "Grouping for GPS GNSS statistics survey-in status state";
        leaf min-duration  {
            type  string {
                length "1..1965";
            }
            description "Minimum Duration";
        } // END of min-duration definition.

        leaf accuracy  {
            type  string {
                length "1..1965";
            }
            description "Accuracy";
        } // END of accuracy definition.

        leaf is-valid  {
            type  boolean;
            description "Valid flag";
        } // END of is-valid definition.

        leaf is-active  {
            type  boolean;
            description "Active flag";
        } // END of is-active definition.

        leaf duration  {
            type  string {
                length "1..1965";
            }
            description "Duration";
        } // END of duration definition.

        leaf variance  {
            type  string {
                length "1..1965";
            }
            description "Variance";
        } // END of variance definition.

    } // END of gps-gnss-survey-in-status-state definition.
    grouping gps-gnss-survey-in-status {
        description
            "Grouping for GPS GNSS survey-in status";
        container gnss-survey-in-status {
            config false;
            description
                "GNSS status";
            container state {
                config false;
                description
                    "Operational state data for GNSS survey-in status";
                uses gps-gnss-survey-in-status-state;
            } // END of state-container definition.
        } // END of gnss-survey-in-status-container definition.
    } // END of gps-gnss-survey-in-status definition.
    grouping gps-gnss-fix-position-status-state {
        description
            "Grouping for GPS GNSS statistics status state";
        leaf latitude  {
            type  string {
                length "1..1965";
            }
            description "Latitude";
        } // END of latitude definition.

        leaf longitude  {
            type  string {
                length "1..1965";
            }
            description "Longitude";
        } // END of longitude definition.

        leaf altitude  {
            type  string {
                length "1..1965";
            }
            description "Altitude";
        } // END of altitude definition.

    } // END of gps-gnss-fix-position-status-state definition.
    grouping gps-gnss-fix-position-status {
        description
            "Grouping for GPS GNSS fix position status";
        container gnss-fix-position-status {
            config false;
            description
                "GNSS fix position status";
            container state {
                config false;
                description
                    "Operational state data for GNSS fix position status";
                uses gps-gnss-fix-position-status-state;
            } // END of state-container definition.
        } // END of gnss-fix-position-status-container definition.
    } // END of gps-gnss-fix-position-status definition.
    grouping gps-state {
        description
            "Grouping for GPS statistics";
        container gps {
            if-feature feature-list:HAVE_PTP_HW_OFFLOAD;
            if-feature feature-list:HAVE_DUNE_OR_HAVE_MARVELL;
            config false;
            description
                "GPS statistics parameters";
            uses gps-gnss-status;
            uses gps-gnss-satellite-status;
            uses gps-gnss-survey-in-status;
            uses gps-gnss-fix-position-status;
        } // END of gps-container definition.
    } // END of gps-state definition.


}
