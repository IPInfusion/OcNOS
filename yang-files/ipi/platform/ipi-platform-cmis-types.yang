/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-cmis-types.yang
*
*/

module ipi-platform-cmis-types {

    yang-version 1.1;

    namespace   "http://www.ipinfusion.com/yang/ocnos/ipi-platform-cmis-types";

    prefix "ipi-platform-cmis-types";

    organization
        "IP Infusion Inc.";

    contact
        "Address: 3965 Freedom Circle, Suite 200, Santa Clara, CA 95054
         Phone: +1 408-4001900
         E-mail: support@ipinfusion.com
         Web: http://www.ipinfusion.com/";

    description
        "YANG version of the ipi-platform-cmis-types";


    revision "2026-02-18" {
        description "Added undefined interface, modulation and bit rate types";
        reference " 0.9.5.";
    }

    revision "2025-10-14" {
        description "Added Infinera custom media interface type";
        reference " 0.9.4.";
    }

    revision "2025-09-23" {
        description "Added WTD RTXM600-411 custom interface types";
        reference " 0.9.3.";
    }

    revision "2025-09-03" {
        description "Added Smartoptics custom 200GBASE-DR2 interface type";
        reference " 0.9.2.";
    }

    revision "2025-07-04" {
        description "Added second laser temperature monitor";
        reference " 0.9.1.";
    }

    revision "2025-06-26" {
        description "Added extra interface types and baud rates";
        reference " 0.9.0.";
    }

    revision "2025-04-28" {
        description "Revert transceiver CLI migration changes";
        reference " 0.8.1.";
    }

    revision "2025-02-22" {
        description "Added amplifier operating mode datatype";
        reference " 0.8.0.";
    }

    revision "2024-12-23" {
        description "Added media lane provision tx filter type data type";
        reference " 0.7.6.";
    }

    revision "2024-12-04" {
        description "Added measurement gating time data type";
        reference " 0.7.5.";
    }

    revision "2024-11-27" {
        description "Added C-CMIS revision 1.3 new types and updates";
        reference " 0.7.4.";
    }

    revision "2024-11-13" {
        description "Added new bit rates, new modulation format and new interface types";
        reference " 0.7.3.";
    }

    revision "2024-09-04" {
        description "Removed alarm recovery elements from the alarm type enum";
        reference " 0.7.2.";
    }

    revision "2024-09-03" {
        description "Added alarm recovery elements to the alarm type enum";
        reference " 0.7.1.";
    }

    revision "2024-06-27" {
        description "Added more Ciena custom modulation interface types and bit rates";
        reference " 0.7.0.";
    }

    revision "2024-05-21" {
        description "Added Ciena custom modulation formats, interface types and bit rates";
        reference " 0.6.7.";
    }

    revision "2024-04-03" {
        description "Added elements for CMM_CMIS_INTERFACE_TYPE_T";
        reference " 0.6.6.";
    }

    revision "2024-03-01" {
        description "Added SI amplitude codes datatype";
        reference " 0.6.5.";
    }

    revision "2024-01-23" {
        description "Added support for CMIS SI and user thresholds HW config status";
        reference " 0.6.3.";
    }

    revision "2023-10-17" {
        description "Added advertisement data types";
        reference " 0.6.2.";
    }

    revision "2023-10-16" {
        description "TIBIT Build Issue Handling";
        reference " 0.6.1.";
    }

    revision "2023-09-06" {
        description "Removed CMM_CMIS_PORT_TYPE_T datatype";
        reference " 0.6.0.";
    }

    revision "2023-06-22" {
        description "Added threshold types for CMIS global, host and media configurables threshold support";
        reference " 0.5.3.";
    }

    revision "2023-06-20" {
        description "Added CCMIS media threshold alarms";
        reference " 0.5.2.";
    }

    revision "2023-06-12" {
        description "Added CCMIS host threshold alarms";
        reference " 0.5.1.";
    }

    revision "2023-06-02" {
        description "Added CCMIS host and media discrete alarms";
        reference " 0.5.0.";
    }

    revision "2023-04-11" {
        description "Removed None threshold alarm type";
        reference " 0.4.0.";
    }

    revision "2023-02-01" {
        description "Added elements for CMM_CMIS_BIT_RATE_T";
        reference " 0.6.4.";
    }

    revision "2022-12-08" {
        description "Added basic module, host side and media side monitors data types";
        reference " 0.3.1.";
    }

    revision "2022-10-10" {
        description "Added laser grid spacing data type";
        reference " 0.3.0.";
    }

    revision "2022-08-25" {
        description "Added PRBS and loopback basic types";
        reference " 0.2.0.";
    }

    revision "2022-06-28" {
        description "Initial Version";
        reference " 0.1.0.";
    }



    typedef  cmm_cmis_yes_no_t {
        type enumeration {
            enum No {
                value 0;
                description "None";
            }
            enum Yes {
                value 1;
                description "None";
            }
        }
        description "type definition for CMM_CMIS_YES_NO_T";
    }

    typedef  cmm_cmis_module_power_class_t {
        type enumeration {
            enum Power-Class-1 {
                value 0;
                description "None";
            }
            enum Power-Class-2 {
                value 1;
                description "None";
            }
            enum Power-Class-3 {
                value 2;
                description "None";
            }
            enum Power-Class-4 {
                value 3;
                description "None";
            }
            enum Power-Class-5 {
                value 4;
                description "None";
            }
            enum Power-Class-6 {
                value 5;
                description "None";
            }
            enum Power-Class-7 {
                value 6;
                description "None";
            }
            enum Power-Class-8 {
                value 7;
                description "None";
            }
        }
        description "type definition for CMM_CMIS_MODULE_POWER_CLASS_T";
    }

    typedef  cmm_cmis_optical_detector_t {
        type enumeration {
            enum PIN {
                value 0;
                description "PIN optical detector";
            }
            enum APD {
                value 1;
                description "APD optical detector";
            }
        }
        description "type definition for CMM_CMIS_OPTICAL_DETECTOR_T";
    }

    typedef  cmm_cmis_rx_power_measur_t {
        type enumeration {
            enum OMA {
                value 0;
                description "OMA power measurement";
            }
            enum Average-Power {
                value 1;
                description "Average,Power measurement";
            }
        }
        description "type definition for CMM_CMIS_RX_POWER_MEASUR_T";
    }

    typedef  cmm_cmis_media_intf_tech_t {
        type enumeration {
            enum 850nm-VCSEL {
                value 0;
                description "None";
            }
            enum 1310nm-VCSEL {
                value 1;
                description "None";
            }
            enum 1550nm-VCSEL {
                value 2;
                description "None";
            }
            enum 1310nm-FP {
                value 3;
                description "None";
            }
            enum 1310nm-DFB {
                value 4;
                description "None";
            }
            enum 1550-nm-DFB {
                value 5;
                description "None";
            }
            enum 1310-nm-EML {
                value 6;
                description "None";
            }
            enum 1550-nm-EML {
                value 7;
                description "None";
            }
            enum Others {
                value 8;
                description "None";
            }
            enum 1490-nm-DFB {
                value 9;
                description "None";
            }
            enum Copper-Cable-Unequalized {
                value 10;
                description "None";
            }
            enum Copper-Cable-Passive-Equalized {
                value 11;
                description "None";
            }
            enum Copper-Cable-Near-End-Far-End-Limiting-Active-Equalizers {
                value 12;
                description "None";
            }
            enum Copper-Cable-Far-End-Limiting-Active-Equalizers {
                value 13;
                description "None";
            }
            enum Copper-Cable-Near-End-Limiting-Active-Equalizers {
                value 14;
                description "None";
            }
            enum Copper-Cable-Linear-Active-Equalizers {
                value 15;
                description "None";
            }
            enum C-band-Tunable-Laser {
                value 16;
                description "None";
            }
            enum L-band-Tunable-Laser {
                value 17;
                description "None";
            }
        }
        description "type definition for CMM_CMIS_MEDIA_INTF_TECH_T";
    }

    typedef  cmm_cmis_memory_model_t {
        type enumeration {
            enum Flat {
                value 0;
                description "None";
            }
            enum Paged {
                value 1;
                description "None";
            }
        }
        description "type definition for CMM_CMIS_MEMORY_MODEL_T";
    }

    typedef  cmm_cmis_mci_max_speed_t {
        type enumeration {
            enum Reserved {
                value 0;
                description "None";
            }
            enum 400-kHz {
                value 1;
                description "None";
            }
            enum 1000-kHz {
                value 2;
                description "None";
            }
        }
        description "type definition for CMM_CMIS_MCI_MAX_SPEED_T";
    }

    typedef  cmm_cmis_media_type_t {
        type enumeration {
            enum None {
                value 0;
                description "None";
            }
            enum Optical-MMF {
                value 1;
                description "None";
            }
            enum Optical-SMF {
                value 2;
                description "None";
            }
            enum Passive-Copper-Cables {
                value 3;
                description "None";
            }
            enum Active-Cables {
                value 4;
                description "None";
            }
            enum BASE-T {
                value 5;
                description "None";
            }
        }
        description "type definition for CMM_CMIS_MEDIA_TYPE_T";
    }

    typedef  cmm_cmis_module_fault_state_t {
        type enumeration {
            enum No-fault {
                value 0;
                description "None";
            }
            enum TEC-runaway {
                value 1;
                description "None";
            }
            enum Data-memory-corrupted {
                value 2;
                description "None";
            }
            enum Program-memory-corrupted {
                value 3;
                description "None";
            }
            enum Reserved {
                value 4;
                description "None";
            }
            enum Unknown {
                value 5;
                description "None";
            }
        }
        description "type definition for CMM_CMIS_MODULE_FAULT_STATE_T";
    }

    typedef  cmm_cmis_module_state_t {
        type enumeration {
            enum Reserved {
                value 0;
                description "None";
            }
            enum Low-Power {
                value 1;
                description "None";
            }
            enum Power-Up {
                value 2;
                description "None";
            }
            enum Ready {
                value 3;
                description "None";
            }
            enum Power-Down {
                value 4;
                description "None";
            }
            enum Fault {
                value 5;
                description "None";
            }
            enum Unknown {
                value 6;
                description "None";
            }
        }
        description "type definition for CMM_CMIS_MODULE_STATE_T";
    }

    typedef  cmm_cmis_datapath_states_t {
        type enumeration {
            enum Reserved {
                value 0;
                description "None";
            }
            enum Deactivated {
                value 1;
                description "None";
            }
            enum Init {
                value 2;
                description "None";
            }
            enum Deinit {
                value 3;
                description "None";
            }
            enum Activated {
                value 4;
                description "None";
            }
            enum Tx-Turn-On {
                value 5;
                description "None";
            }
            enum Tx-Turn-Off {
                value 6;
                description "None";
            }
            enum Initialized {
                value 7;
                description "None";
            }
        }
        description "type definition for CMM_CMIS_DATAPATH_STATES_T";
    }

    typedef  cmm_cmis_prbs_type_t {
        type enumeration {
            enum 31q {
                value 0;
                description "None";
            }
            enum 31 {
                value 1;
                description "None";
            }
            enum 23q {
                value 2;
                description "None";
            }
            enum 23 {
                value 3;
                description "None";
            }
            enum 15q {
                value 4;
                description "None";
            }
            enum 15 {
                value 5;
                description "None";
            }
            enum 13q {
                value 6;
                description "None";
            }
            enum 13 {
                value 7;
                description "None";
            }
            enum 9q {
                value 8;
                description "None";
            }
            enum 9 {
                value 9;
                description "None";
            }
            enum 7q {
                value 10;
                description "None";
            }
            enum 7 {
                value 11;
                description "None";
            }
            enum ssprq {
                value 12;
                description "None";
            }
        }
        description "type definition for CMM_CMIS_PRBS_TYPE_T";
    }

    typedef  cmm_cmis_prbs_location_t {
        type enumeration {
            enum pre-fec {
                value 0;
                description "None";
            }
            enum post-fec {
                value 1;
                description "None";
            }
        }
        description "type definition for CMM_CMIS_PRBS_LOCATION_T";
    }

    typedef  cmm_cmis_loopback_type_t {
        type enumeration {
            enum in {
                value 0;
                description "None";
            }
            enum out {
                value 1;
                description "None";
            }
            enum both {
                value 2;
                description "None";
            }
        }
        description "type definition for CMM_CMIS_LOOPBACK_TYPE_T";
    }

    typedef  cmm_cmis_laser_grid_spacing_t {
        type enumeration {
            enum 3p125 {
                value 0;
                description "None";
            }
            enum 6p25 {
                value 1;
                description "None";
            }
            enum 12p5 {
                value 2;
                description "None";
            }
            enum 25 {
                value 3;
                description "None";
            }
            enum 33 {
                value 4;
                description "None";
            }
            enum 50 {
                value 5;
                description "None";
            }
            enum 75 {
                value 6;
                description "None";
            }
            enum 100 {
                value 7;
                description "None";
            }
        }
        description "type definition for CMM_CMIS_LASER_GRID_SPACING_T";
    }

    typedef  cmm_cmis_gating_interval_t {
        type enumeration {
            enum 5 {
                value 0;
                description "None";
            }
            enum 10 {
                value 1;
                description "None";
            }
            enum 30 {
                value 2;
                description "None";
            }
            enum 60 {
                value 3;
                description "None";
            }
            enum 120 {
                value 4;
                description "None";
            }
            enum 300 {
                value 5;
                description "None";
            }
            enum vendor-specific {
                value 6;
                description "None";
            }
        }
        description "type definition for CMM_CMIS_GATING_INTERVAL_T";
    }

    typedef  cmm_cmis_tx_filter_type_t {
        type enumeration {
            enum root-raised-cosine {
                value 0;
                description "None";
            }
            enum raised-cosine {
                value 1;
                description "None";
            }
            enum gaussian {
                value 2;
                description "None";
            }
        }
        description "type definition for CMM_CMIS_TX_FILTER_TYPE_T";
    }

    typedef  cmm_cmis_module_monitor_id_t {
        type enumeration {
            enum Voltage {
                value 0;
                description "None";
            }
            enum Temperature {
                value 1;
                description "None";
            }
            enum TEC-Current {
                value 2;
                description "None";
            }
            enum Laser-Temperature {
                value 3;
                description "None";
            }
            enum Voltage-2 {
                value 4;
                description "None";
            }
            enum Laser-Temperature-2 {
                value 5;
                description "None";
            }
        }
        description "type definition for CMM_CMIS_MODULE_MONITOR_ID_T";
    }

    typedef  cmm_cmis_host_flag_id_t {
        type enumeration {
            enum Tx-LOS {
                value 0;
                description "None";
            }
            enum Tx-CDR-LOL {
                value 1;
                description "None";
            }
            enum Tx-Adapt-Input-Eq {
                value 2;
                description "None";
            }
            enum Rx-Output {
                value 3;
                description "None";
            }
            enum FEC-Excessive-Degrade {
                value 4;
                description "None";
            }
            enum FEC-Detected-Degrade {
                value 5;
                description "None";
            }
            enum Remote-Degrade {
                value 6;
                description "None";
            }
            enum Local-Degrade {
                value 7;
                description "None";
            }
            enum Flexe-Loss-of-Pad-Block {
                value 8;
                description "None";
            }
            enum Flexe-Loss-of-Multiframe {
                value 9;
                description "None";
            }
            enum Flexe-Loss-of-Frame {
                value 10;
                description "None";
            }
            enum Flexe-Instance-ID-Mismatch {
                value 11;
                description "None";
            }
            enum Flexe-Calendar-Mismatch {
                value 12;
                description "None";
            }
            enum Flexe-Instance-Map-Mismatch {
                value 13;
                description "None";
            }
            enum Flexe-GID-Mismatch {
                value 14;
                description "None";
            }
            enum Tx-Local-Fault {
                value 15;
                description "None";
            }
            enum Tx-Remote-Fault {
                value 16;
                description "None";
            }
            enum Tx-Loss-of-Alignment {
                value 17;
                description "None";
            }
            enum Rx-Local-Fault {
                value 18;
                description "None";
            }
            enum Rx-Remote-Fault {
                value 19;
                description "None";
            }
            enum Rx-Loss-of-Alignment {
                value 20;
                description "None";
            }
            enum Flexe-Remote-PHY-Fault {
                value 21;
                description "None";
            }
        }
        description "type definition for CMM_CMIS_HOST_FLAG_ID_T";
    }

    typedef  cmm_cmis_host_monitor_id_t {
        type enumeration {
            enum eSNR-Input {
                value 0;
                description "None";
            }
            enum PAM4-Level-Transition-Parameter-Input {
                value 1;
                description "None";
            }
            enum Pre-FEC-BER-Minimum-Sample-Input {
                value 2;
                description "None";
            }
            enum Pre-FEC-BER-Maximum-Sample-Input {
                value 3;
                description "None";
            }
            enum Pre-FEC-BER-Sample-Average-Input {
                value 4;
                description "None";
            }
            enum Pre-FEC-BER-Current-Sample-Input {
                value 5;
                description "None";
            }
            enum FERC-Minimum-Sample-Value-Input {
                value 6;
                description "None";
            }
            enum FERC-Maximum-Sample-Value-Input {
                value 7;
                description "None";
            }
            enum FERC-Sample-Average-Value-Input {
                value 8;
                description "None";
            }
            enum FERC-Current-Sample-Value-Input {
                value 9;
                description "None";
            }
            enum FERC-Total-Accumulated-Input {
                value 10;
                description "None";
            }
            enum Tx-Bits {
                value 11;
                description "None";
            }
            enum Tx-Corrected-Bits {
                value 12;
                description "None";
            }
            enum Tx-Frames {
                value 13;
                description "None";
            }
            enum Tx-Uncorrected-Frames {
                value 14;
                description "None";
            }
            enum Tx-Corrected-Frames {
                value 15;
                description "None";
            }
        }
        description "type definition for CMM_CMIS_HOST_MONITOR_ID_T";
    }

    typedef  cmm_cmis_media_monitor_id_t {
        type enumeration {
            enum Rx-Optical-Power {
                value 0;
                description "None";
            }
            enum Tx-Optical-Power {
                value 1;
                description "None";
            }
            enum Tx-Bias-Current {
                value 2;
                description "None";
            }
            enum Laser-Age {
                value 3;
                description "None";
            }
            enum Laser-Frequency-Error {
                value 4;
                description "None";
            }
            enum Laser-Temperature {
                value 5;
                description "None";
            }
            enum eSNR-Input {
                value 6;
                description "None";
            }
            enum PAM4-Level-Transition-Parameter-Input {
                value 7;
                description "None";
            }
            enum Pre-FEC-BER-Minimum-Sample-Input {
                value 8;
                description "None";
            }
            enum Pre-FEC-BER-Maximum-Sample-Input {
                value 9;
                description "None";
            }
            enum Pre-FEC-BER-Sample-Average-Input {
                value 10;
                description "None";
            }
            enum Pre-FEC-BER-Current-Sample-Input {
                value 11;
                description "None";
            }
            enum FERC-Minimum-Sample-Value-Input {
                value 12;
                description "None";
            }
            enum FERC-Maximum-Sample-Value-Input {
                value 13;
                description "None";
            }
            enum FERC-Sample-Average-Value-Input {
                value 14;
                description "None";
            }
            enum FERC-Current-Sample-Value-Input {
                value 15;
                description "None";
            }
            enum FERC-Total-Accumulated-Input {
                value 16;
                description "None";
            }
            enum Modular-Bias-X-I {
                value 17;
                description "None";
            }
            enum Modular-Bias-X-Q {
                value 18;
                description "None";
            }
            enum Modular-Bias-Y-I {
                value 19;
                description "None";
            }
            enum Modular-Bias-Y-Q {
                value 20;
                description "None";
            }
            enum Modular-Bias-X-Phase {
                value 21;
                description "None";
            }
            enum Modular-Bias-Y-Phase {
                value 22;
                description "None";
            }
            enum CD-High-Granularity-Short-Link {
                value 23;
                description "None";
            }
            enum CD-Low-Granularity-Long-Link {
                value 24;
                description "None";
            }
            enum DGD {
                value 25;
                description "None";
            }
            enum SOPMD-High-Granularity {
                value 26;
                description "None";
            }
            enum PDL {
                value 27;
                description "None";
            }
            enum OSNR {
                value 28;
                description "None";
            }
            enum eSNR {
                value 29;
                description "None";
            }
            enum CFO {
                value 30;
                description "None";
            }
            enum EVM {
                value 31;
                description "None";
            }
            enum Tx-Power {
                value 32;
                description "None";
            }
            enum Rx-Total-Power {
                value 33;
                description "None";
            }
            enum Rx-Signal-Power {
                value 34;
                description "None";
            }
            enum SOP-ROC {
                value 35;
                description "None";
            }
            enum MER {
                value 36;
                description "None";
            }
            enum Clock-Recovery-Loop {
                value 37;
                description "None";
            }
            enum SOPMD-Low-Granularity {
                value 38;
                description "None";
            }
            enum Rx-DSP-CCD-Average {
                value 39;
                description "None";
            }
            enum Rx-DSP-CCD-Minimum {
                value 40;
                description "None";
            }
            enum Rx-DSP-CCD-Maximum {
                value 41;
                description "None";
            }
            enum Rx-DGD-Average {
                value 42;
                description "None";
            }
            enum Rx-DGD-Minimum {
                value 43;
                description "None";
            }
            enum Rx-DGD-Maximum {
                value 44;
                description "None";
            }
            enum Rx-HG-SOPMD-Average {
                value 45;
                description "None";
            }
            enum Rx-HG-SOPMD-Minimum {
                value 46;
                description "None";
            }
            enum Rx-HG-SOPMD-Maximum {
                value 47;
                description "None";
            }
            enum Rx-PDL-Average {
                value 48;
                description "None";
            }
            enum Rx-PDL-Minimum {
                value 49;
                description "None";
            }
            enum Rx-PDL-Maximum {
                value 50;
                description "None";
            }
            enum Rx-OSNR-Average {
                value 51;
                description "None";
            }
            enum Rx-OSNR-Minimum {
                value 52;
                description "None";
            }
            enum Rx-OSNR-Maximum {
                value 53;
                description "None";
            }
            enum Rx-eSNR-Average {
                value 54;
                description "None";
            }
            enum Rx-eSNR-Minimum {
                value 55;
                description "None";
            }
            enum Rx-eSNR-Maximum {
                value 56;
                description "None";
            }
            enum Rx-CFO-Average {
                value 57;
                description "None";
            }
            enum Rx-CFO-Minimum {
                value 58;
                description "None";
            }
            enum Rx-CFO-Maximum {
                value 59;
                description "None";
            }
            enum Rx-EVM-Average {
                value 60;
                description "None";
            }
            enum Rx-EVM-Minimum {
                value 61;
                description "None";
            }
            enum Rx-EVM-Maximum {
                value 62;
                description "None";
            }
            enum Tx-Power-Average {
                value 63;
                description "None";
            }
            enum Tx-Power-Minimum {
                value 64;
                description "None";
            }
            enum Tx-Power-Maximum {
                value 65;
                description "None";
            }
            enum Rx-Power-Average {
                value 66;
                description "None";
            }
            enum Rx-Power-Minimum {
                value 67;
                description "None";
            }
            enum Rx-Power-Maximum {
                value 68;
                description "None";
            }
            enum Rx-Signal-Power-Average {
                value 69;
                description "None";
            }
            enum Rx-Signal-Power-Minimum {
                value 70;
                description "None";
            }
            enum Rx-Signal-Power-Maximum {
                value 71;
                description "None";
            }
            enum Rx-SOPCR-Average {
                value 72;
                description "None";
            }
            enum Rx-SOPCR-Minimum {
                value 73;
                description "None";
            }
            enum Rx-SOPCR-Maximum {
                value 74;
                description "None";
            }
            enum Rx-MER-Average {
                value 75;
                description "None";
            }
            enum Rx-MER-Minimum {
                value 76;
                description "None";
            }
            enum Rx-MER-Maximum {
                value 77;
                description "None";
            }
            enum Rx-Clock-Recovery-Loop-Average {
                value 78;
                description "None";
            }
            enum Rx-Clock-Recovery-Loop-Minimum {
                value 79;
                description "None";
            }
            enum Rx-Clock-Recovery-Loop-Maximum {
                value 80;
                description "None";
            }
            enum Rx-LG-SOPMD-Average {
                value 81;
                description "None";
            }
            enum Rx-LG-SOPMD-Minimum {
                value 82;
                description "None";
            }
            enum Rx-LG-SOPMD-Maximum {
                value 83;
                description "None";
            }
            enum Rx-Bits {
                value 84;
                description "None";
            }
            enum Rx-Corrected-Bits {
                value 85;
                description "None";
            }
            enum Rx-Frames {
                value 86;
                description "None";
            }
            enum Rx-Uncorrected-Frames {
                value 87;
                description "None";
            }
            enum Rx-SNR-Margin {
                value 88;
                description "None";
            }
            enum Rx-SNR-Margin-Average {
                value 89;
                description "None";
            }
            enum Rx-SNR-Margin-Minimum {
                value 90;
                description "None";
            }
            enum Rx-SNR-Margin-Maximum {
                value 91;
                description "None";
            }
            enum Rx-Q-Factor {
                value 92;
                description "None";
            }
            enum Rx-Q-Factor-Average {
                value 93;
                description "None";
            }
            enum Rx-Q-Factor-Minimum {
                value 94;
                description "None";
            }
            enum Rx-Q-Factor-Maximum {
                value 95;
                description "None";
            }
            enum Rx-Q-Margin {
                value 96;
                description "None";
            }
            enum Rx-Q-Margin-Average {
                value 97;
                description "None";
            }
            enum Rx-Q-Margin-Minimum {
                value 98;
                description "None";
            }
            enum Rx-Q-Margin-Maximum {
                value 99;
                description "None";
            }
        }
        description "type definition for CMM_CMIS_MEDIA_MONITOR_ID_T";
    }

    typedef  cmm_cmis_media_flag_id_t {
        type enumeration {
            enum Rx-LOS {
                value 0;
                description "None";
            }
            enum Rx-CDR-LOL {
                value 1;
                description "None";
            }
            enum Tx-Failure {
                value 2;
                description "None";
            }
            enum Tx-Output {
                value 3;
                description "None";
            }
            enum Tx-FIFO-Error {
                value 4;
                description "None";
            }
            enum Tx-Deskew-Loss-of-Lock {
                value 5;
                description "None";
            }
            enum Tx-Ref-Clock-Loss-of-Lock {
                value 6;
                description "None";
            }
            enum Tx-CMU-Loss-of-Lock {
                value 7;
                description "None";
            }
            enum Tx-Out-of-Alignment {
                value 8;
                description "None";
            }
            enum Tx-Loss-of-Alignment {
                value 9;
                description "None";
            }
            enum Rx-FIFO-Loss-of-Lock {
                value 10;
                description "None";
            }
            enum Rx-Deskew-Loss-of-Lock {
                value 11;
                description "None";
            }
            enum Rx-Out-of-Alignment {
                value 12;
                description "None";
            }
            enum Rx-Loss-of-Alignment {
                value 13;
                description "None";
            }
            enum Rx-CDC-Loss-of-Lock {
                value 14;
                description "None";
            }
            enum Rx-Demodulator-Loss-of-Lock {
                value 15;
                description "None";
            }
            enum Rx-Loss-of-Multiframe {
                value 16;
                description "None";
            }
            enum Rx-Loss-of-Frame {
                value 17;
                description "None";
            }
            enum FEC-Detected-Degrade {
                value 18;
                description "None";
            }
            enum FEC-Excessive-Degrade {
                value 19;
                description "None";
            }
            enum Remote-PHY-Fault {
                value 20;
                description "None";
            }
            enum Local-Degrade {
                value 21;
                description "None";
            }
            enum Remote-Degrade {
                value 22;
                description "None";
            }
        }
        description "type definition for CMM_CMIS_MEDIA_FLAG_ID_T";
    }

    typedef  cmm_cmis_threshold_alarm_t {
        type enumeration {
            enum High-alarm {
                value 0;
                description "None";
            }
            enum Low-alarm {
                value 1;
                description "None";
            }
            enum High-warning {
                value 2;
                description "None";
            }
            enum Low-warning {
                value 3;
                description "None";
            }
        }
        description "type definition for CMM_CMIS_THRESHOLD_ALARM_T";
    }

    typedef  cmm_ccmis_thres_id_t {
        type enumeration {
            enum rx-fdd {
                value 0;
                description "media Rx BER threshold for FDD";
            }
            enum rx-fed {
                value 1;
                description "media Rx BER threshold for FED";
            }
            enum rx-total-power {
                value 2;
                description "media threshold for Rx Total Power";
            }
            enum rx-signal-power {
                value 3;
                description "media threshold for Rx Signal Power";
            }
            enum tx-fdd {
                value 4;
                description "host BER threshold for FDD";
            }
            enum tx-fed {
                value 5;
                description "host BER threshold for FED";
            }
        }
        description "type definition for CMM_CCMIS_THRES_ID_T";
    }

    typedef  cmm_ccmis_media_lane_thres_id_t {
        type enumeration {
            enum rx-fdd {
                value 0;
                description "BER threshold for FDD";
            }
            enum rx-fed {
                value 1;
                description "BER threshold for FED";
            }
            enum rx-total-power {
                value 2;
                description "threshold for Rx Total Power";
            }
            enum rx-signal-power {
                value 3;
                description "threshold for Rx Signal Power";
            }
        }
        description "type definition for CMM_CCMIS_MEDIA_LANE_THRES_ID_T";
    }

    typedef  cmm_ccmis_host_lane_thres_id_t {
        type enumeration {
            enum tx-fdd {
                value 0;
                description "BER threshold for FDD";
            }
            enum tx-fed {
                value 1;
                description "BER threshold for FED";
            }
        }
        description "type definition for CMM_CCMIS_HOST_LANE_THRES_ID_T";
    }

    typedef  cmm_cmis_lane_assignment_t {
        type bits {
            bit Lane-1 {
                position 0;
                description "Lane 1 is assigned or not";
            }
            bit Lane-2 {
                position 1;
                description "Lane 2 is assigned or not";
            }
            bit Lane-3 {
                position 2;
                description "Lane 3 is assigned or not";
            }
            bit Lane-4 {
                position 3;
                description "Lane 4 is assigned or not";
            }
            bit Lane-5 {
                position 4;
                description "Lane 5 is assigned or not";
            }
            bit Lane-6 {
                position 5;
                description "Lane 6 is assigned or not";
            }
            bit Lane-7 {
                position 6;
                description "Lane 7 is assigned or not";
            }
            bit Lane-8 {
                position 7;
                description "Lane 8 is assigned or not";
            }
        }
        description "type definition for CMM_CMIS_LANE_ASSIGNMENT_T";
    }

    typedef  cmm_cmis_modulation_format_t {
        type enumeration {
            enum Undefined {
                value -1;
                description "Undefined modulation";
            }
            enum NRZ {
                value 0;
                description "NRZ modulation";
            }
            enum PAM4 {
                value 1;
                description "PAM4 modulation";
            }
            enum DP-QPSK {
                value 2;
                description "DP-QPSK modulation";
            }
            enum DP-8QAM {
                value 3;
                description "DP-8QAM modulation";
            }
            enum DP-16QAM {
                value 4;
                description "DP-16QAM modulation";
            }
            enum PAM5 {
                value 5;
                description "PAM5 modulation";
            }
            enum PAM16 {
                value 6;
                description "PAM16 modulation";
            }
            enum None {
                value 7;
                description "No modulation";
            }
            enum PCS {
                value 8;
                description "PCS modulation";
            }
            enum PSC-16QAM {
                value 1000;
                description "PSC-16QAM modulation";
            }
        }
        description "type definition for CMM_CMIS_MODULATION_FORMAT_T";
    }

    typedef  cmm_cmis_tx_squelch_method_t {
        type enumeration {
            enum Not-Supported {
                value 0;
                description "Tx output squelching is not supported";
            }
            enum Reduces-OMA {
                value 1;
                description "Tx output squelching reduces OMA";
            }
            enum Reduces-PAV {
                value 2;
                description "Tx output squelching reduces PAV";
            }
            enum Host-Controllable {
                value 3;
                description "Tx output squelching is host controllable";
            }
        }
        description "type definition for CMM_CMIS_TX_SQUELCH_METHOD_T";
    }

    typedef  cmm_cmis_durations_t {
        type enumeration {
            enum Less-than-1-ms {
                value 0;
                description "None";
            }
            enum 1-ms-to-5-ms {
                value 1;
                description "None";
            }
            enum 5-ms-to-10-ms {
                value 2;
                description "None";
            }
            enum 10-ms-to-50-ms {
                value 3;
                description "None";
            }
            enum 50-ms-to-100-ms {
                value 4;
                description "None";
            }
            enum 100-ms-to-500-ms {
                value 5;
                description "None";
            }
            enum 500-ms-to-1-s {
                value 6;
                description "None";
            }
            enum 1-s-to-5-s {
                value 7;
                description "None";
            }
            enum 5-s-to-10-s {
                value 8;
                description "None";
            }
            enum 10-s-to-1-min {
                value 9;
                description "None";
            }
            enum 1-min-to-5-min {
                value 10;
                description "None";
            }
            enum 5-min-to-10-min {
                value 11;
                description "None";
            }
            enum 10-min-to-50-min {
                value 12;
                description "None";
            }
            enum Greater-than-50-min {
                value 13;
                description "None";
            }
        }
        description "type definition for CMM_CMIS_DURATIONS_T";
    }

    typedef  cmm_cmis_prbs_support_type_t {
        type bits {
            bit PRBS-31Q {
                position 0;
                description "PRBS-31Q is supported or not";
            }
            bit PRBS-31 {
                position 1;
                description "PRBS-31 is supported or not";
            }
            bit PRBS-23Q {
                position 2;
                description "PRBS-23Q is supported or not";
            }
            bit PRBS-23 {
                position 3;
                description "PRBS-23 is supported or not";
            }
            bit PRBS-15Q {
                position 4;
                description "PRBS-15Q is supported or not";
            }
            bit PRBS-15 {
                position 5;
                description "PRBS-15 is supported or not";
            }
            bit PRBS-13Q {
                position 6;
                description "PRBS-13Q is supported or not";
            }
            bit PRBS-13 {
                position 7;
                description "PRBS-13 is supported or not";
            }
            bit PRBS-9Q {
                position 8;
                description "PRBS-9Q is supported or not";
            }
            bit PRBS-9 {
                position 9;
                description "PRBS-9 is supported or not";
            }
            bit PRBS-7Q {
                position 10;
                description "PRBS-7Q is supported or not";
            }
            bit PRBS-7 {
                position 11;
                description "PRBS-7 is supported or not";
            }
            bit SSPRQ {
                position 12;
                description "SSPRQ is supported or not";
            }
            bit Reserved {
                position 13;
                description "Reserved bit";
            }
            bit Custom {
                position 14;
                description "Vendor defined pattern supported or not";
            }
            bit User-Pattern {
                position 15;
                description "User programmable pattern supported or not";
            }
        }
        description "type definition for CMM_CMIS_PRBS_SUPPORT_TYPE_T";
    }

    typedef  cmm_cmis_laser_grid_support_t {
        type bits {
            bit grid-3p125GHz {
                position 0;
                description "3.125 GHz grid spacing is supported or not";
            }
            bit grid-6p25GHz {
                position 1;
                description "6.25 GHz grid spacing is supported or not";
            }
            bit grid-12p5GHz {
                position 2;
                description "12.5 GHz grid spacing is supported or not";
            }
            bit grid-25GHz {
                position 3;
                description "25 GHz grid spacing is supported or not";
            }
            bit grid-50GHz {
                position 4;
                description "50 GHz grid spacing is supported or not";
            }
            bit grid-100GHz {
                position 5;
                description "100 GHz grid spacing is supported or not";
            }
            bit grid-33GHz {
                position 6;
                description "33 GHz grid spacing is supported or not";
            }
            bit grid-75GHz {
                position 7;
                description "75 GHz grid spacing is supported or not";
            }
        }
        description "type definition for CMM_CMIS_LASER_GRID_SUPPORT_T";
    }

    typedef  cmm_cmis_vdm_pages_support_t {
        type enumeration {
            enum Group-1 {
                value 0;
                description "Only group 1 is supported";
            }
            enum Groups-1-and-2 {
                value 1;
                description "Groups 1 and 2 are supported";
            }
            enum Groups-1-to-3 {
                value 2;
                description "Groups 1 to 3 are supported";
            }
            enum Groups-1-to-4 {
                value 3;
                description "Groups 1 to 4 are supported";
            }
        }
        description "type definition for CMM_CMIS_VDM_PAGES_SUPPORT_T";
    }

    typedef  cmm_cmis_bank_per_page_support_t {
        type enumeration {
            enum Bank-0 {
                value 0;
                description "Only bank 0 is supported (8 lanes)";
            }
            enum Banks-0-and-1 {
                value 1;
                description "Banks 0 and 1 are supported (16 lanes)";
            }
            enum Banks-0-to-3 {
                value 2;
                description "Banks 0 to 3 are supported";
            }
            enum Reserved {
                value 3;
                description "Reserved value";
            }
        }
        description "type definition for CMM_CMIS_BANK_PER_PAGE_SUPPORT_T";
    }

    typedef  cmm_cmis_bit_rate_t {
        type enumeration {
            enum Undefined {
                value -1;
                description "Undefined bit rate";
            }
            enum 0.125 {
                value 0;
                description "0.125 GHz bit rate";
            }
            enum 0.2 {
                value 1;
                description "0.2 GHz bit rate";
            }
            enum 0.4 {
                value 2;
                description "0.4 GHz bit rate";
            }
            enum 0.8 {
                value 3;
                description "0.8 GHz bit rate";
            }
            enum 1.12 {
                value 4;
                description "1.12 GHz bit rate";
            }
            enum 1.25 {
                value 5;
                description "1.25 GHz bit rate";
            }
            enum 2 {
                value 6;
                description "2 GHz bit rate";
            }
            enum 2.50 {
                value 7;
                description "2.50 GHz bit rate";
            }
            enum 3.125 {
                value 8;
                description "3.125 GHz bit rate";
            }
            enum 3.20 {
                value 9;
                description "3.20 GHz bit rate";
            }
            enum 5 {
                value 10;
                description "5 GHz bit rate";
            }
            enum 9.25 {
                value 11;
                description "9.25 GHz bit rate";
            }
            enum 9.95 {
                value 12;
                description "9.95 GHz bit rate";
            }
            enum 9.953 {
                value 13;
                description "9.953 GHz bit rate";
            }
            enum 9.95328 {
                value 14;
                description "9.95328 GHz bit rate";
            }
            enum 9.95-11.18 {
                value 15;
                description "9.95-11.18 GHz bit rate";
            }
            enum 10 {
                value 16;
                description "10 GHz bit rate";
            }
            enum 10.31 {
                value 17;
                description "10.31 GHz bit rate";
            }
            enum 10.3125 {
                value 18;
                description "10.3125 GHz bit rate";
            }
            enum 12.50 {
                value 19;
                description "12.50 GHz bit rate";
            }
            enum 20.625 {
                value 20;
                description "20.625 GHz bit rate";
            }
            enum 25 {
                value 21;
                description "25 GHz bit rate";
            }
            enum 25.78 {
                value 22;
                description "25.78 GHz bit rate";
            }
            enum 25.78125 {
                value 23;
                description "25.78125 GHz bit rate";
            }
            enum 26.5625 {
                value 24;
                description "26.5625 GHz bit rate";
            }
            enum 27.9523 {
                value 25;
                description "27.9523 GHz bit rate";
            }
            enum 27.9524 {
                value 26;
                description "27.9524 GHz bit rate";
            }
            enum 27.9525 {
                value 27;
                description "27.9525 GHz bit rate";
            }
            enum 28 {
                value 28;
                description "28 GHz bit rate";
            }
            enum 30.069273 {
                value 29;
                description "30.069273 GHz bit rate";
            }
            enum 31.5697 {
                value 30;
                description "31.5697 GHz bit rate";
            }
            enum 40 {
                value 31;
                description "40 GHz bit rate";
            }
            enum 41.25 {
                value 32;
                description "41.25 GHz bit rate";
            }
            enum 50 {
                value 33;
                description "50 GHz bit rate";
            }
            enum 51.56 {
                value 34;
                description "51.56 GHz bit rate";
            }
            enum 53.125 {
                value 35;
                description "53.125 GHz bit rate";
            }
            enum 53.13 {
                value 36;
                description "53.13 GHz bit rate";
            }
            enum 59.84375 {
                value 37;
                description "59.84375 GHz bit rate";
            }
            enum 60.1385468 {
                value 38;
                description "60.1385468 GHz bit rate";
            }
            enum 63.1395 {
                value 39;
                description "63.1395 GHz bit rate";
            }
            enum 103.13 {
                value 40;
                description "103.13 GHz bit rate";
            }
            enum 106.25 {
                value 41;
                description "106.25 GHz bit rate";
            }
            enum 111.81 {
                value 42;
                description "111.81 GHz bit rate";
            }
            enum 112 {
                value 43;
                description "112 GHz bit rate";
            }
            enum 120.277094 {
                value 44;
                description "120.277094 GHz bit rate";
            }
            enum 126.28 {
                value 45;
                description "126.28 GHz bit rate";
            }
            enum 212.50 {
                value 46;
                description "212.50 GHz bit rate";
            }
            enum 224 {
                value 47;
                description "224 GHz bit rate";
            }
            enum 240.554187 {
                value 48;
                description "240.554187 GHz bit rate";
            }
            enum 252.56 {
                value 49;
                description "252.56 GHz bit rate";
            }
            enum 360.831281 {
                value 50;
                description "360.831281 GHz bit rate";
            }
            enum 425 {
                value 51;
                description "425 GHz bit rate";
            }
            enum 447 {
                value 52;
                description "447 GHz bit rate";
            }
            enum 478.75 {
                value 53;
                description "478.75 GHz bit rate";
            }
            enum 481.108374 {
                value 54;
                description "481.108374 GHz bit rate";
            }
            enum 505.12 {
                value 55;
                description "505.12 GHz bit rate";
            }
            enum 850 {
                value 56;
                description "850 GHz bit rate";
            }
            enum NA {
                value 57;
                description "Not Applicable";
            }
            enum 113.4375 {
                value 58;
                description "113.4375 GHz bit rate";
            }
            enum 118.2 {
                value 59;
                description "118.2 GHz bit rate";
            }
            enum 118.203350603 {
                value 60;
                description "118.203350603 GHz bit rate";
            }
            enum 118.749324509 {
                value 61;
                description "118.749324509 GHz bit rate";
            }
            enum 123.6364 {
                value 62;
                description "123.6364 GHz bit rate";
            }
            enum 124.101712814 {
                value 63;
                description "124.101712814 GHz bit rate";
            }
            enum 124.674930887 {
                value 64;
                description "124.674930887 GHz bit rate";
            }
            enum 131.337056226 {
                value 65;
                description "131.337056226 GHz bit rate";
            }
            enum 131.348528160 {
                value 66;
                description "131.348528160 GHz bit rate";
            }
            enum 945.626804824 {
                value 67;
                description "945.626804824 GHz bit rate";
            }
            enum 949.994596072 {
                value 68;
                description "949.994596072 GHz bit rate";
            }
            enum 992.813702512 {
                value 69;
                description "992.813702512 GHz bit rate";
            }
            enum 997.399447096 {
                value 70;
                description "997.399447096 GHz bit rate";
            }
            enum 1050.696449808 {
                value 71;
                description "1050.696449808 GHz bit rate";
            }
            enum 1050.788225280 {
                value 72;
                description "1050.788225280 GHz bit rate";
            }
            enum 1700.00 {
                value 73;
                description "1700.00 GHz bit rate";
            }
            enum 80.1847291 {
                value 74;
                description "80.1847291 GHz bit rate";
            }
            enum 505.115743 {
                value 75;
                description "505.115743 GHz bit rate";
            }
            enum 63.1394679 {
                value 76;
                description "63.1394679 GHz bit rate";
            }
            enum 378.836807 {
                value 77;
                description "378.836807 GHz bit rate";
            }
            enum 252.557871 {
                value 78;
                description "252.557871 GHz bit rate";
            }
            enum 31.569734 {
                value 79;
                description "31.569734 GHz bit rate";
            }
            enum 126.278935 {
                value 80;
                description "126.278935 GHz bit rate";
            }
            enum 472.813402412 {
                value 81;
                description "472.813402412 GHz bit rate";
            }
            enum 496.406851256 {
                value 82;
                description "496.406851256 GHz bit rate";
            }
            enum 31.5 {
                value 1000;
                description "31.5 GHz bit rate";
            }
            enum 35 {
                value 1001;
                description "35 GHz bit rate";
            }
            enum 58 {
                value 1002;
                description "58 GHz bit rate";
            }
            enum 60 {
                value 1003;
                description "60 GHz bit rate";
            }
            enum 65 {
                value 1004;
                description "65 GHz bit rate";
            }
            enum 70 {
                value 1005;
                description "70 GHz bit rate";
            }
            enum 100 {
                value 1006;
                description "100 GHz bit rate";
            }
            enum 200 {
                value 1007;
                description "200 GHz bit rate";
            }
            enum 300 {
                value 1008;
                description "300 GHz bit rate";
            }
            enum 400 {
                value 1009;
                description "400 GHz bit rate";
            }
        }
        description "type definition for CMM_CMIS_BIT_RATE_T";
    }

    typedef  cmm_cmis_interface_type_t {
        type enumeration {
            enum Undefined {
                value -1;
                description "None";
            }
            enum 1000BASE-CX {
                value 0;
                description "None";
            }
            enum XAUI {
                value 1;
                description "None";
            }
            enum XFI {
                value 2;
                description "None";
            }
            enum SFI {
                value 3;
                description "None";
            }
            enum 25GAUI-C2M {
                value 4;
                description "None";
            }
            enum XLAUI-C2M {
                value 5;
                description "None";
            }
            enum XLPPI {
                value 6;
                description "None";
            }
            enum LAUI-2-C2M {
                value 7;
                description "None";
            }
            enum 50GAUI-2-C2M {
                value 8;
                description "None";
            }
            enum 50GAUI-1-C2M {
                value 9;
                description "None";
            }
            enum CAUI-4-C2M {
                value 10;
                description "None";
            }
            enum 100GAUI-4-C2M {
                value 11;
                description "None";
            }
            enum 100GAUI-2-C2M {
                value 12;
                description "None";
            }
            enum 200GAUI-8-C2M {
                value 13;
                description "None";
            }
            enum 200GAUI-4-C2M {
                value 14;
                description "None";
            }
            enum 400GAUI-16-C2M {
                value 15;
                description "None";
            }
            enum 400GAUI-8-C2M {
                value 16;
                description "None";
            }
            enum 10GBASE-CX4 {
                value 17;
                description "None";
            }
            enum 25GBASE-CR-CA-25G-L {
                value 18;
                description "None";
            }
            enum 25GBASE-CR-or-25GBASE-CR-S-CA-25G-S {
                value 19;
                description "None";
            }
            enum 25GBASE-CR-or-25GBASE-CR-S-CA-25G-N {
                value 20;
                description "None";
            }
            enum 40GBASE-CR4 {
                value 21;
                description "None";
            }
            enum 50GBASE-CR {
                value 22;
                description "None";
            }
            enum 100GBASE-CR10 {
                value 23;
                description "None";
            }
            enum 100GBASE-CR4 {
                value 24;
                description "None";
            }
            enum 100GBASE-CR2 {
                value 25;
                description "None";
            }
            enum 200GBASE-CR4 {
                value 26;
                description "None";
            }
            enum 400G-CR8 {
                value 27;
                description "None";
            }
            enum CAUI-4-C2M-without-FEC {
                value 28;
                description "None";
            }
            enum CAUI-4-C2M-with-RS-FEC {
                value 29;
                description "None";
            }
            enum 50GBASE-CR2-with-RS-FEC {
                value 30;
                description "None";
            }
            enum 50GBASE-CR2-with-BASE-R-Fire-code-FEC {
                value 31;
                description "None";
            }
            enum 50GBASE-CR2-with-no-FEC {
                value 32;
                description "None";
            }
            enum 100GBASE-CR1 {
                value 33;
                description "None";
            }
            enum 200GBASE-CR2 {
                value 34;
                description "None";
            }
            enum 400GBASE-CR4 {
                value 35;
                description "None";
            }
            enum 800GBASE-CR8 {
                value 36;
                description "None";
            }
            enum 100GAUI-1-S-C2M {
                value 37;
                description "None";
            }
            enum 100GAUI-1-L-C2M {
                value 38;
                description "None";
            }
            enum 200GAUI-2-S-C2M {
                value 39;
                description "None";
            }
            enum 200GAUI-2-L-C2M {
                value 40;
                description "None";
            }
            enum 400GAUI-4-S-C2M {
                value 41;
                description "None";
            }
            enum 400GAUI-4-L-C2M {
                value 42;
                description "None";
            }
            enum 800GAUI-8-S-C2M {
                value 43;
                description "None";
            }
            enum 800GAUI-8-L-C2M {
                value 44;
                description "None";
            }
            enum 10GBASE-SW {
                value 45;
                description "None";
            }
            enum 10GBASE-SR {
                value 46;
                description "None";
            }
            enum 25GBASE-SR {
                value 47;
                description "None";
            }
            enum 40GBASE-SR4 {
                value 48;
                description "None";
            }
            enum 40GE-SWDM4-MSA-Spec {
                value 49;
                description "None";
            }
            enum 40GE-BiDi {
                value 50;
                description "None";
            }
            enum 50GBASE-SR {
                value 51;
                description "None";
            }
            enum 100GBASE-SR10 {
                value 52;
                description "None";
            }
            enum 100GBASE-SR4 {
                value 53;
                description "None";
            }
            enum 100GE-SWDM4-MSA-Spec {
                value 54;
                description "None";
            }
            enum 100GE-BiDi {
                value 55;
                description "None";
            }
            enum 100GBASE-SR2 {
                value 56;
                description "None";
            }
            enum 100GBASE-SR {
                value 57;
                description "None";
            }
            enum 200GBASE-SR4 {
                value 58;
                description "None";
            }
            enum 400GBASE-SR16 {
                value 59;
                description "None";
            }
            enum 400GBASE-SR8 {
                value 60;
                description "None";
            }
            enum 400GBASE-SR4 {
                value 61;
                description "None";
            }
            enum 800GBASE-SR8 {
                value 62;
                description "None";
            }
            enum 400GBASE-SR4.2--400GE-BiDi {
                value 63;
                description "None";
            }
            enum 200GBASE-SR2 {
                value 64;
                description "None";
            }
            enum 100GBASE-VR {
                value 65;
                description "None";
            }
            enum 200GBASE-VR2 {
                value 66;
                description "None";
            }
            enum 400GBASE-VR4 {
                value 67;
                description "None";
            }
            enum 10GBASE-LW {
                value 68;
                description "None";
            }
            enum 10GBASE-EW {
                value 69;
                description "None";
            }
            enum 10G-ZW {
                value 70;
                description "None";
            }
            enum 10GBASE-LR {
                value 71;
                description "None";
            }
            enum 10GBASE-ER {
                value 72;
                description "None";
            }
            enum 10G-ZR {
                value 73;
                description "None";
            }
            enum 25GBASE-LR {
                value 74;
                description "None";
            }
            enum 25GBASE-ER {
                value 75;
                description "None";
            }
            enum 40GBASE-LR4 {
                value 76;
                description "None";
            }
            enum 40GBASE-FR {
                value 77;
                description "None";
            }
            enum 50GBASE-FR {
                value 78;
                description "None";
            }
            enum 50GBASE-LR {
                value 79;
                description "None";
            }
            enum 100GBASE-LR4 {
                value 80;
                description "None";
            }
            enum 100GBASE-ER4 {
                value 81;
                description "None";
            }
            enum 100G-PSM4-MSA-Spec {
                value 82;
                description "None";
            }
            enum 100G-CWDM4-MSA-Spec {
                value 83;
                description "None";
            }
            enum 100G-4WDM-10-MSA-Spec {
                value 84;
                description "None";
            }
            enum 100G-4WDM-20-MSA-Spec {
                value 85;
                description "None";
            }
            enum 100G-4WDM-40-MSA-Spec {
                value 86;
                description "None";
            }
            enum 100GBASE-DR {
                value 87;
                description "None";
            }
            enum 100G-FR-MSA-Spec--100GBASE-FR1 {
                value 88;
                description "None";
            }
            enum 100G-LR-MSA-Spec--100GBASE-LR1 {
                value 89;
                description "None";
            }
            enum 200GBASE-DR4 {
                value 90;
                description "None";
            }
            enum 200GBASE-FR4 {
                value 91;
                description "None";
            }
            enum 200GBASE-LR4 {
                value 92;
                description "None";
            }
            enum 400GBASE-FR8 {
                value 93;
                description "None";
            }
            enum 400GBASE-LR8 {
                value 94;
                description "None";
            }
            enum 400GBASE-DR4 {
                value 95;
                description "None";
            }
            enum 400G-FR4-MSA-Spec--400GBASE-FR4 {
                value 96;
                description "None";
            }
            enum 400G-LR4-10-MSA-Spec {
                value 97;
                description "None";
            }
            enum 100G-CWDM4-OCP {
                value 98;
                description "None";
            }
            enum 400ZR-DWDM-Amplified {
                value 99;
                description "None";
            }
            enum 400ZR-Single-Wavelength-Unamplified {
                value 100;
                description "None";
            }
            enum 50GBASE-ER {
                value 101;
                description "None";
            }
            enum 200GBASE-ER4 {
                value 102;
                description "None";
            }
            enum 400GBASE-ER8 {
                value 103;
                description "None";
            }
            enum 400GBASE-LR4-6 {
                value 104;
                description "None";
            }
            enum 100GBASE-ZR {
                value 105;
                description "None";
            }
            enum ZR400-OFEC-16QAM {
                value 106;
                description "None";
            }
            enum ZR300-OFEC-8QAM {
                value 107;
                description "None";
            }
            enum ZR200-OFEC-QPSK {
                value 108;
                description "None";
            }
            enum ZR100-OFEC-QPSK {
                value 109;
                description "None";
            }
            enum 100G-LR1-20-MSA-Spec {
                value 110;
                description "None";
            }
            enum 100G-ER1-30-MSA-Spec {
                value 111;
                description "None";
            }
            enum 100G-ER1-40-MSA-Spec {
                value 112;
                description "None";
            }
            enum 400GBASE-ZR {
                value 113;
                description "None";
            }
            enum 10GBASE-BR {
                value 114;
                description "None";
            }
            enum 25GBASE-BR {
                value 115;
                description "None";
            }
            enum 50GBASE-BR {
                value 116;
                description "None";
            }
            enum 400ZRP-DWDM-Amplified-450Km {
                value 117;
                description "None";
            }
            enum 100ZRP-DWDM-Amplified-600Km {
                value 118;
                description "None";
            }
            enum 100ZRP-DWDM-Amplified-1000Km {
                value 119;
                description "None";
            }
            enum 100ZRP-DWDM-Amplified-2000Km {
                value 120;
                description "None";
            }
            enum 400ZRP-DWDM-Amplified-120Km {
                value 121;
                description "None";
            }
            enum 400ZRP-DWDM-Amplified-450Km--Enhanced-Constellation {
                value 122;
                description "None";
            }
            enum 100ZRP-DWDM-Amplified-600Km--Enhanced-Constellation {
                value 123;
                description "None";
            }
            enum ZR400-OFEC-16QAM--Enhanced-Performance {
                value 124;
                description "None";
            }
            enum ZR200-OFEC-16QAM {
                value 125;
                description "None";
            }
            enum Copper-Cable {
                value 126;
                description "None";
            }
            enum Passive-Loopback-Module {
                value 127;
                description "None";
            }
            enum Active-Cable-Assembly-with-BER-less-than-10e-12 {
                value 128;
                description "None";
            }
            enum Active-Cable-Assembly-with-BER-less-than-5x10e-5 {
                value 129;
                description "None";
            }
            enum Active-Cable-Assembly-with-BER-less-than-2.6x10e-4 {
                value 130;
                description "None";
            }
            enum Active-Cable-Assembly-with-BER-less-than-10e-6 {
                value 131;
                description "None";
            }
            enum Active-Loopback-Module {
                value 132;
                description "None";
            }
            enum 1000BASE-T {
                value 133;
                description "None";
            }
            enum 2.5GBASE-T {
                value 134;
                description "None";
            }
            enum 5GBASE-T {
                value 135;
                description "None";
            }
            enum 10GBASE-T {
                value 136;
                description "None";
            }
            enum 25GBASE-T {
                value 137;
                description "None";
            }
            enum 40GBASE-T {
                value 138;
                description "None";
            }
            enum 50GBASE-T {
                value 139;
                description "None";
            }
            enum 4I1-9D1F-G.959.1 {
                value 140;
                description "None";
            }
            enum 4L1-9C1F-G.959.1 {
                value 141;
                description "None";
            }
            enum 4L1-9D1F-G.959.1 {
                value 142;
                description "None";
            }
            enum C4S1-9D1F-G.695 {
                value 143;
                description "None";
            }
            enum C4S1-4D1F-G.695 {
                value 144;
                description "None";
            }
            enum 4I1-4D1F-G.959.1 {
                value 145;
                description "None";
            }
            enum 8R1-4D1F-G.959.1 {
                value 146;
                description "None";
            }
            enum 8I1-4D1F-G.959.1 {
                value 147;
                description "None";
            }
            enum FOIC1.4-DO-G.709.3Y.1331.3 {
                value 148;
                description "None";
            }
            enum FOIC2.8-DO-G.709.3Y.1331.3 {
                value 149;
                description "None";
            }
            enum FOIC4.8-DO-G.709.3Y.1331.3 {
                value 150;
                description "None";
            }
            enum FOIC2.4-DO-G.709.3Y.1331.3 {
                value 151;
                description "None";
            }
            enum OTL4.4-ITU-T-G.709Y.1331-G.Sup58 {
                value 152;
                description "None";
            }
            enum OTL4.2 {
                value 153;
                description "None";
            }
            enum FOIC1.4-ITU-T-G.709.1-Y.1331-G.Sup58 {
                value 154;
                description "None";
            }
            enum FOIC1.2-ITU-T-G.709.1-Y.1331-G.Sup58 {
                value 155;
                description "None";
            }
            enum 800GBASE-CR4 {
                value 156;
                description "None";
            }
            enum 800GAUI-4 {
                value 157;
                description "None";
            }
            enum 800GBASE-VR8 {
                value 158;
                description "None";
            }
            enum 800G-VR4.2 {
                value 159;
                description "None";
            }
            enum 800G-SR4.2 {
                value 160;
                description "None";
            }
            enum 800GBASE-DR8 {
                value 161;
                description "None";
            }
            enum 800GBASE-DR8-2 {
                value 162;
                description "None";
            }
            enum 800GBASE-DR4 {
                value 163;
                description "None";
            }
            enum 800GBASE-DR4-2 {
                value 164;
                description "None";
            }
            enum 800GBASE-FR4-500 {
                value 165;
                description "None";
            }
            enum 800GBASE-FR4 {
                value 166;
                description "None";
            }
            enum 800GBASE-LR4 {
                value 167;
                description "None";
            }
            enum 800GBASE-LR1 {
                value 168;
                description "None";
            }
            enum 800GBASE-ER1-20 {
                value 169;
                description "None";
            }
            enum 800GBASE-ER1 {
                value 170;
                description "None";
            }
            enum FLEXO-8e-DO-16QAM--FOICe8.8-DO {
                value 171;
                description "None";
            }
            enum FLEXO-8-DO-16QAM--FOIC8.8-DO {
                value 172;
                description "None";
            }
            enum FLEXO-8e-DPO-16QAM--FOICe8.8-DPO {
                value 173;
                description "None";
            }
            enum FLEXO-8-DPO-16QAM--FOIC8.8-DPO {
                value 174;
                description "None";
            }
            enum FLEXO-6e-DPO-16QAM--FOIC6e-DPO {
                value 175;
                description "None";
            }
            enum FLEXO-6-DPO-16QAM--FOIC.6-DPO {
                value 176;
                description "None";
            }
            enum 800ZR-A--150GHz-DWDM--Tx-Output-Range-A {
                value 177;
                description "None";
            }
            enum 800ZR-B--150GHz-DWDM--Tx-Output-Range-B {
                value 178;
                description "None";
            }
            enum 800ZR-C--150GHz-DWDM--Tx-Output-Range-C {
                value 179;
                description "None";
            }
            enum 200GBASE-CR1 {
                value 180;
                description "None";
            }
            enum 400GBASE-CR2 {
                value 181;
                description "None";
            }
            enum 1.6TAUI-16-S-C2M {
                value 182;
                description "None";
            }
            enum 1.6TAUI-16-L-C2M {
                value 183;
                description "None";
            }
            enum 1.6TBASE-CR8 {
                value 184;
                description "None";
            }
            enum 200GAUI-1 {
                value 185;
                description "None";
            }
            enum 400GAUI-2 {
                value 186;
                description "None";
            }
            enum 1.6TAUI-8 {
                value 187;
                description "None";
            }
            enum 1.6T-VR8.2 {
                value 188;
                description "None";
            }
            enum 1.6T-SR8.2 {
                value 189;
                description "None";
            }
            enum ZR400-OFEC-16QAM-HA {
                value 190;
                description "None";
            }
            enum ZR400-OFEC-16QAM-HB {
                value 191;
                description "None";
            }
            enum ZR400-OFEC-8QAM-HA {
                value 192;
                description "None";
            }
            enum 400GBASE-DR4-2 {
                value 193;
                description "None";
            }
            enum ZR400-OFEC-8QAM-HB {
                value 194;
                description "None";
            }
            enum ZR300-OFEC-8QAM-HA {
                value 195;
                description "None";
            }
            enum ZR300-OFEC-8QAM-HB {
                value 196;
                description "None";
            }
            enum ZR200-OFEC-QPSK-HA {
                value 197;
                description "None";
            }
            enum ZR200-OFEC-QPSK-HB {
                value 198;
                description "None";
            }
            enum ZR100-OFEC-QPSK-HA {
                value 199;
                description "None";
            }
            enum ZR100-OFEC-QPSK-HB {
                value 200;
                description "None";
            }
            enum FLEXO-4-DO-16QAM--FOIC4.8-DO {
                value 201;
                description "None";
            }
            enum FLEXO-3-DO-8QAM--FOIC3.6-DO {
                value 202;
                description "None";
            }
            enum FLEXO-2-DO-QPSK--FOIC2.4-DO {
                value 203;
                description "None";
            }
            enum FLEXO-2-DO-16QAM--FOIC2.8-DO {
                value 204;
                description "None";
            }
            enum FLEXO-1-DO-QPSK--FOIC1.4-DO {
                value 205;
                description "None";
            }
            enum FLEXO-4e-DO-QPSK--FOIC4e.4-DO {
                value 206;
                description "None";
            }
            enum FLEXO-4-DO-QPSK--FOIC4.4-DO {
                value 207;
                description "None";
            }
            enum 400G-ER4-30 {
                value 208;
                description "None";
            }
            enum FOIC1.1-RS--G.709.1-Y.1331.58 {
                value 209;
                description "None";
            }
            enum 200GBASE-DR1 {
                value 210;
                description "None";
            }
            enum 200GBASE-DR1-2 {
                value 211;
                description "None";
            }
            enum 400GBASE-DR2 {
                value 212;
                description "None";
            }
            enum 400GBASE-DR2-2 {
                value 213;
                description "None";
            }
            enum 1.6TBASE-DR8 {
                value 214;
                description "None";
            }
            enum 1.6TBASE-DR8-2 {
                value 215;
                description "None";
            }
            enum 100G-OFEC-31.5 {
                value 1000;
                description "None";
            }
            enum 200G-OFEC-31.5 {
                value 1001;
                description "None";
            }
            enum OTN-MAX-200G-SFEC-35 {
                value 1002;
                description "None";
            }
            enum OTN-MAX-200G-SFEC-58 {
                value 1003;
                description "None";
            }
            enum PKT-MAX-200G-SFEC-60 {
                value 1004;
                description "None";
            }
            enum PKT-MAX-300G-SFEC-65 {
                value 1005;
                description "None";
            }
            enum OTN-MAX-300G-SFEC-70 {
                value 1006;
                description "None";
            }
            enum PKT-MAX-400-SFEC-65 {
                value 1007;
                description "None";
            }
            enum PKT-MAX-400-SFEC-70 {
                value 1008;
                description "None";
            }
            enum OTN-MAX-400-SFEC-70 {
                value 1009;
                description "None";
            }
            enum 200GBASE-DR2 {
                value 2000;
                description "None";
            }
            enum 800GBASE-FR8 {
                value 3000;
                description "None";
            }
            enum 200GBASE-FR2 {
                value 3001;
                description "None";
            }
            enum 100GBASE-FR1 {
                value 3002;
                description "None";
            }
            enum 100G-Client-Only {
                value 4000;
                description "None";
            }
        }
        description "type definition for CMM_CMIS_INTERFACE_TYPE_T";
    }

    typedef  cmm_ccmis_thres_state_host_id_t {
        type enumeration {
            enum tx-fdd-active {
                value 0;
                description "Tx FDD active threshold";
            }
            enum tx-fdd-clear {
                value 1;
                description "Tx FDD clear threshold";
            }
            enum tx-fed-active {
                value 2;
                description "Tx FED active threshold";
            }
            enum tx-fed-clear {
                value 3;
                description "Tx FED clear threshold";
            }
        }
        description "type definition for CMM_CCMIS_THRES_STATE_HOST_ID_T";
    }

    typedef  cmm_ccmis_thres_state_media_id_t {
        type enumeration {
            enum rx-fdd-active {
                value 0;
                description "Rx FDD active threshold";
            }
            enum rx-fdd-clear {
                value 1;
                description "Rx FDD clear threshold";
            }
            enum rx-fed-active {
                value 2;
                description "Rx FED active threshold";
            }
            enum rx-fed-clear {
                value 3;
                description "Rx FED clear threshold";
            }
            enum rx-total-power-high-alarm {
                value 4;
                description "Rx total power high alarm threshold";
            }
            enum rx-total-power-high-warning {
                value 5;
                description "Rx total power high warning threshold";
            }
            enum rx-total-power-low-warning {
                value 6;
                description "Rx total power low warning threshold";
            }
            enum rx-total-power-low-alarm {
                value 7;
                description "Rx total power low alarm threshold";
            }
            enum rx-signal-power-high-alarm {
                value 8;
                description "Rx signal power high alarm threshold";
            }
            enum rx-signal-power-high-warning {
                value 9;
                description "Rx signal power high warning threshold";
            }
            enum rx-signal-power-low-warning {
                value 10;
                description "Rx signal power low warning threshold";
            }
            enum rx-signal-power-low-alarm {
                value 11;
                description "Rx signal power low alarm threshold";
            }
        }
        description "type definition for CMM_CCMIS_THRES_STATE_MEDIA_ID_T";
    }

    typedef  cmm_cmis_si_amp_codes_t {
        type bits {
            bit code-0 {
                position 0;
                description "Code 0 support";
            }
            bit code-1 {
                position 1;
                description "Code 1 support";
            }
            bit code-2 {
                position 2;
                description "Code 2 support";
            }
            bit code-3 {
                position 3;
                description "Code 3 support";
            }
        }
        description "type definition for CMM_CMIS_SI_AMP_CODES_T";
    }

    typedef  cmm_ccmis_rx_los_type_t {
        type enumeration {
            enum Rx-LoS-Responds-to-Rx-Total-Power {
                value 1;
                description "None";
            }
            enum Rx-LoS-Responds-to-Rx-Signal-Power {
                value 2;
                description "None";
            }
            enum Rx-LoS-Responds-to-Rx-DSP-Frame-LoL {
                value 3;
                description "None";
            }
            enum Rx-Total-Power-Detection-and-Rx-DSP-Frame-LoL-Hybrid {
                value 4;
                description "None";
            }
            enum Rx-Signal-Power-Detection-and-Rx-DSP-Frame-LoL-Hybrid {
                value 5;
                description "None";
            }
        }
        description "type definition for CMM_CCMIS_RX_LOS_TYPE_T";
    }

    typedef  amplifier_operating_mode_t {
        type enumeration {
            enum agc {
                value 1;
                description "Automatic Gain Control";
            }
            enum apc {
                value 2;
                description "Automatic Power Control";
            }
        }
        description "type definition for AMPLIFIER_OPERATING_MODE_T";
    }

}
