/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-smart-sfp.yang
*
*/

submodule ipi-platform-smart-sfp {

    yang-version 1.1;

    belongs-to  ipi-platform { prefix ipi-platform; }

    import feature-list {
        prefix feature-list;
        revision-date 2026-09-15;
    }

    import ipi-platform-transceiver-types {
        prefix ipi-platform-transceiver-types;
        revision-date 2025-12-30;
    }

    import ipi-platform-sff8024-types {
        prefix ipi-platform-sff8024-types;
        revision-date 2026-01-06;
    }

    organization
        "IP Infusion Inc.";

    contact
        "Address: 3965 Freedom Circle, Suite 200, Santa Clara, CA 95054
         Phone: +1 408-4001900
         E-mail: support@ipinfusion.com
         Web: http://www.ipinfusion.com/";

    description
        "This module defines a schema for Smart SFP transceivers in platform
                datamodel";


    revision "2025-07-31" {
        description "Use CMM_SFF8024_CONNECTOR_TYPE_T instead of DDM_CMM_TRANS_CONNECTOR_TYPE_T";
        reference " 0.2.0.";
    }

    revision "2023-04-14" {
        description "Fix protocol status datatype";
        reference " 0.1.1.";
    }

    revision "2023-03-28" {
        description "Initial version";
        reference " 0.1.0.";
    }

    grouping ipi-platform-remote-sfp-state {
        description
            "ipi-platform-remote-sfp-state";
        leaf port  {
            type  uint8 {
                 range "1..128"  {
                    description "1..128: Supported range 1 - 128";
                 }
            }
            description "A unique value for each panel port within the unit";
        } // END of port definition.

    } // END of ipi-platform-remote-sfp-state definition.
    grouping ipi-platform-remote-sfp-eeprom-state {
        description
            "ipi-platform-remote-sfp-eeprom-state";
        leaf identifier  {
            type  ipi-platform-transceiver-types:ddm_cmm_trans_identifier_t;
            description "The Type of transceiver present eg:SFP/SFP+/SFP28/QSFP/QSFP+/QSFP28.";
        } // END of identifier definition.

        leaf sfp-extended-identifier  {
            type  ipi-platform-transceiver-types:ddm_cmm_trans_sfp_extended_identifier_t;
            description "Extended identifier of SFP transceiver for additional information.";
        } // END of sfp-extended-identifier definition.

        leaf connector-type  {
            type  ipi-platform-sff8024-types:cmm_sff8024_connector_type_t;
            description "Connector type for the transceiver.";
        } // END of connector-type definition.

        leaf ethernet-compliance-code  {
            type  ipi-platform-transceiver-types:ddm_cmm_trans_eth_compliance_t;
            description "Values of Ethernet Compliance codes.";
        } // END of ethernet-compliance-code definition.

        leaf extended-ethernet-compliance-code  {
            type  ipi-platform-transceiver-types:ddm_cmm_trans_ext_eth_compliance_t;
            description "Bitmap of Extended Ethernet Compliance codes. null indicates
                        unavailable.";
        } // END of extended-ethernet-compliance-code definition.

        leaf sonet-compliance-code  {
            type  ipi-platform-transceiver-types:ddm_cmm_trans_sonet_compliance_t;
            description "Sonet Compliance codes of transceiver. null indicates unavailable.";
        } // END of sonet-compliance-code definition.

        leaf fiber-channel-link-length  {
            type  ipi-platform-transceiver-types:ddm_cmm_trans_fiber_channel_linklen_t;
            description "Fiber Channel Link Length.";
        } // END of fiber-channel-link-length definition.

        leaf fiber-channel-transmission-technology  {
            type  ipi-platform-transceiver-types:ddm_cmm_trans_fiber_channel_transmittech_t;
            description "Fiber Channel Transmitter Technology.";
        } // END of fiber-channel-transmission-technology definition.

        leaf fiber-channel-transmission-media  {
            type  ipi-platform-transceiver-types:ddm_cmm_trans_fiber_channel_transmitmedia_t;
            description "Fiber Channel Transmission Media.";
        } // END of fiber-channel-transmission-media definition.

        leaf fiber-channel-sfp-speed  {
            type  ipi-platform-transceiver-types:ddm_cmm_trans_fiber_channel_speed_t;
            description "SFP Fiber Channel Speed.";
        } // END of fiber-channel-sfp-speed definition.

        leaf sfp-infiniband-compliance-code  {
            type  ipi-platform-transceiver-types:ddm_cmm_trans_sfp_infiniband_compliance_t;
            description "SFP Infiniband Compliance.";
        } // END of sfp-infiniband-compliance-code definition.

        leaf sfp-escon-compliance-code  {
            type  ipi-platform-transceiver-types:ddm_cmm_trans_sfp_escon_compliance_t;
            description "FP Enterprise Systems Connection compliance.";
        } // END of sfp-escon-compliance-code definition.

        leaf sfp-plus-cable-technology  {
            type  ipi-platform-transceiver-types:ddm_cmm_trans_sfp_plus_cable_tech_t;
            description "SFP+ Cable Technology.";
        } // END of sfp-plus-cable-technology definition.

        leaf serial-encoding-algorithm  {
            type  ipi-platform-transceiver-types:ddm_cmm_trans_encoding_t;
            description "Code for SFP/QSFP high speed serial encoding algorithm";
        } // END of serial-encoding-algorithm definition.

        leaf link-length-kilometer  {
            type  int32;
            units "Km";
            description "Link length supported for single mode fiber, units of km.";
        } // END of link-length-kilometer definition.

        leaf link-length-meter  {
            type  int32;
            units "100m";
            description "Link length supported for single mode fiber, units of 100 m.";
        } // END of link-length-meter definition.

        leaf om1-link-length  {
            type  int32;
            units "10m";
            description "Link length supported for 62.5 um OM1 fiber, units of 10 m.";
        } // END of om1-link-length definition.

        leaf om2-link-length  {
            type  int32;
            units "10m";
            description "Link length supported for 50 um OM2 fiber, units of 10 m.";
        } // END of om2-link-length definition.

        leaf om3-link-length  {
            type  int32;
            units "10m";
            description "Link length supported for 50 um OM3 fiber, units of 10 m.";
        } // END of om3-link-length definition.

        leaf om4-link-length  {
            type  int32;
            units "10m";
            description "Link length supported for 50 um OM4 fiber, units of 10 m.";
        } // END of om4-link-length definition.

        leaf vendor-name  {
            type  string {
                length "0..1965";
            }
            description "Transceiver vendor name.";
        } // END of vendor-name definition.

        leaf vendor-ieee-id  {
            type  string {
                length "0..1965";
            }
            description "SFP vendor IEEE company ID.";
        } // END of vendor-ieee-id definition.

        leaf vendor-part-number  {
            type  string {
                length "0..1965";
            }
            description "Part number provided by transceiver vendor.";
        } // END of vendor-part-number definition.

        leaf vendor-revision-number  {
            type  string {
                length "0..1965";
            }
            description "Revision level for part number provided by vendor.";
        } // END of vendor-revision-number definition.

        leaf check-code  {
            type  string {
                length "0..1965";
            }
            description "Check code for Base ID Fields.";
        } // END of check-code definition.

        leaf extended-check-code  {
            type  string {
                length "0..1965";
            }
            description "Check code for the Extended ID Fields.";
        } // END of extended-check-code definition.

        leaf nominal-signalling-rate  {
            type  int32;
            units "100MBd";
            description "Nominal signalling rate, units of 100MBd.";
        } // END of nominal-signalling-rate definition.

        leaf maximum-signalling-rate  {
            type  int32;
            description "Upper bit rate margin, units of 1% above the Nominal Bit Rate.";
        } // END of maximum-signalling-rate definition.

        leaf minimum-signalling-rate  {
            type  int32;
            description "Lower bit rate margin, units of 1% below the Nominal Bit Rate.";
        } // END of minimum-signalling-rate definition.

        leaf vendor-serial-number  {
            type  string {
                length "0..1965";
            }
            description "Serial number provided by vendor.";
        } // END of vendor-serial-number definition.

        leaf vendor-manufacturing-date  {
            type  string {
                length "0..1965";
            }
            description "Vendor's manufacturing date code.";
        } // END of vendor-manufacturing-date definition.

        leaf ddm-type  {
            type  ipi-platform-transceiver-types:ddm_cmm_trans_ddm_support_t;
            description "Indicates which type of diagnostic monitoring is implemented.";
        } // END of ddm-type definition.

        leaf maximum-case-temperature  {
            type  decimal64 {
                 fraction-digits 2;            }
            units "C";
            description "Maximum case temperature in Celsius.";
        } // END of maximum-case-temperature definition.

        leaf sfp-options-implemented  {
            type  ipi-platform-transceiver-types:ddm_cmm_trans_sfp_options_implemented_t;
            description "Transceiver Options Implemented for SFP Transceiver.";
        } // END of sfp-options-implemented definition.

    } // END of ipi-platform-remote-sfp-eeprom-state definition.
    grouping ipi-platform-remote-sfp-eeprom-top {
        description
            "ipi-platform-remote-sfp-eeprom-top";
        container state {
            config false;
            description
                "State data for Remote SFP EEPROM";
            uses ipi-platform-remote-sfp-eeprom-state;
        } // END of state-container definition.
    } // END of ipi-platform-remote-sfp-eeprom-top definition.
    grouping ipi-platform-remote-sfp-monitor-state {
        description
            "ipi-platform-remote-sfp-monitor-state";
        leaf id  {
            type  ipi-platform-transceiver-types:cmm_smart_sfp_ddm_monitor_id_t;
            description "Module monitor ID";
        } // END of id definition.

        leaf description  {
            type  string {
                length "1..1965";
            }
            description "Module monitor description";
        } // END of description definition.

        leaf value  {
            type  decimal64 {
                 fraction-digits 3;            }
            description "Module monitor value";
        } // END of value definition.

        leaf high-alarm  {
            type  decimal64 {
                 fraction-digits 3;            }
            description "Module monitor high alarm value";
        } // END of high-alarm definition.

        leaf high-warning  {
            type  decimal64 {
                 fraction-digits 3;            }
            description "Module monitor high warning value";
        } // END of high-warning definition.

        leaf low-warning  {
            type  decimal64 {
                 fraction-digits 3;            }
            description "Module monitor low warning value";
        } // END of low-warning definition.

        leaf low-alarm  {
            type  decimal64 {
                 fraction-digits 3;            }
            description "Module monitor low alarm value";
        } // END of low-alarm definition.

    } // END of ipi-platform-remote-sfp-monitor-state definition.
    grouping ipi-platform-remote-sfp-monitors-top {
        description
            "ipi-platform-remote-sfp-monitors-top";

        list monitor {
            key "id";
            config false;
            description
                "List of Remote SFP DMM monitors";
            leaf id  {
                type  leafref {
                    path  "../state/id";
                }
                description "DDM monitor ID";
            } // END of id definition.

            container state {
                config false;
                description
                    "Remote SFP DDM monitor state";
                uses ipi-platform-remote-sfp-monitor-state;
            } // END of state-container definition.
        } // End of monitor-list
    } // END of ipi-platform-remote-sfp-monitors-top definition.
    grouping ipi-platform-remote-sfp-monitor-alarm-state {
        description
            "ipi-platform-remote-sfp-monitor-alarm-state";
        leaf alarm-id  {
            type  ipi-platform-transceiver-types:cmm_smart_sfp_ddm_monitor_id_t;
            description "Threshold alarm ID";
        } // END of alarm-id definition.

        leaf alarm-type  {
            type  ipi-platform-transceiver-types:cmm_ddm_threshold_alarm_t;
            description "Threshold alarm type";
        } // END of alarm-type definition.

        leaf current-value  {
            type  decimal64 {
                 fraction-digits 3;            }
            description "Current monitor value";
        } // END of current-value definition.

        leaf threshold-minimum  {
            type  decimal64 {
                 fraction-digits 3;            }
            description "Threshold minimum value";
        } // END of threshold-minimum definition.

        leaf threshold-maximum  {
            type  decimal64 {
                 fraction-digits 3;            }
            description "Threshold maximum value";
        } // END of threshold-maximum definition.

    } // END of ipi-platform-remote-sfp-monitor-alarm-state definition.
    grouping ipi-platform-remote-sfp-monitor-alarm-top {
        description
            "ipi-platform-remote-sfp-monitor-alarm-top";
        container state {
            config false;
            description
                "State data for Remote SFP DDM alarms";
            uses ipi-platform-remote-sfp-monitor-alarm-state;
        } // END of state-container definition.
    } // END of ipi-platform-remote-sfp-monitor-alarm-top definition.
    grouping ipi-platform-remote-sfp-protocol-state {
        description
            "ipi-platform-remote-sfp-protocol-state";
        leaf protocol-running-state  {
            type  ipi-platform-transceiver-types:cmm_smart_sfp_protocol_running_state_t;
            description "Smart SFP protocol running state.";
        } // END of protocol-running-state definition.

        leaf protocol-local-status  {
            type  ipi-platform-transceiver-types:cmm_smart_sfp_protocol_status_t;
            description "Smart SFP local protocol status.";
        } // END of protocol-local-status definition.

        leaf protocol-remote-status  {
            type  ipi-platform-transceiver-types:cmm_smart_sfp_protocol_status_t;
            description "Smart SFP remote protocol status.";
        } // END of protocol-remote-status definition.

        leaf packets-rx  {
            type  int32;
            description "Smart SFP number of protocol packets received.";
        } // END of packets-rx definition.

        leaf packets-tx  {
            type  int32;
            description "Smart SFP number of protocol packets transmitted.";
        } // END of packets-tx definition.

        leaf packets-error  {
            type  int32;
            description "Smart SFP number of protocol packets received with errors.";
        } // END of packets-error definition.

    } // END of ipi-platform-remote-sfp-protocol-state definition.
    grouping ipi-platform-remote-sfp-protocol-alarm-state {
        description
            "ipi-platform-remote-sfp-protocol-alarm-state";
        leaf alarm-id  {
            type  ipi-platform-transceiver-types:cmm_smart_sfp_protocol_alarm_id_t;
            description "Remote SFP protocol alarm ID";
        } // END of alarm-id definition.

        leaf current-status  {
            type  ipi-platform-transceiver-types:cmm_smart_sfp_protocol_status_t;
            description "Remote SFP protocol alarm status";
        } // END of current-status definition.

    } // END of ipi-platform-remote-sfp-protocol-alarm-state definition.
    grouping ipi-platform-remote-sfp-protocol-top {
        description
            "ipi-platform-remote-sfp-protocol-top";
        container state {
            config false;
            description
                "State data for Remote SFP protocol";
            uses ipi-platform-remote-sfp-protocol-state;
        } // END of state-container definition.
        container alarm {
            config false;
            description
                "Remote SFP protocol alarm information";
            container state {
                config false;
                description
                    "State data for Remote SFP protocol alarms";
                uses ipi-platform-remote-sfp-protocol-alarm-state;
            } // END of state-container definition.
        } // END of alarm-container definition.
    } // END of ipi-platform-remote-sfp-protocol-top definition.
    grouping ipi-platform-remote-sfp-top {
        description
            "ipi-platform-remote-sfp-top";

        list remote-sfp {
            key "port";
            config false;
            description
                "List of Remote SFP available";
            leaf port  {
                type  leafref {
                    path  "../state/port";
                }
                description "A value for each panel port within the unit";
            } // END of port definition.

            container state {
                config false;
                description
                    "Operational state data for a Remote SFP";
                uses ipi-platform-remote-sfp-state;
            } // END of state-container definition.
            container eeprom {
                config false;
                description
                    "Remote SFP EEPROM information";
                uses ipi-platform-remote-sfp-eeprom-top;
            } // END of eeprom-container definition.
            container monitors {
                config false;
                description
                    "Remote SFP DDM monitors information";
                uses ipi-platform-remote-sfp-monitors-top;
            } // END of monitors-container definition.
            container monitor-alarm {
                config false;
                description
                    "Remote SFP DDM alarm information";
                uses ipi-platform-remote-sfp-monitor-alarm-top;
            } // END of monitor-alarm-container definition.
            container protocol {
                config false;
                description
                    "Remote SFP protocol information";
                uses ipi-platform-remote-sfp-protocol-top;
            } // END of protocol-container definition.
        } // End of remote-sfp-list
    } // END of ipi-platform-remote-sfp-top definition.

    grouping  remote-sfps-grouping {
    description
        "Top level container of Remote SFP modules with their state data";
    container remote-sfps {
        if-feature feature-list:HAVE_CMMD;
        config false;
        description
            "Top level container of Remote SFP modules with their state data";
        uses ipi-platform-remote-sfp-top;
    } // END of remote-sfps-container definition.
    } // END of remote-sfps-grouping definition.


}
