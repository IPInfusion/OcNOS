/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-network-address-translation-types.yang
*
*/

module ipi-network-address-translation-types {

    yang-version 1.1;

    namespace   "http://www.ipinfusion.com/yang/ocnos/ipi-network-address-translation-types";

    prefix "ipi-network-address-translation-types";

    organization
        "IP Infusion Inc.";

    contact
        "Address: 3965 Freedom Circle, Suite 200, Santa Clara, CA 95054
         Phone: +1 408-400-1900
         E-mail: support@ipinfusion.com
         Web: http://www.ipinfusion.com/";

    description
        "Network Address Translation Types";


    revision "2022-06-01" {
        description "Updated the yang file with feature";
        reference " 0.2.0.";
    }

    revision "2021-08-26" {
        description "Inital version";
        reference " 0.1.0.";
    }



    typedef  nat_protocol_t {
        type enumeration {
            enum tcp {
                value 0;
                description "TCP";
            }
            enum udp {
                value 1;
                description "UDP";
            }
        }
        description "type definition for NAT_PROTOCOL_T";
    }

}
