/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-network-address-translation-interface.yang
*
*/

submodule ipi-network-address-translation-interface {

    yang-version 1.1;

    belongs-to  ipi-network-address-translation { prefix ipi-network-address-translation; }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Network Address Translation Interfaces.";


    revision "2025-08-13" {
        description "Removing extra callback-mapping tag";
        reference " 0.3.1.";
    }

    revision "2022-06-28" {
        description "Updated when expressions in yang";
        reference " 0.3.0.";
    }

    revision "2022-06-01" {
        description "Updated the yang file with feature";
        reference " 0.2.";
    }

    revision "2021-10-12" {
        description "Review corrections";
        reference " 0.1.1.";
    }

    revision "2021-08-27" {
        description "Initial Version";
        reference " 0.1.0.";
    }

    grouping network-address-translation-interface-config {
        description
            "Grouping Network Address Translation Interface configuration";
        leaf name  {
            type  string {
                length "1..33";
                pattern "[^?' =,>|]+";
            }
            description "The interface name to configure the NAT parameters.";
        } // END of name definition.

        leaf incoming  {
            type  empty;
            description "Incoming interface";
        } // END of incoming definition.

        leaf outgoing  {
            type  empty;
            description "Outgoing interface";
        } // END of outgoing definition.

    } // END of network-address-translation-interface-config definition.

    grouping  interfaces-grouping {
    description
        "NAT interfaces";
    container interfaces {
        if-feature feature-list:HAVE_IMI;
        if-feature feature-list:HAVE_NAT;
        description
            "NAT interfaces";

        list interface {
        // when " ipi-interface:interfaces/interface/config/enable-switchport != '1' ";
            key "name";
            description
                "List of NAT interfaces";
            leaf name  {
                type  leafref {
                    path  "../config/name";
                }
                description "The interface name to configure the NAT parameters.";
            } // END of name definition.

            container config {
                description
                    "Configuration data for OSPF interface";
                uses network-address-translation-interface-config;
            } // END of config-container definition.
            container state {
                config false;
                description
                    "Operational state data for OSPF interface";
                uses network-address-translation-interface-config;
            } // END of state-container definition.
        } // End of interface-list
    } // END of interfaces-container definition.
    } // END of interfaces-grouping definition.


}
