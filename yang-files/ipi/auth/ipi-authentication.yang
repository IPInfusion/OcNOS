/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-authentication.yang
*
*/

module ipi-authentication {

    yang-version 1.1;

    namespace   "http://www.ipinfusion.com/yang/ocnos/ipi-authentication";

    prefix "ipi-authentication";

    import ipi-authentication-types {
        prefix ipi-authentication-types;
        revision-date 2022-08-10;
    }

    import feature-list {
        prefix feature-list;
        revision-date 2026-09-15;
    }

    include ipi-authentication-dot1x-interface { revision-date 2022-07-04;}
    include ipi-authentication-mac-interface { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Authentication Configurations";


    revision "2023-03-17" {
        description "Added when tag dependency for debug container on system level debug disable command";
        reference " 0.10.1.";
    }

    revision "2022-08-10" {
        description "Debug hierarchy change";
        reference " 0.9.0.";
    }

    revision "2022-07-04" {
        description "No need to check switchport status for enable-mac-auth-bypass parameter";
        reference " 0.8.0.";
    }

    revision "2022-06-01" {
        description "Updated the yang file with feature";
        reference " 0.7.0.";
    }

    revision "2022-04-05" {
        description "Added groupings for operational values";
        reference " 0.6.0.";
    }

    revision "2022-04-01" {
        description "Added some state attributes on radius datamodel";
        reference " 0.5.0.";
    }

    revision "2022-03-18" {
        description "Changes made in submodules";
        reference " 0.4.0.";
    }

    revision "2022-02-16" {
        description "Fix when tag for switchport";
        reference " 0.3.0.";
    }

    revision "2022-01-28" {
        description "Restructured module in accordance with OpenConfig style";
        reference " 0.2.0.";
    }

    revision "2018-06-21" {
        description "Initial Version";
        reference " 0.1.0.";
    }

    grouping auth-debug-config {
        description
            "Grouping for Authentication Debug configurations";
        leaf options  {
            type  ipi-authentication-types:auth_dot1x_debug_t;
            description "Use this attribute to turn on or turn off 802.1x debugging at various
                        levels.";
        } // END of options definition.

    } // END of auth-debug-config definition.
    grouping auth-terminal-debug-state {
        description
            "Grouping for Authentication Debug configurations";
        leaf terminal-debug-status  {
            type  ipi-authentication-types:auth_dot1x_debug_t;
            description "Use this attribute to turn on or turn off 802.1x debugging at various
                        levels.";
        } // END of terminal-debug-status definition.

    } // END of auth-terminal-debug-state definition.
    grouping auth-debug-top {
        description
            "Grouping for Authentication Debug";
        container debug {
            description
                "Authentication Debug";
            container config {
                description
                    "Configuration data for Authentication Debug";
                uses auth-debug-config;
            } // END of config-container definition.
            container state {
                config false;
                description
                    "Operational state data for Authentication Debug";
                uses auth-debug-config;
                uses auth-terminal-debug-state;
            } // END of state-container definition.
        } // END of debug-container definition.
    } // END of auth-debug-top definition.
    grouping auth-global-config {
        description
            "Grouping for Authentication global configuration data";
        leaf mac-authentication  {
            if-feature feature-list:HAVE_MAC_AUTH;
            type  empty;
            description "Use this attribute to enable MAC authentication globally. If MAC
                        authentication is not enabled, other MAC authentication related
                        commands throw an error when issued.";
        } // END of mac-authentication definition.

        leaf dot1x-authentication  {
            type  empty;
            description "Use this attribute to enable globally authentication.";
        } // END of dot1x-authentication definition.

    } // END of auth-global-config definition.
    grouping auth-global-top {
        description
            "Grouping for Authentication global configuration";
        container global {
            description
                "Authentication global configuration";
            container config {
                description
                    "Configuration data for Authentication global";
                uses auth-global-config;
            } // END of config-container definition.
            container state {
                config false;
                description
                    "Operational state data for Authentication global";
                uses auth-global-config;
            } // END of state-container definition.
        } // END of global-container definition.
    } // END of auth-global-top definition.

    grouping  authentication-grouping {
    description
        "Grouping for Authentication";
    container authentication {
        if-feature feature-list:HAVE_AUTHD;
        description
            "Grouping for Authentication";
        uses auth-global-top;
        uses auth-dot1x-interface-top;
        uses auth-mac-interface-top;
        uses auth-debug-top;
    } // END of authentication-container definition.
    } // END of authentication-grouping definition.

    uses authentication-grouping;

    rpc dot1x-authentication-initialize-interface {
        if-feature feature-list:HAVE_MAC_AUTH;
        if-feature feature-list:HAVE_AUTHD;
        description "Initialize IEEE 802.1X Port-Based Access Control in an interface";
        input  {
            leaf name  {
                type string {
                    length "1..33";
                }
                mandatory true;
                description "Select an interface to initialize.";
            }
        }
    }

    rpc dot1x-authentication-snmp-restart {
        if-feature feature-list:HAVE_SNMP;
        if-feature feature-list:HAVE_AUTHD;
        description "Restart SNMP in Authentication";
    }

    rpc dot1x-authentication-terminal-debug-on {
        if-feature feature-list:HAVE_AUTHD;
        description "Enable Authentication debug categories";
        input  {
            leaf terminal-debug-options  {
                type ipi-authentication-types:auth_dot1x_debug_t;
                mandatory true;
                description "Bitmap representing Authentication debug categories";
            }
        }
    }

    rpc dot1x-authentication-terminal-debug-off {
        if-feature feature-list:HAVE_AUTHD;
        description "Disable Authentication debug categories";
        input  {
            leaf terminal-debug-options  {
                type ipi-authentication-types:auth_dot1x_debug_t;
                mandatory true;
                description "Bitmap representing Authentication debug categories";
            }
        }
    }

}
