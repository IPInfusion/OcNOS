/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-authentication-types.yang
*
*/

module ipi-authentication-types {

    yang-version 1.1;

    namespace   "http://www.ipinfusion.com/yang/ocnos/ipi-authentication-types";

    prefix "ipi-authentication-types";

    organization
        "IP Infusion Inc.";

    contact
        "Address: 3965 Freedom Circle, Suite 200, Santa Clara, CA 95054
         Phone: +1 408-400-1900
         E-mail: support@ipinfusion.com
         Web: http://www.ipinfusion.com/";

    description
        "Authentication Types";


    revision "2022-08-10" {
        description "Debug hierarchy change";
        reference " 0.4.0.";
    }

    revision "2022-06-01" {
        description "Updated the yang file with feature";
        reference " 0.3.0.";
    }

    revision "2022-03-18" {
        description "Added new type AUTH_DOT1X_MAC_ADDRESS_T";
        reference " 0.2.0.";
    }

    revision "2022-01-28" {
        description "Initial Version";
        reference " 0.1.0.";
    }



    typedef  auth_dot1x_control_t {
        type enumeration {
            enum force-unauthorized {
                value 0;
                description "Force port state to unauthorized";
            }
            enum force-authorized {
                value 1;
                description "Force port state to authorized";
            }
            enum auto {
                value 2;
                description "Allow port client to negotiate authentication";
            }
        }
        description "type definition for AUTH_DOT1X_CONTROL_T";
    }

    typedef  auth_dot1x_eapol_version_t {
        type enumeration {
            enum 1 {
                value 1;
                description "EAPOL v1";
            }
            enum 2 {
                value 2;
                description "EAPOL v2";
            }
        }
        description "type definition for AUTH_DOT1X_EAPOL_VERSION_T";
    }

    typedef  auth_dot1x_control_dir_t {
        type enumeration {
            enum both {
                value 0;
                description "Auth Ctrl Dir Both";
            }
            enum in {
                value 1;
                description "Auth Ctrl Dir In";
            }
        }
        description "type definition for AUTH_DOT1X_CONTROL_DIR_T";
    }

    typedef  auth_dot1x_port_status_t {
        type enumeration {
            enum Unknown {
                value 0;
                description "Unknown";
            }
            enum Authorized {
                value 1;
                description "Authorized";
            }
            enum Unauthorized {
                value 2;
                description "Unauthorized";
            }
        }
        description "type definition for AUTH_DOT1X_PORT_STATUS_T";
    }

    typedef  auth_dot1x_pae_state_t {
        type enumeration {
            enum Down {
                value 0;
                description "Down";
            }
            enum Init {
                value 1;
                description "Init";
            }
            enum Connected {
                value 2;
                description "Connected";
            }
            enum Connecting {
                value 3;
                description "Connecting";
            }
            enum Authenticating {
                value 4;
                description "Authenticating";
            }
            enum Authenticated {
                value 5;
                description "Authenticated";
            }
            enum Aborting {
                value 6;
                description "Aborting";
            }
            enum Held {
                value 7;
                description "Held";
            }
            enum Force-Authorized {
                value 8;
                description "Force,Authorized";
            }
            enum Force-Unauthorized {
                value 9;
                description "Force,Unauthorized";
            }
            enum Restart {
                value 10;
                description "Restart";
            }
        }
        description "type definition for AUTH_DOT1X_PAE_STATE_T";
    }

    typedef  auth_dot1x_port_ctrl_t {
        type enumeration {
            enum Invalid {
                value 0;
                description "Invalid";
            }
            enum Force-Unauthorized {
                value 1;
                description "Force,Unauthorized";
            }
            enum Force-Authorized {
                value 2;
                description "Force,Authorized";
            }
            enum Auto {
                value 3;
                description "Auto";
            }
        }
        description "type definition for AUTH_DOT1X_PORT_CTRL_T";
    }

    typedef  auth_dot1x_mac_auth_bypass_t {
        type enumeration {
            enum enable {
                value 1;
                description "Enable MAC authentication bypass";
            }
            enum disable {
                value 2;
                description "Disable MAC authentication bypass";
            }
        }
        description "type definition for AUTH_DOT1X_MAC_AUTH_BYPASS_T";
    }

    typedef  auth_be_state_t {
        type enumeration {
            enum Invalid {
                value 0;
                description "Invalid";
            }
            enum Request {
                value 1;
                description "Request";
            }
            enum Response {
                value 2;
                description "Response";
            }
            enum Success {
                value 3;
                description "Success";
            }
            enum Fail {
                value 4;
                description "Fail";
            }
            enum Timeout {
                value 5;
                description "Timeout";
            }
            enum Idle {
                value 6;
                description "Idle";
            }
            enum Initialize {
                value 7;
                description "Initialize";
            }
        }
        description "type definition for AUTH_BE_STATE_T";
    }

    typedef  auth_mac_mode_t {
        type enumeration {
            enum filter {
                value 0;
                description "Set port to filter mode";
            }
            enum shutdown {
                value 1;
                description "Set port to disable mode";
            }
        }
        description "type definition for AUTH_MAC_MODE_T";
    }

    typedef  auth_mac_dot1x_timer_status_t {
        type enumeration {
            enum Expired {
                value 0;
                description "Expired";
            }
            enum Running {
                value 1;
                description "Running";
            }
        }
        description "type definition for AUTH_MAC_DOT1X_TIMER_STATUS_T";
    }

    typedef  auth_mac_status_t {
        type enumeration {
            enum Unknown {
                value 0;
                description "Unknown";
            }
            enum Authorized {
                value 1;
                description "Authorized";
            }
            enum Unauthorized {
                value 2;
                description "Unauthorized";
            }
        }
        description "type definition for AUTH_MAC_STATUS_T";
    }

    typedef  auth_dot1x_debug_t {
        type bits {
            bit event {
                position 0;
                description "802.1X events";
            }
            bit timer {
                position 1;
                description "802.1X timer";
            }
            bit packet {
                position 2;
                description "802.1X packets";
            }
            bit nsm {
                position 3;
                description "802.1X NSM information";
            }
        }
        description "type definition for AUTH_DOT1X_DEBUG_T";
    }

    typedef  auth_dot1x_mac_address_t {
        type string {
            pattern "[0-9a-fA-F]{4}(.[0-9a-fA-F]{4}){2}";
        }
        description "The mac-address type representation in format XXXX.XXXX.XXXX";
    }

}
