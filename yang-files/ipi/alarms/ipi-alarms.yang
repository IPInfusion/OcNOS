/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-alarms.yang
*
*/

module ipi-alarms {

    yang-version 1.1;

    namespace   "http://www.ipinfusion.com/yang/ocnos/ipi-alarms";

    prefix "ipi-alarms";

    import cml-data-types {
        prefix cml-data-types;
        revision-date 2026-05-15;
    }

    import ipi-platform {
        prefix ipi-platform;
        revision-date 2026-08-14;
    }

    import ipi-alarms-types {
        prefix ipi-alarms-types;
        revision-date 2022-06-01;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for operational state data related to alarms that the device
                is reporting";


    revision "2026-03-03" {
        description "Changed the type for time-created to unint64 as TimeTicks not supported for 64 bits";
        reference " 0.6.2.";
    }

    revision "2025-09-11" {
        description "Added CHECK_SNMP flag in subType for alarm notification";
        reference " 0.6.1.";
    }

    revision "2025-08-08" {
        description "Added SNMP MIB file generation support for datamodel";
        reference " 0.6.0.";
    }

    revision "2023-09-11" {
        description "Added if-feature for platform module ,to avoide sku compilation failure";
        reference " 0.5.0.";
    }

    revision "2023-05-17" {
        description "Added units tag for milliseconds in time-created attribute";
        reference " 0.4.0.";
    }

    revision "2022-10-20" {
        description "Added attribute is-clear on Netconf notification";
        reference " 0.3.3.";
    }

    revision "2022-09-30" {
        description "Import cml-data-types used by notifications";
        reference " 0.3.2.";
    }

    revision "2022-08-09" {
        description "Added skip SMI generation";
        reference " 0.3.1.";
    }

    revision "2022-06-01" {
        description "Updated the yang file with feature";
        reference " 0.3.0.";
    }

    revision "2021-09-03" {
        description "Update descriptions of attribute";
        reference " 0.2.0.";
    }

    revision "2021-07-28" {
        description "Initial Version";
        reference " 0.1.0.";
    }

    grouping alarm-state {
        description
            "Operational state data for device alarms";
        leaf id  {
            type  string {
                length "1..1965";
            }
            description "Unique ID for the alarm";
        } // END of id definition.

        leaf resource  {
            type  string {
                length "1..1965";
            }
            description "The item that is under alarm within the device";
        } // END of resource definition.

        leaf text  {
            type  string {
                length "1..1965";
            }
            description "The string used to inform operators about the alarm";
        } // END of text definition.

        leaf time-created  {
            type  uint64;
            description "The time at which the alarm was raised by the system. This value is
                        expressed relative to the Unix Epoch";
        } // END of time-created definition.

        leaf alarm-reported-timestamp  {
            type  ipi-alarms-types:alarm_date_time_t {
                length "1..1965";
            }
            description "The date-time at which the alarm was raised by the system";
        } // END of alarm-reported-timestamp definition.

        leaf alarm-severity  {
            type  ipi-alarms-types:alarm_severity_t;
            description "The severity level indicating the criticality and impact of the alarm";
        } // END of alarm-severity definition.

        leaf type-id  {
            type  ipi-alarms-types:alarm_type_id_t;
            description "The abbreviated name of the alarm";
        } // END of type-id definition.

    } // END of alarm-state definition.
    grouping alarm-list-top {
        description
            "Top-level grouping for device alarms";

        list alarm {
            key "id";
            config false;
            description
                "List of alarms, keyed by a unique id";
            leaf id  {
                type  leafref {
                    path  "../state/id";
                }
                description "References the unique alarm id";
            } // END of id definition.

            container state {
                config false;
                description
                    "Operational state data for a device alarm";
                uses alarm-state;
            } // END of state-container definition.
        } // End of alarm-list
    } // END of alarm-list-top definition.

    grouping  alarms-grouping {
    description
        "Top-level container for operational state data related to alarms that
                the device is reporting";
    container alarms {
        if-feature feature-list:HAVE_FMS;
        description
            "Top-level container for operational state data related to alarms that
                    the device is reporting";
        uses alarm-list-top;
    } // END of alarms-container definition.
    } // END of alarms-grouping definition.

    grouping  component-alarm-grouping {
    description
        "Container for component alarm";
    container component-alarm {
        if-feature feature-list:HAVE_CMMD;
        if-feature feature-list:HAVE_FMS;
        config false;
        description
            "Container for component alarm";
        leaf equipment-failure  {
            type  boolean;
            description "If trueCOMMA the hardware indicates that the component's physical
                        equipment";
        } // END of equipment-failure definition.

    } // END of component-alarm-container definition.
    } // END of component-alarm-grouping definition.

    uses alarms-grouping;
    augment /ipi-platform:components/ipi-platform:component/ipi-platform:state {
        if-feature feature-list:HAVE_CMMD;
        description
            "Container for component alarm";
        uses component-alarm-grouping;
    }


    notification alarm {
        if-feature feature-list:HAVE_FMS;

        description "Notify the event of an alarm raised.";

        leaf severity {
            type cml-data-types:cml_notif_severity_t;
            description "Notification severity level";
        }

        leaf eventClass {
            type cml-data-types:cml_notif_class_t;
            description "Notification event class (value: STATE)";
        }

        leaf id {
            type  string;
        description
            "References the unique alarm id";
        }

        leaf resource {
            type  string;
        description
            "The item that is under alarm within the device";
        }

        leaf text {
            type  string;
        description
            "The string used to inform operators about the alarm";
        }

        leaf time-created {
            type  uint64;
        description
            "The time at which the alarm was raised by the system. This value is
                    expressed relative to the Unix Epoch";
        }

        leaf alarm-reported-timestamp {
            type ipi-alarms-types:alarm_date_time_t;
        description
            "The date-time at which the alarm was raised by the system";
        }

        leaf alarm-severity {
            type ipi-alarms-types:alarm_severity_t;
        description
            "The severity level indicating the criticality and impact of the alarm";
        }

        leaf type-id {
            type ipi-alarms-types:alarm_type_id_t;
        description
            "The abbreviated name of the alarm";
        }

        leaf is-clear {
            type  boolean;
        description
            "Indicates if this alarm is a clear alarm or not";
        }
    }

}
