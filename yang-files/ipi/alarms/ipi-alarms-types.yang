/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-alarms-types.yang
*
*/

module ipi-alarms-types {

    yang-version 1.1;

    namespace   "http://www.ipinfusion.com/yang/ocnos/ipi-alarms-types";

    prefix "ipi-alarms-types";

    organization
        "IP Infusion Inc.";

    contact
        "Address: 3965 Freedom Circle, Suite 200, Santa Clara, CA 95054
         Phone: +1 408-400-1900
         E-mail: support@ipinfusion.com
         Web: http://www.ipinfusion.com/";

    description
        "Data types for ipi-alarms";


    revision "2022-06-01" {
        description "Updated the yang file with feature";
        reference " 0.3.0.";
    }

    revision "2021-09-03" {
        description "Update descriptions of attribute";
        reference " 0.2.0.";
    }

    revision "2021-07-12" {
        description "Initial Version";
        reference " 0.1.0.";
    }



    typedef  alarm_date_time_t {
        type string;
        description "Alarm date-time creation definition";
    }

    typedef  alarm_severity_t {
        type enumeration {
            enum CRITICAL {
                value 0;
                description "Indicates that a service affecting condition has ocorrued and an immediate corrective action is required. Such a severity can be reported for example: when a resource becomes totally out of service and its capability must be resported";
            }
            enum MAJOR {
                value 1;
                description "Indicates that a service affecting condition has developed and an urgent corrective action is required. Such a severity can be reported for example: when there is a severe degradation in the capability of the resource and its full capability must be restored";
            }
            enum MINOR {
                value 2;
                description "Indicates the existence of a non-service affecting fault condition and that corrective action should be taken in order to prevent a more serious (for example service affecting) fault. Such a severity can be reported for example: when the detected alarm condition is not currently degrading the capacity of the resource";
            }
            enum WARNING {
                value 3;
                description "Indicates the detection of a potential or impeding service affecting fault before any significant effects have been felt. Action should be taken to further diagnose (if necessary) and correct the problem in order to prevent it from becoming a more serious service affecting fault";
            }
            enum UNKNOWN {
                value 4;
                description "Indicates that the severity level could not be determined.";
            }
        }
        description "type definition for ALARM_SEVERITY_T";
    }

    typedef  alarm_type_id_t {
        type enumeration {
            enum AIS {
                value 0;
                description "Defines an alarm indication signal type of alarm";
            }
            enum EQPT {
                value 1;
                description "Defines an equipment related type of alarm that is specific to the physical hardware";
            }
            enum LOS {
                value 2;
                description "Defines a loss of signal type of alarm";
            }
            enum OTS {
                value 3;
                description "Defines a optical transport signal type of alarm";
            }
            enum OPWR {
                value 4;
                description "Defines a optical power type of alarm";
            }
            enum UNKNOWN {
                value 5;
                description "Defines an unknown type of alarm";
            }
        }
        description "type definition for ALARM_TYPE_ID_T";
    }

}
