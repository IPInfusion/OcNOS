/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-streaming-telemetry.yang
*
*/

module ipi-streaming-telemetry {

    yang-version 1.1;

    namespace   "http://www.ipinfusion.com/yang/ocnos/ipi-streaming-telemetry";

    prefix "ipi-streaming-telemetry";

    import ipi-streaming-telemetry-types {
        prefix ipi-streaming-telemetry-types;
        revision-date 2025-08-26;
    }

    import ietf-inet-types {
        prefix inet;
        revision-date 2013-07-15;
    }

    import ipi-network-instance {
        prefix ipi-network-instance;
        revision-date 2026-08-12;
    }

    import ipi-vrf {
        prefix ipi-vrf;
        revision-date 2026-08-12;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for management streaming telemetry configurations";


    revision "2025-09-04" {
        description "do-not-suppress cli moved to hidded cli";
        reference " 0.2.26.";
    }

    revision "2025-08-29" {
        description "Port range updated for tls and non-tls port";
        reference " 0.2.25.";
    }

    revision "2025-08-26" {
        description "Inclusion of runtime leafs for on-change support";
        reference " 0.2.24.";
    }

    revision "2025-05-07" {
        description "removal of debug telemetry configuration,while doing no debug all in config mode";
        reference " 0.2.23.";
    }

    revision "2025-04-18" {
        description "CPU default threshold value updated";
        reference " 0.2.22.";
    }

    revision "2025-04-09" {
        description "Copy right year update ";
        reference " 0.2.21.";
    }

    revision "2025-03-28" {
        description "CPU Monitoring feature added";
        reference " 0.2.20.";
    }

    revision "2025-02-10" {
        description "Added telemetry keyword for global mode CLIs";
        reference " 0.2.19.";
    }

    revision "2025-01-28" {
        description "Insecure cli moved to tls cli command";
        reference " 0.2.18.";
    }

    revision "2025-01-17" {
        description "Added platform specific default value in minimum-sample-interval cli helpstring";
        reference " 0.2.17.";
    }

    revision "2025-01-09" {
        description "moved gnmi-debug when expression to debug/config container";
        reference " 0.2.16.";
    }

    revision "2024-12-09" {
        description "modified debug/config container to presence container and removed CML_FORCE_SET flag";
        reference " 0.2.15.";
    }

    revision "2024-11-28" {
        description "moved retry-interval leaf to retry/cofig container";
        reference " 0.2.14.";
    }

    revision "2024-11-19" {
        description "Added runtime attribute for maximum-subscribe-path and minimum-sample-interval";
        reference " 0.2.13.";
    }

    revision "2024-11-15" {
        description "modifying max-element as 4 for supporting multiple vrf instances of  telemetry, and moving debug to global level";
        reference " 0.2.12.";
    }

    revision "2024-11-12" {
        description "TLS attributes moved under streaming-telemetry-feature-config grouping";
        reference " 0.2.11.";
    }

    revision "2024-11-09" {
        description "TLS CLI added";
        reference " 0.2.10.";
    }

    revision "2024-11-07" {
        description "Added support for max-subscribe-path and minimum-sample-interval";
        reference " 0.2.9.";
    }

    revision "2024-07-08" {
        description "Added dependent object in telemetry enable object";
        reference " 0.2.8.";
    }

    revision "2024-05-29" {
        description "Support default, user-defined VRFs in addition to management vrf that is currently supported";
        reference " 0.2.7.";
    }

    revision "2024-05-23" {
        description "Inclusion of platform-type leaf under streaming-telemetry/state";
        reference " 0.2.6.";
    }

    revision "2024-05-02" {
        description "Inclusion of state atributes under streaming-telemetry/state";
        reference " 0.2.5.";
    }

    revision "2024-02-26" {
        description "Pattern update for persistent subscription sensor-path";
        reference " 0.2.4.";
    }

    revision "2024-01-23" {
        description "Modified retry-interval range and default value";
        reference " 0.2.3.";
    }

    revision "2024-01-19" {
        description "Encoding CLI added";
        reference " 0.2.2.";
    }

    revision "2023-12-13" {
        description "Modified sample-interval min range from 5 to 10";
        reference " 0.2.1.";
    }

    revision "2023-11-08" {
        description "Inclusion of dial-out CLI's";
        reference " 0.2.0.";
    }

    revision "2023-10-26" {
        description "Inclusion of streaming telemetry data-types yang";
        reference " 0.1.3.";
    }

    revision "2023-10-06" {
        description "Adding client-address attr in dynamic subscription show command";
        reference " 0.1.2.";
    }

    revision "2023-08-10" {
        description "Inclusion of gnmi debug commands";
        reference " 0.1.1.";
    }

    revision "2023-04-25" {
        description "Initial version to include streaming telemetry configs";
        reference " 0.1.0.";
    }

    grouping telemetry-dial-in-sensor-path-config {
        description
            "Configuration parameters relating to the grouping of data model paths
                        comprising a sensor grouping";
        leaf path  {
            type  string {
                length "1..1965";
            }
            description "Path to a section of operational state of interest (the sensor)";
        } // END of path definition.

    } // END of telemetry-dial-in-sensor-path-config definition.
    grouping telemetry-dial-in-sensor-paths {
        description
            "Dial-in sensor path related configs";
        container sensor-paths {
            config false;
            description
                "Top level container to hold a set of sensor paths grouped together";

            list sensor-path {
                key "path";
                config false;
                description
                    "List of paths in the model which together comprise a sensor grouping";
                leaf path  {
                    type  leafref {
                        path  "../state/path";
                    }
                    description "Reference to the path of interest";
                } // END of path definition.

                container state {
                    config false;
                    description
                        "State information for a dynamic subscription's paths of interest";
                    uses telemetry-dial-in-sensor-path-config;
                } // END of state-container definition.
            } // End of sensor-path-list
        } // END of sensor-paths-container definition.
    } // END of telemetry-dial-in-sensor-paths definition.
    grouping telemetry-dial-in-subscription {
        description
            "Configuration parameters relating to the telemetry subscription";
        leaf id  {
            type  uint64;
            description "System generated identifer of the telemetry subscription";
        } // END of id definition.

        leaf client-address  {
            type  string {
                length "1..1965";
            }
            description "Dial-in subscription client address which is combination of
                        ip-address:port";
        } // END of client-address definition.

        leaf sample-interval  {
            type  uint64;
            description "Time in seconds between the device's sample of a telemetry data source";
        } // END of sample-interval definition.

        leaf stream-mode  {
            type  ipi-streaming-telemetry-types:cml_streaming_types_t;
            description "Specifies the mode of streaming request whether once or poll or stream";
        } // END of stream-mode definition.

        leaf heartbeat-interval  {
            type  uint64;
            description "Time in seconds between the device's updated telemetry data source for
                        on-change subscriptions";
        } // END of heartbeat-interval definition.

        leaf stream-type  {
            type  ipi-streaming-telemetry-types:cml_stream_mode_types_t;
            description "Specifies the stream mode type sample or on-change";
        } // END of stream-type definition.

        leaf encoding  {
            type  ipi-streaming-telemetry-types:cml_data_encode_t;
            description "Selection of the specific encoding or RPC framework for telemetry
                        messages to and from the network element. The encoding method controls
                        specifically the wire format of the telemetry data, and also controls
                        which RPC framework may be in use to exchange telemetry data";
        } // END of encoding definition.

    } // END of telemetry-dial-in-subscription definition.
    grouping streaming-telemetry-dial-in-top {
        description
            "Dynamic subscriptions Info";
        container dynamic-subscriptions {
            config false;
            description
                "This container holds information relating to dynamic telemetry
                        subscriptions";

            list dynamic-subscription {
                key "id";
                config false;
                description
                    "List representation of telemetry subscriptions that are configured via
                                an inline RPC, otherwise known as dynamic telemetry subscriptions";
                leaf id  {
                    type  leafref {
                        path  "../state/id";
                    }
                    description "System generated identifer of the telemetry subscription";
                } // END of id definition.

                container state {
                    config false;
                    description
                        "State information relating to dynamic telemetry subscriptions";
                    uses telemetry-dial-in-subscription;
                } // END of state-container definition.
                uses telemetry-dial-in-sensor-paths;
            } // End of dynamic-subscription-list
        } // END of dynamic-subscriptions-container definition.
    } // END of streaming-telemetry-dial-in-top definition.
    grouping telemetry-debug-options {
        description
            "Parameters related to debug";
        leaf gnmi-debug  {
            type  empty;
            mandatory true;
            description "Enable or Disable device's debug telemetry";
        } // END of gnmi-debug definition.

        leaf gnmi-severity  {
            // when " ../gnmi-debug ";
            type  ipi-streaming-telemetry-types:cml_gnmi_debug_severity_t;
            default "error";
            description "device's debug telemetry severity level";
        } // END of gnmi-severity definition.

    } // END of telemetry-debug-options definition.
    grouping streaming-telemetry-debug {
        description
            "Configuration objects related to debigging";
        container debug {
            description
                "Container for debug related configurations";
            container config {
                when " /ipi-streaming-telemetry:telemetry-system/ipi-streaming-telemetry:vrfs/ipi-streaming-telemetry:vrf/ipi-streaming-telemetry:streaming-telemetry/ipi-streaming-telemetry:config/ipi-streaming-telemetry:feature-enabled ";
                presence "gnmi-debug container";
                description
                    "Config container for debug options";
                uses telemetry-debug-options;
            } // END of config-container definition.
            container state {
                presence "gnmi-debug-container";
                config false;
                description
                    "state container for debug options";
                uses telemetry-debug-options;
            } // END of state-container definition.
        } // END of debug-container definition.
    } // END of streaming-telemetry-debug definition.
    grouping streaming-telemetry-state-details {
        description
            "State information related to streaming telemetry";
        leaf platform-type  {
            type  ipi-streaming-telemetry-types:cml_telemetry_platform_type_t;
            description "Specifies type of patform whether high range or low - medium range";
        } // END of platform-type definition.

        leaf default-retry-interval  {
            type  uint8;
            description "If the grpc-tunnel-server is unreachable, the gnmi-server retries to
                        connect with gnmi-client after the default retry-interval";
        } // END of default-retry-interval definition.

        leaf active-sensor-paths  {
            type  uint8;
            description "Count of active number of sensor-paths in the device, which is
                        including both dial-in and dial-out";
        } // END of active-sensor-paths definition.

        leaf active-dial-in-sensor-paths  {
            type  uint8;
            description "Count of active number of dial-in sensor-paths in the device";
        } // END of active-dial-in-sensor-paths definition.

        leaf active-dial-out-sensor-paths  {
            type  uint8;
            description "Count of active number of dial-out sensor-paths in the device";
        } // END of active-dial-out-sensor-paths definition.

    } // END of streaming-telemetry-state-details definition.
    grouping streaming-telemetry-feature-config {
        description
            "Configuration parameters related to streaming telemetry";
        leaf feature-enabled  {
            type  empty;
            mandatory true;
            description "Use this attribute to enable or disable Telemetry feature";
        } // END of feature-enabled definition.

        leaf tls-port  {
            // when " !ipi-streaming-telemetry:telemetry-system/vrfs/vrf/streaming-telemetry/config/non-tls-port ";
            type  uint32 {
                 range "1024..65535"  {
                    description "1024..65535: Supported range 1024 - 65535";
                 }
            }
            description "Port for secure connection";
        } // END of tls-port definition.

        leaf insecure-tls  {
            // when " ipi-streaming-telemetry:telemetry-system/vrfs/vrf/streaming-telemetry/config/tls-port ";
            type  empty;
            description "Disable certificate validation in a TLS-enabled connection";
        } // END of insecure-tls definition.

        leaf non-tls-port  {
            // when " !ipi-streaming-telemetry:telemetry-system/vrfs/vrf/streaming-telemetry/config/tls-port ";
            type  uint32 {
                 range "1024..65535"  {
                    description "1024..65535: Supported range 1024 - 65535";
                 }
            }
            description "Insecure port for Telemetry feature";
        } // END of non-tls-port definition.

    } // END of streaming-telemetry-feature-config definition.
    grouping streaming-telemetry-retry-config {
        description
            "Configuration parameters related to streaming telemetry";
        leaf retry-interval  {
            type  uint32 {
                 range "30..3000"  {
                    description "30..3000: Supported range 30 - 3000";
                 }
            }
            units "seconds";
            default "60";
            description "If the grpc-tunnel-server is unreachable, the gnmi-server retries to
                        connect with gnmi-client after the retry-interval";
        } // END of retry-interval definition.

    } // END of streaming-telemetry-retry-config definition.
    grouping streaming-telemetry-retry-top {
        description
            "Telemetry retry related configuration";
        container retry {
            when " /ipi-streaming-telemetry:telemetry-system/ipi-streaming-telemetry:vrfs/ipi-streaming-telemetry:vrf/ipi-streaming-telemetry:streaming-telemetry/ipi-streaming-telemetry:config/ipi-streaming-telemetry:feature-enabled ";
            description
                "Configuration parameters related to retry-interval";
            container config {
                when " /ipi-streaming-telemetry:telemetry-system/ipi-streaming-telemetry:vrfs/ipi-streaming-telemetry:vrf/ipi-streaming-telemetry:streaming-telemetry/ipi-streaming-telemetry:config/ipi-streaming-telemetry:feature-enabled ";
                description
                    "Configuration parameters related to retry-interval";
                uses streaming-telemetry-retry-config;
            } // END of config-container definition.
            container state {
                config false;
                description
                    "State information related to retry-interval";
                uses streaming-telemetry-retry-config;
            } // END of state-container definition.
        } // END of retry-container definition.
    } // END of streaming-telemetry-retry-top definition.
    grouping streaming-telemetry-global-top {
        description
            "Telemetry global configuration";
        container global {
            when " /ipi-streaming-telemetry:telemetry-system/ipi-streaming-telemetry:vrfs/ipi-streaming-telemetry:vrf/ipi-streaming-telemetry:streaming-telemetry/ipi-streaming-telemetry:config/ipi-streaming-telemetry:feature-enabled ";
            description
                "Configuration parameters related to global telemetry";
            container config {
                when " /ipi-streaming-telemetry:telemetry-system/ipi-streaming-telemetry:vrfs/ipi-streaming-telemetry:vrf/ipi-streaming-telemetry:streaming-telemetry/ipi-streaming-telemetry:config/ipi-streaming-telemetry:feature-enabled ";
                description
                    "Configuration parameters related to global telemetry";
                uses streaming-telemetry-global-config;
            } // END of config-container definition.
            container state {
                config false;
                description
                    "State information related to global telemetry";
                uses streaming-telemetry-global-config;
                uses streaming-telemetry-global-state;
            } // END of state-container definition.
        } // END of global-container definition.
    } // END of streaming-telemetry-global-top definition.
    grouping streaming-telemetry-global-config {
        description
            "Telemetry global configuration";
        leaf config-maximum-subscribe-paths  {
            type  uint32 {
                 range "10..1000"  {
                    description "10..1000: Supported range 10 - 1000";
                 }
            }
            description "Maximum number of sensor-paths supported for this device";
        } // END of config-maximum-subscribe-paths definition.

        leaf config-minimum-sample-interval  {
            type  uint32 {
                 range "10..3600"  {
                    description "10..3600: Supported range 10 - 3600";
                 }
            }
            description "Minimum sample-interval supported for this device";
        } // END of config-minimum-sample-interval definition.

    } // END of streaming-telemetry-global-config definition.
    grouping streaming-telemetry-global-state {
        description
            "Telemetry global configuration";
        leaf maximum-subscribe-paths  {
            type  uint32 {
                 range "10..1000"  {
                    description "10..1000: Supported range 10 - 1000";
                 }
            }
            description "Maximum number of sensor-paths supported for this device";
        } // END of maximum-subscribe-paths definition.

        leaf minimum-sample-interval  {
            type  uint32 {
                 range "10..3600"  {
                    description "10..3600: Supported range 10 - 3600";
                 }
            }
            description "Minimum sample-interval supported for this device";
        } // END of minimum-sample-interval definition.

    } // END of streaming-telemetry-global-state definition.
    grouping streaming-telemetry-subsystem-config {
        description
            "gNMI server configuration";
        leaf vrf-name  {
            if-feature feature-list:HAVE_VRF;
            type  leafref {
                path  "/ipi-network-instance:network-instances/ipi-network-instance:network-instance/ipi-vrf:vrf/ipi-vrf:config/ipi-vrf:vrf-name";
            }
            description "VRF Name associated with this instance";
        } // END of vrf-name definition.

    } // END of streaming-telemetry-subsystem-config definition.
    grouping streaming-telemetry-subsystem-top {
        description
            "Grouping for gNMI subsystem related configuration";
        container vrfs {
            if-feature feature-list:HAVE_VRF;
            description
                "gNMI server VRF configurations";

            list vrf {
            // when " ipi-streaming-telemetry:telemetry-system/vrfs/vrf/streaming-telemetry/config/feature-enabled ";
                key "vrf-name";
                max-elements 4;
                description
                    "gNMI server VRF instance configurations";
                leaf vrf-name  {
                    type  leafref {
                        path  "../config/vrf-name";
                    }
                    description "Use this attribute to specify the VRF for which STREAMING-TELEMETRY
                                feature is enabled";
                } // END of vrf-name definition.

                container config {
                    description
                        "config container for gNMI Server VRF instance configurations";
                    uses streaming-telemetry-subsystem-config;
                } // END of config-container definition.
                container state {
                    config false;
                    description
                        "state container for STREAMING-TELEMETRY VRF instance configurations";
                    uses streaming-telemetry-subsystem-config;
                } // END of state-container definition.
                uses streaming-telemetry-top;
                uses streaming-telemetry-subscription-groups;
                uses streaming-telemetry-sensor-groups;
                uses streaming-telemetry-destination-groups;
            } // End of vrf-list
        } // END of vrfs-container definition.
    } // END of streaming-telemetry-subsystem-top definition.
    grouping streaming-telemetry-top {
        description
            "Top level grouping for streaming telemetry configuration and
                        operational state data";
        container streaming-telemetry {
            description
                "Top level container for enable or disable telemetry configurations";
            container config {
                // when " ipi-streaming-telemetry:telemetry-system/vrfs/vrf/streaming-telemetry/config/feature-enabled ";
                presence "feature-enabled";
                description
                    "Configuration parameters related to streaming telemetry enable or
                            disable";
                uses streaming-telemetry-feature-config;
            } // END of config-container definition.
            container state {
                config false;
                description
                    "state information related to streaming telemetry enable or disable";
                uses streaming-telemetry-feature-config;
                uses streaming-telemetry-state-details;
            } // END of state-container definition.
            uses streaming-telemetry-retry-top;
        } // END of streaming-telemetry-container definition.
    } // END of streaming-telemetry-top definition.
    grouping telemetry-sensor-path-config {
        description
            "Configuration parameters relating to the grouping of data model paths
                        comprising a sensor grouping";
        leaf path  {
            type  string {
                length "1..1965";
                pattern "[^?',>|]+";
            }
            description "Path to a section of operational state of interest (the sensor)";
        } // END of path definition.

    } // END of telemetry-sensor-path-config definition.
    grouping telemetry-sensor-group-config {
        description
            "Config parameters related to the sensor groups on the device";
        leaf sensor-group-id  {
            type  string {
                length "1..64";
                pattern "[^?' =,>|]+";
            }
            description "Name or identifier for the sensor group itself.Will be referenced by
                        other configuration specifying a sensor group";
        } // END of sensor-group-id definition.

    } // END of telemetry-sensor-group-config definition.
    grouping streaming-telemetry-sensor-groups {
        description
            "Top level grouping for sensor-groups";
        container sensor-groups {
            description
                "Top level container for sensor-groups";

            list sensor-group {
            when " /ipi-streaming-telemetry:telemetry-system/ipi-streaming-telemetry:vrfs/ipi-streaming-telemetry:vrf/ipi-streaming-telemetry:streaming-telemetry/ipi-streaming-telemetry:config/ipi-streaming-telemetry:feature-enabled ";
                key "sensor-group-id";
                description
                    "List of telemetry sensor- groups information";
                leaf sensor-group-id  {
                    type  leafref {
                        path  "../config/sensor-group-id";
                    }
                    description "Name or identifier for the sensor group itself.Will be referenced by
                                other configuration specifying a sensor group";
                } // END of sensor-group-id definition.

                container config {
                    description
                        "Configuration parameters relating to the telemetry sensor grouping";
                    uses telemetry-sensor-group-config;
                } // END of config-container definition.
                container state {
                    config false;
                    description
                        "State information relating to the telemetry sensor grouping";
                    uses telemetry-sensor-group-config;
                } // END of state-container definition.
                container sensor-paths {
                    description
                        "Top level container to hold a set of sensor paths grouped together";

                    list sensor-path {
                        key "path";
                        description
                            "List of paths in the model which together comprise a sensor grouping";
                        leaf path  {
                            type  leafref {
                                path  "../config/path";
                            }
                            description "Reference to the path of interest";
                        } // END of path definition.

                        container config {
                            description
                                "Configuration parameters to configure a set of data model paths as a
                                        sensor grouping";
                            uses telemetry-sensor-path-config;
                        } // END of config-container definition.
                        container state {
                            config false;
                            description
                                "State information relating to set of data model paths as a sensor
                                        grouping";
                            uses telemetry-sensor-path-config;
                        } // END of state-container definition.
                    } // End of sensor-path-list
                } // END of sensor-paths-container definition.
            } // End of sensor-group-list
        } // END of sensor-groups-container definition.
    } // END of streaming-telemetry-sensor-groups definition.
    grouping telemetry-stream-destination-config {
        description
            "Configuration parameters for the stream destinations";
        leaf destination-address  {
            type  inet:ipv4-address;
            description "IP address of the telemetry stream destination";
        } // END of destination-address definition.

        leaf destination-port  {
            type  uint16 {
                 range "1..65535"  {
                    description "1..65535: Supported range 1 - 65535";
                 }
            }
            description "Protocol (udp or tcp) port number for the telemetry stream destination";
        } // END of destination-port definition.

    } // END of telemetry-stream-destination-config definition.
    grouping telemetry-destination-groups-config {
        description
            "Top level state container for destination groups";
        leaf group-id  {
            type  string {
                length "1..64";
                pattern "[^?' =,>|]+";
            }
            description "Unique identifier for the destination group";
        } // END of group-id definition.

    } // END of telemetry-destination-groups-config definition.
    grouping streaming-telemetry-destination-groups {
        description
            "Top level grouping for destination groups";
        container destination-groups {
            description
                "Top level container for destination group configuration and state";

            list destination-group {
            when " /ipi-streaming-telemetry:telemetry-system/ipi-streaming-telemetry:vrfs/ipi-streaming-telemetry:vrf/ipi-streaming-telemetry:streaming-telemetry/ipi-streaming-telemetry:config/ipi-streaming-telemetry:feature-enabled ";
                key "group-id";
                description
                    "List of destination-groups.A destination group may contain one or more
                                telemetry destinations";
                leaf group-id  {
                    type  leafref {
                        path  "../config/group-id";
                    }
                    description "Unique identifier for the destination group";
                } // END of group-id definition.

                container config {
                    description
                        "Top level config container for destination groups";
                    uses telemetry-destination-groups-config;
                } // END of config-container definition.
                container state {
                    config false;
                    description
                        "Top level state container for destination groups";
                    uses telemetry-destination-groups-config;
                } // END of state-container definition.
                container destinations {
                    description
                        "The destination container lists the destination information such as IP
                                address and port of the telemetry messages from the network element";

                    list destination {
                        key "destination-address destination-port";
                        description
                            "List of telemetry stream destinatios";
                        leaf destination-address  {
                            type  leafref {
                                path  "../config/destination-address";
                            }
                            description "Reference to the destination address of the telemetry stream";
                        } // END of destination-address definition.

                        leaf destination-port  {
                            type  leafref {
                                path  "../config/destination-port";
                            }
                            description "Reference to the port number of the stream destination";
                        } // END of destination-port definition.

                        container config {
                            description
                                "Configuration parameters relating to telemetry destinations";
                            uses telemetry-stream-destination-config;
                        } // END of config-container definition.
                        container state {
                            config false;
                            description
                                "State information associated with telemetry destinations";
                            uses telemetry-stream-destination-config;
                        } // END of state-container definition.
                    } // End of destination-list
                } // END of destinations-container definition.
            } // End of destination-group-list
        } // END of destination-groups-container definition.
    } // END of streaming-telemetry-destination-groups definition.
    grouping telemetry-subscription-config {
        description
            "This grouping holds information related to persistent configurations";
        leaf name  {
            type  string {
                length "1..64";
                pattern "[^?' =,>|]+";
            }
            description "User configured identifier of the telemetry subscription. This value
                        is used primarily for subscriptions configured locally on the network
                        element";
        } // END of name definition.

        leaf encoding  {
            type  ipi-streaming-telemetry-types:cml_data_encode_t;
            description "Selection of the specific encoding or RPC framework for telemetry
                        messages to and from the network element. The encoding method controls
                        specifically the wire format of the telemetry data, and also controls
                        which RPC framework may be in use to exchange telemetry data";
        } // END of encoding definition.

    } // END of telemetry-subscription-config definition.
    grouping telemetry-subscription-state-configs {
        description
            "This grouping holds information related to persistent state info";
        leaf id  {
            type  uint64;
            description "System generated identifer of the telemetry subscription";
        } // END of id definition.

        leaf subscription-status  {
            type  ipi-streaming-telemetry-types:cml_telemetry_status_t;
            description "Status of the subscription";
        } // END of subscription-status definition.

        leaf inactive-cause  {
            type  string {
                length "1..1965";
            }
            description "Reason for inactive subscriptions";
        } // END of inactive-cause definition.

        leaf protocol  {
            type  ipi-streaming-telemetry-types:cml_telemetry_protocol_t;
            description "Selection of the transport protocol for the telemetry stream";
        } // END of protocol definition.

    } // END of telemetry-subscription-state-configs definition.
    grouping telemetry-sensor-profile-config {
        description
            "Configuration parameters relating to the sensor groups used in the
                        sensor profile";
        leaf sensor-group  {
            type  leafref {
                path  "/telemetry-system/vrfs/vrf/sensor-groups/sensor-group/sensor-group-id";
            }
            description "Reference to the sensor group which is used in the profile";
        } // END of sensor-group definition.

        leaf sample-interval  {
            type  uint64 {
                 range "10..3600"  {
                    description "10..3600: Supported range 10 - 3600";
                 }
            }
            units "seconds";
            mandatory true;
            description "Time in seconds between the device's sample of a telemetry data source";
        } // END of sample-interval definition.

    } // END of telemetry-sensor-profile-config definition.
    grouping telemetry-destination-profile-config {
        description
            "Configuration parameters related to telemetry destinations";
        leaf group-id  {
            type  leafref {
                path  "/telemetry-system/vrfs/vrf/destination-groups/destination-group/group-id";
            }
            description "The destination group id references a reusable group of destination
                        addresses and ports for the telemetry stream";
        } // END of group-id definition.

    } // END of telemetry-destination-profile-config definition.
    grouping streaming-telemetry-dial-out-top {
        description
            "This grouping holds information relating to persistent telemetry
                        subscriptions";
        container persistent-subscriptions {
            description
                "A persistent telemetry subscription is configued locally on the device
                        through configuration, and is persistent across device restarts or
                        other redundancy changes";

            list persistent-subscription {
            when " /ipi-streaming-telemetry:telemetry-system/ipi-streaming-telemetry:vrfs/ipi-streaming-telemetry:vrf/ipi-streaming-telemetry:streaming-telemetry/ipi-streaming-telemetry:config/ipi-streaming-telemetry:feature-enabled ";
                key "name";
                description
                    "List of telemetry subscriptions. A telemetry subscription consists of
                                a set of collection destinations, stream attributes, and associated
                                paths to state information in the model";
                leaf name  {
                    type  leafref {
                        path  "../config/name";
                    }
                    description "Reference to the identifier of the subscription itself. The id will be
                                the handle to refer to the subscription once created";
                } // END of name definition.

                container config {
                    description
                        "Config parameters relating to the telemetry subscriptions on the local
                                device";
                    uses telemetry-subscription-config;
                } // END of config-container definition.
                container state {
                    config false;
                    description
                        "State parameters relating to the telemetry subscriptions on the local
                                device";
                    uses telemetry-subscription-config;
                    uses telemetry-subscription-state-configs;
                } // END of state-container definition.
                container sensor-profiles {
                    description
                        "A sensor profile is a set of sensor groups or individual sensor paths
                                which are associated with a telemetry subscription";

                    list sensor-profile {
                        key "sensor-group";
                        description
                            "List of telemetry sensor groups used in the subscription";
                        leaf sensor-group  {
                            type  leafref {
                                path  "../config/sensor-group";
                            }
                            description "Reference to the telemetry sensor group name";
                        } // END of sensor-group definition.

                        container config {
                            description
                                "Configuration parameters related to the sensor profile for a
                                        subscription";
                            uses telemetry-sensor-profile-config;
                        } // END of config-container definition.
                        container state {
                            config false;
                            description
                                "State information relating to the sensor profile for a subscription";
                            uses telemetry-sensor-profile-config;
                        } // END of state-container definition.
                    } // End of sensor-profile-list
                } // END of sensor-profiles-container definition.
                container destination-groups {
                    description
                        "A subscription may specify destination addresses.If the subscription
                                supplies destination addresses, the network element will be the
                                initiator of the telemetry streaming, sending it to the destination(s)
                                specified.";

                    list destination-group {
                        key "group-id";
                        description
                            "Identifier of the previously defined destination group";
                        leaf group-id  {
                            type  leafref {
                                path  "../config/group-id";
                            }
                            description "The destination group id references a configured group of destinations
                                        for the telemetry stream";
                        } // END of group-id definition.

                        container config {
                            description
                                "Configuration parameters related to telemetry destinations";
                            uses telemetry-destination-profile-config;
                        } // END of config-container definition.
                        container state {
                            config false;
                            description
                                "State information related to telemetry destinations";
                            uses telemetry-destination-profile-config;
                        } // END of state-container definition.
                    } // End of destination-group-list
                } // END of destination-groups-container definition.
            } // End of persistent-subscription-list
        } // END of persistent-subscriptions-container definition.
    } // END of streaming-telemetry-dial-out-top definition.
    grouping streaming-telemetry-subscription-groups {
        description
            "Grouping related to stream subscriptions";
        container subscriptions {
            description
                "This container holds information for both persistent and dynamic
                        telemetry subscriptions";
            uses streaming-telemetry-dial-in-top;
            uses streaming-telemetry-dial-out-top;
        } // END of subscriptions-container definition.
    } // END of streaming-telemetry-subscription-groups definition.
    grouping telemetry-cpu-monitoring {
        description
            "Configuration objects related to CPU Utilization";
        container cpu-monitoring {
            description
                "CPU utilization container";
            container config {
                when " /ipi-streaming-telemetry:telemetry-system/ipi-streaming-telemetry:vrfs/ipi-streaming-telemetry:vrf/ipi-streaming-telemetry:streaming-telemetry/ipi-streaming-telemetry:config/ipi-streaming-telemetry:feature-enabled ";
                presence "enable-cpu-limit";
                description
                    "Configuration data for cpu-utlization";
                uses telemetry-cpu-monitoring-config;
            } // END of config-container definition.
            container state {
                config false;
                description
                    "Operational data for cpu-utlization";
                uses telemetry-cpu-monitoring-config;
            } // END of state-container definition.
            uses telemetry-cpu-monitoring-sensor-group;
        } // END of cpu-monitoring-container definition.
    } // END of telemetry-cpu-monitoring definition.
    grouping telemetry-cpu-monitoring-config {
        description
            "Configuration objects related to CPU Utilization configs";
        leaf enable-cpu-limit  {
            type  ipi-streaming-telemetry-types:cml_telemetry_cpu_monitoring_t;
            mandatory true;
            description "Enable CPU monitoring for streaming telemetry";
        } // END of enable-cpu-limit definition.

        leaf suppress-threshold  {
            type  uint16 {
                 range "20..80"  {
                    description "20..80: Supported range 20 - 80";
                 }
            }
            default "40";
            description "Set CPU threshold for suppressing active streaming";
        } // END of suppress-threshold definition.

    } // END of telemetry-cpu-monitoring-config definition.
    grouping telemetry-cpu-monitoring-sensor-group {
        description
            "Configuration objects related to do not suppress sensor group";
        container no-suppress-grps {
            description
                "CPU utilization container";

            list no-suppress-grp {
                if-feature feature-list:HAVE_VRF;
                key "vrf-name sensor-group-id";
                description
                    "List of suppressed groups";
                leaf vrf-name  {
                    type  leafref {
                        path  "../config/vrf-name";
                    }
                    description "VRF Name associated with this instance";
                } // END of vrf-name definition.

                leaf sensor-group-id  {
                    type  leafref {
                        path  "../config/sensor-group-id";
                    }
                    description "Reference to the sensor group which is used in the profile";
                } // END of sensor-group-id definition.

                container config {
                    presence "CPU Utilization";
                    description
                        "Configuration data for cpu-utlization";
                    uses telemetry-cpu-monitoring-sensor-group-config;
                } // END of config-container definition.
                container state {
                    presence "CPU Utilization";
                    description
                        "State data for cpu-utlization";
                    uses telemetry-cpu-monitoring-sensor-group-config;
                } // END of state-container definition.
            } // End of no-suppress-grp-list
        } // END of no-suppress-grps-container definition.
    } // END of telemetry-cpu-monitoring-sensor-group definition.
    grouping telemetry-cpu-monitoring-sensor-group-config {
        description
            "Configuration objects related to do not suppress sensor group";
        leaf vrf-name  {
            if-feature feature-list:HAVE_VRF;
            type  leafref {
                path  "/telemetry-system/vrfs/vrf/vrf-name";
            }
            description "VRF Name associated with this instance";
        } // END of vrf-name definition.

        leaf sensor-group-id  {
            type  leafref {
                path  "/telemetry-system/vrfs/vrf/sensor-groups/sensor-group/sensor-group-id";
            }
            description "Reference to the sensor group which is used in the profile";
        } // END of sensor-group-id definition.

    } // END of telemetry-cpu-monitoring-sensor-group-config definition.

    grouping  telemetry-system-grouping {
    description
        "Top level container for device's streaming telemetry configurations";
    container telemetry-system {
        if-feature feature-list:HAVE_CMLD;
        if-feature feature-list:HAVE_TELEMETRY;
        description
            "Top level container for device's streaming telemetry configurations";
        uses streaming-telemetry-global-top;
        uses streaming-telemetry-subsystem-top;
        uses streaming-telemetry-debug;
        uses telemetry-cpu-monitoring;
    } // END of telemetry-system-container definition.
    } // END of telemetry-system-grouping definition.

    uses telemetry-system-grouping;

}
