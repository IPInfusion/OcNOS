/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-streaming-telemetry-types.yang
*
*/

module ipi-streaming-telemetry-types {

    yang-version 1.1;

    namespace   "http://www.ipinfusion.com/yang/ocnos/ipi-streaming-telemetry-types";

    prefix "ipi-streaming-telemetry-types";

    organization
        "IP Infusion Inc.";

    contact
        "Address: 3965 Freedom Circle, Suite 200, Santa Clara, CA 95054
         Phone: +1 408-400-1900
         E-mail: support@ipinfusion.com
         Web: http://www.ipinfusion.com/";

    description
        "Streaming Telemetry types";


    revision "2025-08-26" {
        description "Adding stream mode types";
        reference " 0.2.5.";
    }

    revision "2025-04-09" {
        description "Copy right year update";
        reference " 0.2.4.";
    }

    revision "2025-03-28" {
        description "CPU Monitoring feature added";
        reference " 0.2.3.";
    }

    revision "2024-05-23" {
        description "Added platform-type in data types";
        reference " 0.2.2.";
    }

    revision "2024-01-19" {
        description "Encoding Data type modified";
        reference " 0.2.1.";
    }

    revision "2023-11-08" {
        description "Inclusion of dialout data types";
        reference " 0.2.0.";
    }

    revision "2023-10-26" {
        description "Initial version of streaming telemetry data types";
        reference " 0.1.0.";
    }



    typedef  cml_gnmi_debug_severity_t {
        type enumeration {
            enum debug {
                value 0;
                description "DebugLevel logs a message at debug level";
            }
            enum info {
                value 1;
                description "InfoLevel logs a message at info level";
            }
            enum warning {
                value 2;
                description "WarnLevel logs a message at warning level";
            }
            enum error {
                value 3;
                description "ErrorLevel logs a message at error level";
            }
            enum fatal {
                value 4;
                description "FatalLevel logs a message  then calls os.Exit(1)";
            }
            enum panic {
                value 5;
                description "PanicLevel logs a message then panics";
            }
            enum d-panic {
                value 6;
                description "DPanicLevel logs at PanicLevel; otherwise it logs at ErrorLevel";
            }
        }
        description "type definition for CML_GNMI_DEBUG_SEVERITY_T";
    }

    typedef  cml_data_encode_t {
        type enumeration {
            enum json-ietf {
                value 0;
                description "JSON encoded based on IETF draft standard";
            }
            enum json {
                value 1;
                description "JSON encoding";
            }
            enum proto {
                value 2;
                description "Protocol buffers v3";
            }
        }
        description "type definition for CML_DATA_ENCODE_T";
    }

    typedef  cml_telemetry_protocol_t {
        type enumeration {
            enum gRPC {
                value 1;
                description "Telemetry stream is carried over via the gRPC framework";
            }
        }
        description "type definition for CML_TELEMETRY_PROTOCOL_T";
    }

    typedef  cml_streaming_types_t {
        type enumeration {
            enum STREAM {
                value 1;
                description "Stream mode";
            }
            enum POLL {
                value 2;
                description "Poll mode";
            }
        }
        description "type definition for CML_STREAMING_TYPES_T";
    }

    typedef  cml_stream_mode_types_t {
        type enumeration {
            enum SAMPLE {
                value 1;
                description "Stream with sample mode";
            }
            enum ON-CHANGE {
                value 2;
                description "Stream with on-change mode";
            }
        }
        description "type definition for CML_STREAM_MODE_TYPES_T";
    }

    typedef  cml_telemetry_status_t {
        type enumeration {
            enum IN-ACTIVE {
                value 0;
                description "Persistent subscription is in in-active state";
            }
            enum ACTIVE {
                value 1;
                description "Persistent subscription is in active state";
            }
        }
        description "type definition for CML_TELEMETRY_STATUS_T";
    }

    typedef  cml_telemetry_platform_type_t {
        type enumeration {
            enum Standard-range {
                value 0;
                description "Hardware is of type \"Standard range\"";
            }
            enum High-range {
                value 1;
                description "Hardware is of type  \"High range\"";
            }
        }
        description "type definition for CML_TELEMETRY_PLATFORM_TYPE_T";
    }

    typedef  cml_telemetry_cpu_monitoring_t {
        type enumeration {
            enum enable {
                value 0;
                description "Enable";
            }
            enum disable {
                value 1;
                description "Disabled";
            }
        }
        description "type definition for CML_TELEMETRY_CPU_MONITORING_T";
    }

}
