/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ipv6-router-adv.yang
*
*/

module ipi-ipv6-router-adv {

    yang-version 1.1;

    namespace   "http://www.ipinfusion.com/yang/ocnos/ipi-ipv6-router-adv";

    prefix "ipi-ipv6-router-adv";

    import cml-data-types {
        prefix cml-data-types;
        revision-date 2026-05-15;
    }

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "IPv6 Router Advertisement";


    revision "2025-09-04" {
        description "Removed EVPN_IRB_IF_MODE while configuring IRB interface";
        reference " 0.4.0.";
    }

    revision "2025-04-14" {
        description "Fix compilation warnings";
        reference " 0.3.3.";
    }

    revision "2024-10-03" {
        description "Added ipv6 nd suppress-ra,ra-interval and ra-lifetime CLI support for irb interface";
        reference " 0.3.2.";
    }

    revision "2022-12-01" {
        description "Updated when expressions";
        reference " 0.3.1.";
    }

    revision "2022-07-31" {
        description "Stop using inet:ipv4-prefix and inet:ipv6-prefix due to Cisco NSO iterop";
        reference " 0.3.0.";
    }

    revision "2022-07-30" {
        description "Updated when expressions in yang";
        reference " 0.2.6.";
    }

    revision "2022-06-29" {
        description "Adding auto-populate tag to router advertisment container";
        reference " 0.1.0.";
    }

    revision "2022-06-01" {
        description "Updated the yang file with feature";
        reference " 0.2.5.";
    }

    revision "2022-05-15" {
        description "Changing router advertisement default behaviour";
        reference " 0.1.0.";
    }

    revision "2021-09-29" {
        description "Changed max-ra-interval and min-ra-interval inside ra-interval container";
        reference " 0.2.4.";
    }

    revision "2021-09-21" {
        description "Add when cross-clauses in the leaves valid-lifetime and preferred-lifetime of object ipv6 prefix";
        reference " 0.2.3.";
    }

    revision "2021-09-04" {
        description "Removed grouping router-advertisement-top";
        reference " 0.2.2.";
    }

    revision "2021-09-01" {
        description "Changed base interface module's switchport attribute name and the datatype from bool to empty";
        reference " 0.2.1.";
    }

    revision "2021-06-23" {
        description "Restructured module in accordance with OpenConfig style";
        reference " 0.2.0.";
    }

    revision "2018-06-21" {
        description "Initial Version";
        reference " 0.1.0.";
    }

    grouping router-advertisement-interfaces-timers-prefixes-address-state {
        description
            "Grouping for Router Advertisement Interface Timers state";
        leaf random-interval  {
            type  uint32;
            units "seconds";
            description "The IPV6 Router Advertisement Random Interval";
        } // END of random-interval definition.

        leaf time-remaining  {
            type  uint32;
            units "seconds";
            description "The IPV6 Router Advertisement Remain Time";
        } // END of time-remaining definition.

    } // END of router-advertisement-interfaces-timers-prefixes-address-state definition.
    grouping router-advertisement-interfaces-prefixes-address-config {
        description
            "Grouping for Router Advertisement Interface Prefixes Address
                        configuration";
        leaf ipv6-address  {
            type  cml-data-types:cml_ipv6_prefix_t;
            description "The IPV6 Router Advertisement prefix address";
        } // END of ipv6-address definition.

        leaf valid-lifetime  {
            // when " ../preferred-lifetime ";
            type  uint32 {
                 range "0..4294967295"  {
                    description "0..4294967295: Supported range 0 - 4294967295";
                 }
            }
            units "seconds";
            default "2592000";
            description "The IPV6 Router Advertisement prefix address valid lifetime";
        } // END of valid-lifetime definition.

        leaf preferred-lifetime  {
            // when " ../valid-lifetime ";
            type  uint32 {
                 range "0..4294967295"  {
                    description "0..4294967295: Supported range 0 - 4294967295";
                 }
            }
            units "seconds";
            default "604800";
            description "The IPV6 Router Advertisement prefix address preferred lifetime";
        } // END of preferred-lifetime definition.

        leaf off-link  {
            // when " ../valid-lifetime ";
            type  empty;
            description "The IPV6 Router Advertisement prefix off-link flag";
        } // END of off-link definition.

        leaf no-auto-configuration  {
            // when " ../valid-lifetime ";
            type  empty;
            description "The IPV6 Router Advertisement prefix no auto-configuration flag";
        } // END of no-auto-configuration definition.

    } // END of router-advertisement-interfaces-prefixes-address-config definition.
    grouping router-advertisement-interfaces-prefixes-address-top {
        description
            "Grouping for Router Advertisement Interfaces Prefixes Address";

        list ipv6-prefix {
            key "ipv6-address";
            description
                "List of IPV6 Router Advertisement Interface Prefixes";
            leaf ipv6-address  {
                type  leafref {
                    path  "../config/ipv6-address";
                }
                description "The IPV6 Router Advertisement prefix address";
            } // END of ipv6-address definition.

            container config {
                description
                    "Configuration data for IPV6 Router Advertisement Interfaces Prefixes
                            Address";
                uses router-advertisement-interfaces-prefixes-address-config;
            } // END of config-container definition.
            container state {
                config false;
                description
                    "Operational state data for IPV6 Router Advertisement Interfaces
                            Prefixes Address";
                uses router-advertisement-interfaces-prefixes-address-config;
            } // END of state-container definition.
        } // End of ipv6-prefix-list
    } // END of router-advertisement-interfaces-prefixes-address-top definition.
    grouping router-advertisement-interfaces-prefixes-config {
        description
            "Grouping for Router Advertisement Interface Prefixes configuration";
        leaf off-link  {
            type  empty;
            description "The IPV6 Router Advertisement prefix off-link flag";
        } // END of off-link definition.

        leaf no-auto-configuration  {
            type  empty;
            description "The IPV6 Router Advertisement prefix no auto-configuration flag";
        } // END of no-auto-configuration definition.

        leaf valid-lifetime  {
            type  uint32 {
                 range "0..4294967295"  {
                    description "0..4294967295: Supported range 0 - 4294967295";
                 }
            }
            units "seconds";
            default "2592000";
            description "The IPV6 Router Advertisement prefix valid lifetime";
        } // END of valid-lifetime definition.

        leaf preferred-lifetime  {
            type  uint32 {
                 range "0..4294967295"  {
                    description "0..4294967295: Supported range 0 - 4294967295";
                 }
            }
            units "seconds";
            default "604800";
            description "The IPV6 Router Advertisement prefix preferred lifetime";
        } // END of preferred-lifetime definition.

    } // END of router-advertisement-interfaces-prefixes-config definition.
    grouping router-advertisement-interfaces-prefixes-top {
        description
            "Grouping for Router Advertisement Interfaces Prefixes";
        container ipv6-prefixes {
            description
                "IPV6 Router Advertisement Interface Prefixes";
            container config {
                description
                    "Configuration data for IPV6 Router Advertisement Interface Prefixes";
                uses router-advertisement-interfaces-prefixes-config;
            } // END of config-container definition.
            container state {
                config false;
                description
                    "Operational state data for IPV6 Router Advertisement Interface
                            Prefixes";
                uses router-advertisement-interfaces-prefixes-config;
            } // END of state-container definition.
            uses router-advertisement-interfaces-prefixes-address-top;
        } // END of ipv6-prefixes-container definition.
    } // END of router-advertisement-interfaces-prefixes-top definition.
    grouping router-advertisement-ra-interval-config {
        description
            "Grouping for IPV6 Router Advertisement Interface Interval Timers
                        configuration";
        leaf max-ra-interval  {
            type  uint32 {
                 range "4..1800"  {
                    description "4..1800: Supported range 4 - 1800";
                 }
            }
            units "seconds";
            mandatory true;
            description "Use this attribute to set maximum IPv6 router advertisement interval
                        (min-ra-interval must be no greater than 0.75*max-ra-interval)";
        } // END of max-ra-interval definition.

        leaf min-ra-interval  {
            type  uint32 {
                 range "3..1350"  {
                    description "3..1350: Supported range 3 - 1350";
                 }
            }
            units "seconds";
            mandatory true;
            description "Use this attribute to set minimum IPv6 router advertisement interval
                        (it must be no greater than 0.75*max-ra-interval)";
        } // END of min-ra-interval definition.

    } // END of router-advertisement-ra-interval-config definition.
    grouping router-advertisement-ra-interval-top {
        description
            "Grouping for IPV6 Router Advertisement Interface Interval Timers";
        container ra-interval {
            description
                "Container for IPV6 Router Advertisement Interface Interval Timers";
            container config {
                presence "yes";
                description
                    "Configuration data for IPV6 Router Advertisement Interface Interval
                            Timers";
                uses router-advertisement-ra-interval-config;
            } // END of config-container definition.
            container state {
                config false;
                description
                    "Operational state data for IPV6 Router Advertisement Interface
                            Interval Timers";
                uses router-advertisement-ra-interval-config;
            } // END of state-container definition.
        } // END of ra-interval-container definition.
    } // END of router-advertisement-ra-interval-top definition.
    grouping router-advertisement-interfaces-timers-config {
        description
            "Grouping for Router Advertisement Interface configuration";
        leaf reachable-time  {
            type  uint32 {
                 range "0..3600000"  {
                    description "0..3600000: Supported range 0 - 3600000";
                 }
            }
            units "miliseconds";
            default "0";
            description "Use this attribute to set advertised reachability time";
        } // END of reachable-time definition.

        leaf retransmission-time  {
            type  uint32 {
                 range "0..4294967295"  {
                    description "0..4294967295: Supported range 0 - 4294967295";
                 }
            }
            units "miliseconds";
            default "0";
            description "Use this attribute to set advertised retransmission timer";
        } // END of retransmission-time definition.

        leaf router-lifetime  {
            type  uint16 {
                 range "0..9000"  {
                    description "0..9000: Supported range 0 - 9000";
                 }
            }
            units "seconds";
            default "1800";
            description "Use this attribute to set IPv6 router advertisement lifetime";
        } // END of router-lifetime definition.

    } // END of router-advertisement-interfaces-timers-config definition.
    grouping router-advertisement-interfaces-timers-top {
        description
            "Grouping for Router Advertisement Interface configuration";
        container timers {
            description
                "IPV6 Router Advertisement Interface Timers";
            container config {
                description
                    "Configuration data for IPV6 Router Advertisement Interface Timers";
                uses router-advertisement-interfaces-timers-config;
            } // END of config-container definition.
            container state {
                config false;
                description
                    "Operational state data for IPV6 Router Advertisement Interface Timers";
                uses router-advertisement-interfaces-timers-config;
                uses router-advertisement-interfaces-timers-prefixes-address-state;
            } // END of state-container definition.
            uses router-advertisement-ra-interval-top;
        } // END of timers-container definition.
    } // END of router-advertisement-interfaces-timers-top definition.
    grouping router-advertisement-interface-config {
        description
            "Grouping for Router Advertisement Interface configuration";
        leaf name  {
            type  leafref {
                path  "/ipi-interface:interfaces/ipi-interface:interface/ipi-interface:name";
            }
            description "The IPV6 Router Advertisement interface name";
        } // END of name definition.

        leaf suppress-ra  {
            type  empty;
            description "Use this attribute to suppress IPv6 Router Advertisements";
        } // END of suppress-ra definition.

        leaf suppress-ra-mtu  {
            type  empty;
            description "Use this attribute to disable sending MTU in Router Advertisement
                        messages";
        } // END of suppress-ra-mtu definition.

        leaf managed-flag  {
            type  empty;
            description "Use this attribute to use DHCP for address config by host";
        } // END of managed-flag definition.

        leaf other-config-flag  {
            type  empty;
            description "Use this attribute to use DHCP for non-address config by host";
        } // END of other-config-flag definition.

        leaf current-hop-limit  {
            type  uint8 {
                 range "0..255"  {
                    description "0..255: Supported range 0 - 255";
                 }
            }
            default "64";
            description "Use this attribute to set advertised current hop limit";
        } // END of current-hop-limit definition.

        leaf link-mtu  {
            type  uint32 {
                 range "1280..65535"  {
                    description "1280..65535: Supported range 1280 - 65535";
                 }
            }
            default "1500";
            description "Use this attribute to set advertised link-mtu option";
        } // END of link-mtu definition.

        leaf dad-attempts  {
            type  uint16 {
                 range "0..600"  {
                    description "0..600: Supported range 0 - 600";
                 }
            }
            default "1";
            description "Use this attribute to set number of attempts for duplicate address
                        detection";
        } // END of dad-attempts definition.

    } // END of router-advertisement-interface-config definition.
    grouping router-advertisement-interfaces-top {
        description
            "Grouping for Router Advertisement Interfaces";
        container interfaces {
            description
                "IPV6 Router Advertisement Interfaces";

            list interface {
            // when " not(/ipi-interface:interfaces/ipi-interface:interface/ipi-interface:config/ipi-interface:enable-switchport) ";
                key "name";
                description
                    "List of IPV6 Router Advertisement Interfaces";
                leaf name  {
                    type  leafref {
                        path  "../config/name";
                    }
                    description "The IPV6 Router Advertisement interface name";
                } // END of name definition.

                container config {
                    description
                        "Configuration data for IPV6 Router Advertisement Interface";
                    uses router-advertisement-interface-config;
                } // END of config-container definition.
                container state {
                    config false;
                    description
                        "Operational state data for IPV6 Router Advertisement Interface";
                    uses router-advertisement-interface-config;
                } // END of state-container definition.
                uses router-advertisement-interfaces-prefixes-top;
                uses router-advertisement-interfaces-timers-top;
            } // End of interface-list
        } // END of interfaces-container definition.
    } // END of router-advertisement-interfaces-top definition.

    grouping  router-advertisement-grouping {
    description
        "IPV6 Router Advertisement";
    container router-advertisement {
        if-feature feature-list:HAVE_RTADV;
        description
            "IPV6 Router Advertisement";
        uses router-advertisement-interfaces-top;
    } // END of router-advertisement-container definition.
    } // END of router-advertisement-grouping definition.

    uses router-advertisement-grouping;

}
