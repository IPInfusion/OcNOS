/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-cfm-vxlan-oam.yang
*
*/

submodule ipi-cfm-vxlan-oam {

    yang-version 1.1;

    belongs-to  ipi-cfm { prefix ipi-cfm; }

    import feature-list {
        prefix feature-list;
        revision-date 2026-09-15;
    }

    import ietf-inet-types {
        prefix inet;
        revision-date 2013-07-15;
    }

    import ietf-yang-types {
        prefix yang;
        revision-date 2013-07-15;
    }

    import ipi-cfm-data-types {
        prefix ipi-cfm-data-types;
        revision-date 2025-08-22;
    }

    organization
        "IP Infusion Inc.";

    contact
        "Address: 3965 Freedom Circle, Suite 200, Santa Clara, CA 95054
         Phone: +1 408-400-1900
         E-mail: support@ipinfusion.com
         Web: http://www.ipinfusion.com/";

    description
        "Data model for IPI CFM VXLAN OAM Configuration and Operational state";


    revision "2025-08-22" {
        description " Change of name of HAVE_NVO3_OAM flag ";
        reference " 0.1.0.";
    }

    revision "2024-03-22" {
        description " The CLI generation was modified for vxlan-oam (spine) ";
        reference " 0.0.7.";
    }

    revision "2024-03-13" {
        description "Add UNSET_FIRST flag to 'enable' attribute";
        reference " 0.0.6.";
    }

    revision "2022-09-27" {
        description "Removed unnecessary attributes from BaseMode operational data";
        reference " 0.0.5.";
    }

    revision "2022-09-25" {
        description "Added support for NVO3 OAM CCM status";
        reference " 0.0.4.";
    }

    revision "2022-09-20" {
        description "Added support for NVO3 OAM notifications";
        reference " 0.0.3.";
    }

    revision "2022-09-19" {
        description "Added support to BaseMode operational data";
        reference " 0.0.2.";
    }

    revision "2022-08-22" {
        description "Added suport for NVO3 OAM";
        reference " 0.0.1.";
    }

    grouping cfm-nvo3-oam-evpn-ccm-state {
        description
            "Grouping for NVO3 OAM EVPN CCMs operational state data";
        leaf remote-mep-id  {
            type  uint32;
            description "This attribute represents the CCM remote mep-id";
        } // END of remote-mep-id definition.

        leaf last-good-flow-id  {
            type  uint32;
            description "This attribute represents the CCM flow-id before flap";
        } // END of last-good-flow-id definition.

        leaf last-recovered-flow-id  {
            type  uint32;
            description "This attribute represents the CCM flow-id after flap";
        } // END of last-recovered-flow-id definition.

        leaf first-good-sequence-number  {
            type  uint32;
            description "This attribute represents the first good sequence-number of the CCM";
        } // END of first-good-sequence-number definition.

        leaf last-good-sequence-number  {
            type  uint32;
            description "This attribute represents the last good sequence-number of the CCM";
        } // END of last-good-sequence-number definition.

        leaf flow-state  {
            type  ipi-cfm-data-types:cfm_nvo_oam_ccm_flow_status_t;
            description "This attribute represents the current flow state";
        } // END of flow-state definition.

        leaf last-flapped-time  {
            type  yang:date-and-time {
                pattern "\\d{4}-\\d{2}-\\d{2}T\\d{2}:\\d{2}:\\d{2}(\\.\\d+)?(Z|[\\+\\-]\\d{2}:\\d{2})";
                }
                description "This attribute represents the time of the last down transition";
            } // END of last-flapped-time definition.

            leaf last-recovered-time  {
                type  yang:date-and-time {
                    pattern "\\d{4}-\\d{2}-\\d{2}T\\d{2}:\\d{2}:\\d{2}(\\.\\d+)?(Z|[\\+\\-]\\d{2}:\\d{2})";
                    }
                    description "This attribute represents the time of the last up transition";
                } // END of last-recovered-time definition.

    } // END of cfm-nvo3-oam-evpn-ccm-state definition.
    grouping cfm-nvo3-oam-global-config {
        description
            "VxLAN-specific global configuration";
        leaf enable  {
            type  empty;
            description "Enable the CFM-over-VxLAN feature";
        } // END of enable definition.

        leaf mode  {
            // when " ipi-cfm-vxlan-oam:nvo3-oam/config/enable ";
            type  ipi-cfm-data-types:cfm_nvo3_vxlan_oam_mode_t;
            description "Use this attribute to set the VxLAN OAM mode of operation";
        } // END of mode definition.

    } // END of cfm-nvo3-oam-global-config definition.
    grouping maintenance-domain-operational-state {
        description
            "Grouping for BaseMode MD operational state data";
        leaf type  {
            type  ipi-cfm-data-types:cfm_md_type_t;
            description "Type discriminator for the value union described in the 'md-name' leaf";
        } // END of type definition.

        leaf level  {
            type  uint8;
            description "Integer identifying the Maintenance Domain Level (MD Level)";
        } // END of level definition.

        leaf mip-creation  {
            type  ipi-cfm-data-types:cfm_mip_creation_mode_t;
            description "This parameter indicates whether the management entity can create MIPs
                        for this MD at this level";
        } // END of mip-creation definition.

    } // END of maintenance-domain-operational-state definition.
    grouping maintenance-association-operational-state {
        description
            "Grouping for BaseMode MA operational state data";
        leaf type  {
            type  ipi-cfm-data-types:cfm_ma_type_t;
            description "Name type discriminator for the 'ma-name' leaf";
        } // END of type definition.

        leaf vnid  {
            type  uint32;
            description "This attribute indicates the EVPN id of the MA";
        } // END of vnid definition.

        leaf vlan-id  {
            type  uint16;
            description "The VID monitored by this MA";
        } // END of vlan-id definition.

    } // END of maintenance-association-operational-state definition.
    grouping maintenance-end-point-operational-state {
        description
            "Grouping for BaseMode MEP operational state data";
        leaf direction  {
            type  ipi-cfm-data-types:cfm_mep_direction_t;
            description "A value indicating the direction in which the MEP faces on the
                        interface";
        } // END of direction definition.

        leaf administrative-state  {
            type  ipi-cfm-data-types:cfm_mep_state_t;
            description "The administrative state of the MEP";
        } // END of administrative-state definition.

        leaf remote-vtep-ip  {
            type  inet:ipv4-address;
            description "This attribute indicates the remote VxLAN Tunnel Endpoint IP address";
        } // END of remote-vtep-ip definition.

    } // END of maintenance-end-point-operational-state definition.

    grouping  md-nvo-operational-grouping {
    description
        "Container for BaseMode MD operational data";
    container md-nvo-operational {
        if-feature feature-list:HAVE_CFM;
        if-feature feature-list:HAVE_ONMD;
        if-feature feature-list:HAVE_VXLAN_OAM;
        config false;
        description
            "Container for BaseMode MD operational data";
        container state {
            config false;
            description
                "Operational state data for BaseMode MD";
            uses maintenance-domain-operational-state;
        } // END of state-container definition.
    } // END of md-nvo-operational-container definition.
    } // END of md-nvo-operational-grouping definition.

    grouping  ma-nvo-operational-grouping {
    description
        "Container for BaseMode MA operational data";
    container ma-nvo-operational {
        if-feature feature-list:HAVE_CFM;
        if-feature feature-list:HAVE_ONMD;
        if-feature feature-list:HAVE_VXLAN_OAM;
        config false;
        description
            "Container for BaseMode MA operational data";
        container state {
            config false;
            description
                "Operational state data for BaseMode MA";
            uses maintenance-association-operational-state;
        } // END of state-container definition.
    } // END of ma-nvo-operational-container definition.
    } // END of ma-nvo-operational-grouping definition.

    grouping  mep-nvo-operational-grouping {
    description
        "Container for BaseMode MEP operational data";
    container mep-nvo-operational {
        if-feature feature-list:HAVE_CFM;
        if-feature feature-list:HAVE_ONMD;
        if-feature feature-list:HAVE_VXLAN_OAM;
        config false;
        description
            "Container for BaseMode MEP operational data";
        container state {
            config false;
            description
                "Operational state data for BaseMode MEP";
            uses maintenance-end-point-operational-state;
        } // END of state-container definition.
    } // END of mep-nvo-operational-container definition.
    } // END of mep-nvo-operational-grouping definition.

    grouping  nvo3-oam-grouping {
    description
        "NVO3 OAM global options";
    container nvo3-oam {
        if-feature feature-list:HAVE_CFM;
        if-feature feature-list:HAVE_ONMD;
        if-feature feature-list:HAVE_VXLAN_OAM;
        description
            "NVO3 OAM global options";
        container config {
            description
                "Configuration data for NVO3 OAM global";
            uses cfm-nvo3-oam-global-config;
        } // END of config-container definition.
        container state {
            config false;
            description
                "Operational state data for NVO3 OAM global";
            uses cfm-nvo3-oam-global-config;
        } // END of state-container definition.
    } // END of nvo3-oam-container definition.
    } // END of nvo3-oam-grouping definition.

    grouping  evpn-ccms-grouping {
    description
        "NVO3 OAM EVPN CCMs runtime data";
    container evpn-ccms {
        if-feature feature-list:HAVE_CFM;
        if-feature feature-list:HAVE_ONMD;
        if-feature feature-list:HAVE_VXLAN_OAM;
        config false;
        description
            "NVO3 OAM EVPN CCMs runtime data";

        list evpn-ccm {
            key "remote-mep-id";
            config false;
            description
                "List of EVPN CCM instances";
            leaf remote-mep-id  {
                type  leafref {
                    path  "../state/remote-mep-id";
                }
                description "This attribute represents the CCM remote mep-id";
            } // END of remote-mep-id definition.

            container state {
                config false;
                description
                    "Operational state data for NVO3 OAM EVPN CCMs";
                uses cfm-nvo3-oam-evpn-ccm-state;
            } // END of state-container definition.
        } // End of evpn-ccm-list
    } // END of evpn-ccms-container definition.
    } // END of evpn-ccms-grouping definition.


}
