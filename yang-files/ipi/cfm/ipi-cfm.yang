/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-cfm.yang
*
*/

module ipi-cfm {

    yang-version 1.1;

    namespace   "http://www.ipinfusion.com/yang/ocnos/ipi-cfm";

    prefix "ipi-cfm";

    import ietf-yang-types {
        prefix yang;
        revision-date 2013-07-15;
    }

    import ipi-cfm-data-types {
        prefix ipi-cfm-data-types;
        revision-date 2025-08-22;
    }

    import cml-data-types {
        prefix cml-data-types;
        revision-date 2026-05-15;
    }

    import feature-list {
        prefix feature-list;
        revision-date 2026-09-15;
    }

    include ipi-cfm-common { revision-date 2026-02-16;}
    include ipi-cfm-vxlan-oam { revision-date 2025-08-22;}
    include ipi-cfm-y1731 { revision-date 2026-03-27;}
    organization
        "IP Infusion Inc.";

    contact
        "Address: 3965 Freedom Circle, Suite 200, Santa Clara, CA 95054
         Phone: +1 408-400-1900
         E-mail: support@ipinfusion.com
         Web: http://www.ipinfusion.com/";

    description
        "Data model for IPI CFM Configuration and Operational state";


    revision "2026-03-27" {
        description "Enabled loss measurement message period 10ms";
        reference " 0.11.1.";
    }

    revision "2026-03-04" {
        description "Enabled loss measurement message period 3ms,1min and 10min";
        reference " 0.11.0.";
    }

    revision "2026-02-16" {
        description "Adding missing near/far-end frame-loss-ratio attributes";
        reference " 0.10.7.";
    }

    revision "2025-12-09" {
        description "Adding near/far end loss ratio attributes";
        reference " 0.10.6.";
    }

    revision "2025-08-22" {
        description "Change of HAVE_NVO3_OAM flag name";
        reference " 0.10.5.";
    }

    revision "2025-07-06" {
        description "Removing CRC options for pattern-type attributes";
        reference " 0.10.4.";
    }

    revision "2025-07-03" {
        description "Updated CIR and EIR bandwidth limitations";
        reference " 0.10.3.";
    }

    revision "2025-05-29" {
        description "Correting max length value for md-name attribute";
        reference " 0.10.2.";
    }

    revision "2025-05-19" {
        description "Correting max length value for md-name attribute";
        reference " 0.10.1.";
    }

    revision "2024-11-06" {
        description "Changing datatype to the frame-size attribute and added CIR and EIR Attributes";
        reference " 0.10.0.";
    }

    revision "2024-07-26" {
        description "Added when tag for the attribute vlan-id";
        reference " 0.9.6.";
    }

    revision "2024-06-06" {
        description "Masking LMM option for Marvell platform";
        reference " 0.9.5.";
    }

    revision "2024-06-03" {
        description " Mask EVPN options for Marvell platform";
        reference " 0.9.4.";
    }

    revision "2024-05-15" {
        description " Added support for configuring RMEP under MEP";
        reference " 0.9.3.";
    }

    revision "2024-05-14" {
        description "Added when tag for vlan-id";
        reference " 0.9.2.";
    }

    revision "2024-05-12" {
        description "Enable rmep auto-discovery CLI for Marvell";
        reference " 0.9.1.";
    }

    revision "2024-05-08" {
        description " Added MEP vlan cli support";
        reference " 0.9.0.";
    }

    revision "2024-05-02" {
        description "Removed the include-input-for-unset for enable-lm-responder";
        reference " 0.8.8.";
    }

    revision "2024-03-22" {
        description " The CLI generation was modified for vxlan-oam (spine) in ipi-cfm-nvo3-oam";
        reference " 0.8.7.";
    }

    revision "2024-03-19" {
        description "Adding missing attributes for ETH-CSF";
        reference " 0.8.6.";
    }

    revision "2024-03-13" {
        description "Add UNSET_FIRST flag to 'enable' attribute";
        reference " 0.8.5.";
    }

    revision "2024-02-20" {
        description "Blocking MIP creation static CLI, since it is NVO3 feature ";
        reference " 0.8.4.";
    }

    revision "2024-01-17" {
        description "adaptive bandwidth disable cli implementation";
        reference " 0.8.3.";
    }

    revision "2023-10-25" {
        description "Enable ETH-TST, LCK, AIS, CSF and BN CLIs for Marvell platform";
        reference " 0.9.5.";
    }

    revision "2023-10-20" {
        description "removed ethernet and cfm which is added twice in the cliprependstr";
        reference " 0.9.6.";
    }

    revision "2023-09-21" {
        description "Modified MA_NAME Range";
        reference " 0.9.4.";
    }

    revision "2023-08-11" {
        description "cfm dependency checking with add vlan to port";
        reference " 0.9.3.";
    }

    revision "2023-07-21" {
        description "cfm disable for q2 ipbase";
        reference " 0.9.2.";
    }

    revision "2023-07-13" {
        description "Removed if-not-feature for CFM msg intrvals of 1-min and 10-mins";
        reference " 0.9.1.";
    }

    revision "2023-06-05" {
        description "Removed when tag for vlan-id attribute";
        reference " 0.9.0.";
    }

    revision "2023-05-16" {
        description "Removed if-feature for LB, LT state container";
        reference " 0.8.12.";
    }

    revision "2023-04-25" {
        description "Removed delete-on-no-child on when tag for maintenance-end-point objectlist to clean the DB from maintenance-end-points";
        reference " 0.8.11.";
    }

    revision "2023-03-24" {
        description "Removed if-feature for clear ethernet cfm statistics RPC";
        reference " 0.8.10.";
    }

    revision "2023-03-06" {
        description "Added When tag for no-debug-all command";
        reference " 0.8.9.";
    }

    revision "2023-03-02" {
        description "Added if-not-feature for CFM msg intrvals of 1-min and 10-mins";
        reference " 0.8.7.";
    }

    revision "2023-03-01" {
        description "Enabling clear CFM MEP statistics CLI for a new SKU";
        reference " 0.8.8.";
    }

    revision "2023-02-28" {
        description "Adding proper flag for objectAction";
        reference " 0.8.6.";
    }

    revision "2023-02-23" {
        description "Enabling cfm clear stats CLI for a new SKU";
        reference " 0.8.4.";
    }

    revision "2023-02-22" {
        description "Added all option for debug commands on cfm";
        reference " 0.8.3.";
    }

    revision "2023-02-14" {
        description "Enabling clear CFM statistics CLI for a new SKU";
        reference " 0.8.5.";
    }

    revision "2023-02-13" {
        description "Added if-feature for LM, DM, Abort and Clear RPCs";
        reference " 0.8.2.";
    }

    revision "2023-02-07" {
        description "Added support for clear commands for TST and LCK";
        reference " 0.8.0.";
    }

    revision "2023-01-17" {
        description "Adressed cli-prependstr not used warnings";
        reference " 0.8.1.";
    }

    revision "2023-01-11" {
        description "Reverting if-feature for LM, DM, Abort and Clear RPCs";
        reference " 0.7.1.";
    }

    revision "2023-01-06" {
        description "Added if-feature for LM, DM, Abort and Clear RPCs";
        reference " 0.7.0.";
    }

    revision "2022-10-14" {
        description "Added if-feature for evpn-id, vpws-vc-name attribute and evpn-id, vpws-vc-name cli command";
        reference " 0.6.18.";
    }

    revision "2022-09-30" {
        description "Import cml-data-types used by notifications";
        reference " 0.6.17.";
    }

    revision "2022-09-27" {
        description "Updated NVO3 OAM submodule";
        reference " 0.6.16.";
    }

    revision "2022-09-25" {
        description "Added support for NVO3 OAM CCM status";
        reference " 0.6.15.";
    }

    revision "2022-09-23" {
        description "Added when expression for maintenance-end-point config container and objectlist to clean the DB from maintenance-end-points";
        reference " 0.6.14.";
    }

    revision "2022-09-22" {
        description "Added support for NVO3 OAM notifications";
        reference " 0.6.13.";
    }

    revision "2022-09-21" {
        description "Added support to BaseMode operational data";
        reference " 0.6.12.";
    }

    revision "2022-09-20" {
        description "Corrected suppress-unset-cli flag to suppress-cli for bridge-id attribute under MA";
        reference " 0.6.11.";
    }

    revision "2022-09-16" {
        description "Added when expression to clean the DB from ma-name attribute";
        reference " 0.6.10.";
    }

    revision "2022-09-13" {
        description "Added if-feature for evpn-id attribute and vpws-vc-name attribute";
        reference " 0.6.9.";
    }

    revision "2022-09-06" {
        description "Added when expression to clean the DB from maintenance-end-points";
        reference " 0.6.8.";
    }

    revision "2022-08-25" {
        description "Added cache-enable attribute under config container and added cli command for ethernet cfm traceroute cache";
        reference " 0.6.7.";
    }

    revision "2022-08-22" {
        description "Added support for NVO3 OAM";
        reference " 0.6.6.";
    }

    revision "2022-08-16" {
        description "Removed l2-bridge container and removed bridge-id attribute from traceroute cache";
        reference " 0.6.5.";
    }

    revision "2022-08-10" {
        description "Debug hierarchy change";
        reference " 0.6.2.";
    }

    revision "2022-08-05" {
        description "Removed bridge-id attribute from LB, LT, LM, DM, TST, Clear and Abort RPCs";
        reference " 0.6.3.";
    }

    revision "2022-08-01" {
        description "Removed bridge-id attribute under MD, removed all MPLS CLIs from CFM and LB, LT, LM, DM, Clear and Abort RPCs and removed optional attribute from link-level-ma";
        reference " 0.6.4.";
    }

    revision "2022-07-30" {
        description "Updated when expressions in yang";
        reference " 0.6.1.";
    }

    revision "2022-07-26" {
        description "Added optional attribute bridge-id to MA, made mip-creation attr optional for MD and MA, added support for evpn-id and vpws-vc-name under MA and support for remote-evpn-id and remote-vpws-vc-name under MEP";
        reference " 0.6.0.";
    }

    revision "2022-07-19" {
        description "Update if-feature for Notification";
        reference " 0.5.7.";
    }

    revision "2022-06-01" {
        description "Updated the yang file with feature";
        reference " 0.5.6.";
    }

    revision "2022-05-31" {
        description "Added support for CFM msg intrvals of 1-min and 10-mins";
        reference " 0.5.6.";
    }

    revision "2022-05-26" {
        description "Added support to make rmep parameter for ETH-LM to take RMEPID or RMAC as input as per MEF";
        reference " 0.5.5.";
    }

    revision "2022-05-21" {
        description "Corrected grouping name for cfm-mep-common-state and cfm-mep-common-config";
        reference " 0.5.4.";
    }

    revision "2022-05-18" {
        description "Added bitmap check flag for inner-vlan-id";
        reference " 0.5.3.";
    }

    revision "2022-05-11" {
        description "Added optional attribute inner-vlan-id to MA";
        reference " 0.5.2.";
    }

    revision "2022-05-09" {
        description "Updation of MPLS flags for CFM and debug CFM CLI";
        reference " 0.5.1.";
    }

    revision "2022-04-29" {
        description "Restructure CFM and Y.1731 over MPLS components to OpenConfig style and enable NETCONF support";
        reference " 0.5.0.";
    }

    revision "2022-04-25" {
        description "Enabled Y1731 LM DM support for non-hardware offload";
        reference " 0.4.0.";
    }

    revision "2022-04-21" {
        description "Made ma-name a mandatory parameter for ping, traceroute, LM and DM CLIs";
        reference " 0.4.9.";
    }

    revision "2022-04-15" {
        description "Addition of GetAPI for CSF module";
        reference " 0.4.8.";
    }

    revision "2022-04-14" {
        description "Removed 're-routing' CLI from MEP mode and added in interface mode";
        reference " 0.4.7.";
    }

    revision "2022-04-13" {
        description "Removed bridge and vlan dependency from LB, LT, LM and DM RPCs";
        reference " 0.4.5.";
    }

    revision "2022-04-12" {
        description "Removed bridge and vlan dependency from TST,Clear and Abort RPCs for LM and DM";
        reference " 0.4.6.";
    }

    revision "2022-04-10" {
        description "Removed ETH-BN hold-off-timer attribute";
        reference " 0.4.4.";
    }

    revision "2022-04-09" {
        description "elapsed-time state attribute for ethernet-test-signal container is changed from uint8 to uint32";
        reference " 0.4.3.";
    }

    revision "2022-04-08" {
        description "Addition of new ETH-BN CLIs and NETCONF support";
        reference " 0.4.2.";
    }

    revision "2022-04-07" {
        description "Added support for ETH-BN peer port ID";
        reference " 0.4.1.";
    }

    revision "2022-04-05" {
        description "Added support for Client Signal Fail (CSF) feature";
        reference " 0.4.0.";
    }

    revision "2022-04-04" {
        description "Added if-feature in mo_ipi-cfm-common.xml";
        reference " 0.3.0.";
    }

    revision "2022-03-22" {
        description "Addition of new ETH-BN bw-margin and min-transmit-threshold CLIs";
        reference " 0.2.2.";
    }

    revision "2022-03-17" {
        description "Added transaction-id support to linktrace RPC";
        reference " 0.2.1.";
    }

    revision "2022-03-10" {
        description "Restructure LB, LT and CFM Y.1731 L2 bridge dependent CLIs to OpenConfig style";
        reference " 0.2.0.";
    }

    revision "2021-12-20" {
        description "Made bridge-id attribute optional for MD object to remove bridge dependency for L2/VLAN CFM";
        reference " 0.1.2.";
    }

    revision "2021-12-15" {
        description "Removed skip-yang as FW dependency is resolved";
        reference " 0.1.1.";
    }

    revision "2021-12-09" {
        description "Initial Version";
        reference " 0.1.0.";
    }

    grouping cfm-debug-top {
        description
            "Grouping for Global CFM attributes";
        container debug {
            description
                "Enclosing container for CFM debugs";
            container config {
                description
                    "Configuration data for CFM MEP Continuity Check Message";
                uses cfm-debug-parameters-config;
            } // END of config-container definition.
            container state {
                config false;
                description
                    "Operational data for CFM MEP Continuity Check Message";
                uses cfm-debug-parameters-config;
                uses cfm-terminal-debug-state;
            } // END of state-container definition.
        } // END of debug-container definition.
    } // END of cfm-debug-top definition.
    grouping cfm-debug-parameters-config {
        description
            "Grouping for Global CFM attributes";
        leaf options  {
            type  ipi-cfm-data-types:cfm_debug_t;
            description "This attribute enables debugging for CFM";
        } // END of options definition.

    } // END of cfm-debug-parameters-config definition.
    grouping cfm-terminal-debug-state {
        description
            "Grouping for CFM terminal Debug attributes";
        leaf terminal-debug-status  {
            type  ipi-cfm-data-types:cfm_debug_t;
            description "This attribute describes the CFM terminal debug status";
        } // END of terminal-debug-status definition.

    } // END of cfm-terminal-debug-state definition.
    grouping cfm-mep-ccm-top {
        description
            "Grouping for CFM MEP Continuity Check Messages";
        container continuity-check {
            description
                "Enclosing container for the list of CFM MEP Continuity Check Messages";
            container config {
                description
                    "Configuration data for CFM MEP Continuity Check Message";
                uses cfm-mep-ccm-config;
            } // END of config-container definition.
            container state {
                config false;
                description
                    "Operational data for CFM MEP Continuity Check Message";
                uses cfm-mep-ccm-config;
                uses cfm-mep-ccm-state;
            } // END of state-container definition.
            uses cfm-remote-meps-top;
            uses evpn-ccms-grouping;
        } // END of continuity-check-container definition.
    } // END of cfm-mep-ccm-top definition.
    grouping cfm-meps-top {
        description
            "Grouping for CFM Maintenence End Points";
        container maintenance-end-points {
            description
                "Enclosing container for the list of Maintenence End Points";

            list maintenance-end-point {
                key "mep-id";
                description
                    "List of Maintenence End Points";
                leaf mep-id  {
                    type  leafref {
                        path  "../config/mep-id";
                    }
                    description "Integer that is unique among all the MEPs in the same MA. Other
                                definition is: a small integer, unique over a given Maintenance
                                Association, identifying a specific Maintenance association End Point";
                } // END of mep-id definition.

                container config {
                    description
                        "Configuration data for Maintenence End Point";
                    uses cfm-mep-common-config;
                    uses cfm-mep-bandwidth-shaping-config;
                    uses cfm-mep-l2-bridge-config;
                    uses cfm-mep-mpls-service-config;
                    uses cfm-mep-nvo3-oam-config;
                } // END of config-container definition.
                container state {
                    config false;
                    description
                        "Operational data for Maintenence End Point";
                    uses cfm-mep-common-config;
                    uses cfm-mep-l2-bridge-config;
                    uses cfm-mep-mpls-service-config;
                    uses cfm-mep-common-state;
                    uses cfm-mep-bandwidth-shaping-config;
                    uses cfm-mep-nvo3-oam-config;
                } // END of state-container definition.
                uses cfm-mep-ccm-top;
                uses cfm-loopback-last-result-top;
                uses cfm-linktrace-database-state;
                uses mep-nvo-operational-grouping;
                uses ethernet-bandwidth-notification-grouping;
                uses ethernet-client-signal-fail-grouping;
                uses ethernet-locked-signal-grouping;
                uses ethernet-alarm-indication-signal-grouping;
                uses y1731-responders-grouping;
                uses ethernet-test-signal-grouping;
                uses ethernet-loss-measurements-grouping;
                uses ethernet-delay-measurements-grouping;
            } // End of maintenance-end-point-list
        } // END of maintenance-end-points-container definition.
    } // END of cfm-meps-top definition.
    grouping cfm-mas-top {
        description
            "Grouping for CFM Maintenence Assosiations";
        container maintenance-associations {
            description
                "Enclosing container for the list of Maintenence associations";

            list maintenance-association {
                key "ma-name";
                description
                    "List of Maintenence associations";
                leaf ma-name  {
                    type  leafref {
                        path  "../config/ma-name";
                    }
                    description "The value union for the Maintenance Association Name.";
                } // END of ma-name definition.

                container config {
                    description
                        "Configuration data for Maintenence association";
                    uses cfm-ma-l2-bridge-config;
                    uses cfm-ma-mpls-service-config;
                    uses cfm-ma-common-config;
                } // END of config-container definition.
                container state {
                    config false;
                    description
                        "Operational data for Maintenence Association";
                    uses cfm-ma-l2-bridge-config;
                    uses cfm-ma-mpls-service-config;
                    uses cfm-ma-common-config;
                } // END of state-container definition.
                uses cfm-meps-top;
                uses cfm-ma-default-mips-top;
                uses ma-nvo-operational-grouping;
            } // End of maintenance-association-list
        } // END of maintenance-associations-container definition.
    } // END of cfm-mas-top definition.
    grouping cfm-mds-top {
        description
            "Grouping for CFM Maintenence Domains";
        container maintenance-domains {
            description
                "Enclosing container for the list of Maintenence Domains";

            list maintenance-domain {
                key "md-name";
                description
                    "List of Maintenence Domains";
                leaf md-name  {
                    type  leafref {
                        path  "../config/md-name";
                    }
                    description "A unique identifier of a Maintenance Domain";
                } // END of md-name definition.

                container config {
                    description
                        "Configuration data for Maintenence Domain";
                    uses cfm-md-common-config;
                } // END of config-container definition.
                container state {
                    config false;
                    description
                        "Operational data for Maintenence Domain";
                    uses cfm-md-common-config;
                } // END of state-container definition.
                uses cfm-mas-top;
                uses md-nvo-operational-grouping;
            } // End of maintenance-domain-list
        } // END of maintenance-domains-container definition.
    } // END of cfm-mds-top definition.
    grouping cfm-global-top {
        description
            "Grouping for CFM Global Configurations";
        container global {
            description
                "Global CFM container";
            uses cfm-loopback-top;
            uses cfm-linktrace-top;
            uses nvo3-oam-grouping;
        } // END of global-container definition.
    } // END of cfm-global-top definition.

    grouping  cfm-grouping {
    description
        "Top level container for Ethernet Connectivity Fault Management
                Protocol (CFM)";
    container cfm {
        if-feature feature-list:HAVE_CFM;
        if-feature feature-list:HAVE_ONMD;
        description
            "Top level container for Ethernet Connectivity Fault Management
                    Protocol (CFM)";
        uses cfm-global-top;
        uses cfm-debug-top;
        uses cfm-mds-top;
        uses ethernet-test-signal-profiles-grouping;
        uses ethernet-loss-measurement-profiles-grouping;
        uses ethernet-delay-measurement-profiles-grouping;
    } // END of cfm-container definition.
    } // END of cfm-grouping definition.

    uses cfm-grouping;

    rpc cfm-l2-abort-eth-test-signal {
        if-feature feature-list:Y1731_HW_OFFLOAD;
        if-feature feature-list:HAVE_CFM;
        if-feature feature-list:HAVE_ONMD;
        if-feature feature-list:HAVE_CFM_Y1731;
        description "RPC to abort an ongoing ETH-Test Signal session";
        input  {
            leaf mep-id  {
                type uint16 {
                    range "1..8191";
                }
                mandatory true;
                description "The MEP ID of the source MEP";
            }
            leaf ma-name  {
                type string {
                    length "1..6";
                }
                mandatory true;
                description "A unique identifier of a Maintenance Association";
            }
            leaf domain-name  {
                type string;
                mandatory true;
                description "A unique identifier of a Maintenance Domain";
            }
        }
    }

    rpc cfm-l2-eth-test-on-demand-start-relative-stop-relative {
        if-feature feature-list:Y1731_HW_OFFLOAD;
        if-feature feature-list:HAVE_CFM;
        if-feature feature-list:HAVE_ONMD;
        if-feature feature-list:HAVE_CFM_Y1731;
        description "RPC to start on-demand ETH-TST session with start time as relative and
                    stop time as relative";
        input  {
            leaf test-target  {
                type ipi-cfm-data-types:cfm_rmep_type_t;
                mandatory true;
                description "Unicast MAC address or MEP ID of the peer MEP for which ETH-Test is
                            intended";
            }
            leaf mep-id  {
                type uint16 {
                    range "1..8191";
                }
                mandatory true;
                description "The MEP ID of the source MEP";
            }
            leaf ma-name  {
                type string {
                    length "1..6";
                }
                mandatory true;
                description "A unique identifier of a Maintenance Association";
            }
            leaf md-name  {
                type string {
                    length "1..43";
                }
                mandatory true;
                description "A unique identifier of a Maintenance Domain";
            }
            leaf profile-name  {
                type string {
                    length "1..64";

                    pattern "[a-zA-Z0-9_-]*";
                }
                mandatory true;
                description "This attribute contains the profile name for ETH-TST session";
            }
            leaf start-time-type  {
                type ipi-cfm-data-types:cfm_relative_time_t;
                mandatory true;
                description "This attribute defines the session start time";
            }
            leaf start-time  {
                type uint32 {
                    range "0..4294967295";
                }
                mandatory true;
                description "The time when the session is supposed to be started";
            }
            leaf stop-time-type  {
                type ipi-cfm-data-types:cfm_relative_time_t;
                mandatory true;
                description "This attribute defines the session stop time";
            }
            leaf stop-time  {
                type uint32 {
                    range "0..4294967295";
                }
                mandatory true;
                description "This attribute defines the session stop time";
            }
        }
    }

    rpc cfm-l2-eth-test-on-demand-start-absolute-stop-relative {
        if-feature feature-list:Y1731_HW_OFFLOAD;
        if-feature feature-list:HAVE_CFM;
        if-feature feature-list:HAVE_ONMD;
        if-feature feature-list:HAVE_CFM_Y1731;
        description "RPC to start on-demand ETH-TST session with start time as absolute and
                    stop time as relative";
        input  {
            leaf test-target  {
                type ipi-cfm-data-types:cfm_rmep_type_t;
                mandatory true;
                description "Unicast MAC address or MEP ID of the peer MEP for which ETH-Test is
                            intended";
            }
            leaf mep-id  {
                type uint16 {
                    range "1..8191";
                }
                mandatory true;
                description "The MEP ID of the source MEP";
            }
            leaf ma-name  {
                type string {
                    length "1..6";
                }
                mandatory true;
                description "A unique identifier of a Maintenance Association";
            }
            leaf md-name  {
                type string {
                    length "1..43";
                }
                mandatory true;
                description "A unique identifier of a Maintenance Domain";
            }
            leaf profile-name  {
                type string {
                    length "1..64";

                    pattern "[a-zA-Z0-9_-]*";
                }
                mandatory true;
                description "This attribute contains the profile name for ETH-TST session";
            }
            leaf start-time-type  {
                type ipi-cfm-data-types:cfm_absolute_time_t;
                mandatory true;
                description "This attribute defines the session start time";
            }
            leaf start-time  {
                type string;
                mandatory true;
                description "This attribute states that the session start time should be in
                            absolute format i.e. HH:MM:SS-DD-Mon-YYYY";
            }
            leaf stop-time-type  {
                type ipi-cfm-data-types:cfm_relative_time_t;
                mandatory true;
                description "This attribute defines the session stop time";
            }
            leaf stop-time  {
                type uint32 {
                    range "0..4294967295";
                }
                mandatory true;
                description "This attribute defines the session stop time";
            }
        }
    }

    rpc cfm-l2-eth-test-on-demand-start-relative-stop-absolute {
        if-feature feature-list:Y1731_HW_OFFLOAD;
        if-feature feature-list:HAVE_CFM;
        if-feature feature-list:HAVE_ONMD;
        if-feature feature-list:HAVE_CFM_Y1731;
        description "RPC to start on-demand ETH-TST session with start time as relative and
                    stop time as absolute";
        input  {
            leaf test-target  {
                type ipi-cfm-data-types:cfm_rmep_type_t;
                mandatory true;
                description "Unicast MAC address or MEP ID of the peer MEP for which ETH-Test is
                            intended";
            }
            leaf mep-id  {
                type uint16 {
                    range "1..8191";
                }
                mandatory true;
                description "The MEP ID of the source MEP";
            }
            leaf ma-name  {
                type string {
                    length "1..6";
                }
                mandatory true;
                description "A unique identifier of a Maintenance Association";
            }
            leaf md-name  {
                type string {
                    length "1..43";
                }
                mandatory true;
                description "A unique identifier of a Maintenance Domain";
            }
            leaf profile-name  {
                type string {
                    length "1..64";

                    pattern "[a-zA-Z0-9_-]*";
                }
                mandatory true;
                description "This attribute contains the profile name for ETH-TST session";
            }
            leaf start-time-type  {
                type ipi-cfm-data-types:cfm_relative_time_t;
                mandatory true;
                description "Session start time can be relative or absolute";
            }
            leaf start-time  {
                type uint32 {
                    range "0..4294967295";
                }
                mandatory true;
                description "The time when the session is supposed to be started";
            }
            leaf stop-time-type  {
                type ipi-cfm-data-types:cfm_absolute_time_t;
                mandatory true;
                description "This attribute defines the session stop time";
            }
            leaf stop-time  {
                type string;
                mandatory true;
                description "This attribute states that the session stop time should be in absolute
                            format i.e. HH:MM:SS-DD-Mon-YYYY";
            }
        }
    }

    rpc cfm-l2-eth-test-on-demand-start-absolute-stop-absolute {
        if-feature feature-list:Y1731_HW_OFFLOAD;
        if-feature feature-list:HAVE_CFM;
        if-feature feature-list:HAVE_ONMD;
        if-feature feature-list:HAVE_CFM_Y1731;
        description "RPC to start on-demand ETH-TST session with start time as absolute and
                    stop time as absolute";
        input  {
            leaf test-target  {
                type ipi-cfm-data-types:cfm_rmep_type_t;
                mandatory true;
                description "Unicast MAC address or MEP ID of the peer MEP for which ETH-Test is
                            intended";
            }
            leaf mep-id  {
                type uint16 {
                    range "1..8191";
                }
                mandatory true;
                description "The MEP ID of the source MEP";
            }
            leaf ma-name  {
                type string {
                    length "1..6";
                }
                mandatory true;
                description "A unique identifier of a Maintenance Association";
            }
            leaf md-name  {
                type string {
                    length "1..43";
                }
                mandatory true;
                description "A unique identifier of a Maintenance Domain";
            }
            leaf profile-name  {
                type string {
                    length "1..64";

                    pattern "[a-zA-Z0-9_-]*";
                }
                mandatory true;
                description "This attribute specifies the profile name for ETH-TST session";
            }
            leaf start-time-type  {
                type ipi-cfm-data-types:cfm_absolute_time_t;
                mandatory true;
                description "The time that the session is supposed to be started";
            }
            leaf start-time  {
                type string;
                mandatory true;
                description "This attribute states that the session start time should be in
                            absolute format i.e. HH:MM:SS-DD-Mon-YYYY";
            }
            leaf stop-time-type  {
                type ipi-cfm-data-types:cfm_absolute_time_t;
                mandatory true;
                description "The time that the session is supposed to be stopped";
            }
            leaf stop-time  {
                type string;
                mandatory true;
                description "This attribute states that the session stop time should be in absolute
                            format i.e. HH:MM:SS-DD-Mon-YYYY";
            }
        }
    }

    rpc cfm-l2-eth-lm-start-proactive {
        if-feature feature-list:Y1731_HW_OFFLOAD;
        if-feature feature-list:HAVE_CFM;
        if-feature feature-list:HAVE_ONMD;
        if-feature feature-list:HAVE_CFM_Y1731;
        description "RPC to start a proactive Loss Measurement session for an L2 bridge";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM LM Session";
            }
            leaf rmep-id  {
                type ipi-cfm-data-types:cfm_rmep_type_t;
                mandatory true;
                description "The remote MEP can be identified by either a MAC address or a MEP ID";
            }
        }
    }

    rpc cfm-l2-eth-lm-on-demand-start-immediate-stop-none {
        if-feature feature-list:Y1731_HW_OFFLOAD;
        if-feature feature-list:HAVE_CFM;
        if-feature feature-list:HAVE_ONMD;
        if-feature feature-list:HAVE_CFM_Y1731;
        description "RPC to start an on-demand Loss Measurement session for an L2 bridge
                    with start time as immediate and stop time as none";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM LM Session";
            }
            leaf rmep-id  {
                type ipi-cfm-data-types:cfm_rmep_type_t;
                mandatory true;
                description "The remote MEP can be identified by either a MAC address or a MEP ID";
            }
            leaf start-time-type  {
                type ipi-cfm-data-types:cfm_start_time_immediate_t;
                mandatory true;
                description "Measurement session start time can be immediate, relative or absolute";
            }
            leaf stop-time-type  {
                type ipi-cfm-data-types:cfm_stop_time_none_t;
                mandatory true;
                description "Measurement session stop time can be none, relative or absolute";
            }
            leaf repetition-period  {
                type yang:timeticks {
                    range "6000..4294967295";
                }
                mandatory true;
                description "This object specifies a configurable repetition time between
                            Measurement Intervals in a Measurement session in hundredths of a
                            second";
            }
        }
    }

    rpc cfm-l2-eth-lm-on-demand-start-immediate-stop-relative {
        if-feature feature-list:Y1731_HW_OFFLOAD;
        if-feature feature-list:HAVE_CFM;
        if-feature feature-list:HAVE_ONMD;
        if-feature feature-list:HAVE_CFM_Y1731;
        description "RPC to start an on-demand Loss Measurement session for an L2 bridge
                    with start time as immediate and stop time as relative";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM LM Session";
            }
            leaf rmep-id  {
                type ipi-cfm-data-types:cfm_rmep_type_t;
                mandatory true;
                description "The remote MEP can be identified by either a MAC address or a MEP ID";
            }
            leaf start-time-type  {
                type ipi-cfm-data-types:cfm_start_time_immediate_t;
                mandatory true;
                description "Measurement session start time can be immediate, relative or absolute";
            }
            leaf stop-time-type  {
                type ipi-cfm-data-types:cfm_relative_time_t;
                mandatory true;
                description "Measurement session stop time can be none, relative or absolute";
            }
            leaf stop-time  {
                type string;
                mandatory true;
                description "This attribute defines the session stop time";
            }
            leaf repetition-period  {
                type yang:timeticks {
                    range "6000..4294967295";
                }
                mandatory true;
                description "This object specifies a configurable repetition time between
                            Measurement Intervals in a Measurement session in hundredths of a
                            second";
            }
        }
    }

    rpc cfm-l2-eth-lm-on-demand-start-immediate-stop-absolute {
        if-feature feature-list:Y1731_HW_OFFLOAD;
        if-feature feature-list:HAVE_CFM;
        if-feature feature-list:HAVE_ONMD;
        if-feature feature-list:HAVE_CFM_Y1731;
        description "RPC to start an on-demand Loss Measurement session for an L2 bridge
                    with start time as immediate and stop time as absolute";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM LM Session";
            }
            leaf rmep-id  {
                type ipi-cfm-data-types:cfm_rmep_type_t;
                mandatory true;
                description "The remote MEP can be identified by either a MAC address or a MEP ID";
            }
            leaf start-time-type  {
                type ipi-cfm-data-types:cfm_start_time_immediate_t;
                mandatory true;
                description "Measurement session start time can be immediate, relative or absolute";
            }
            leaf stop-time-type  {
                type ipi-cfm-data-types:cfm_absolute_time_t;
                mandatory true;
                description "This attribute defines the session stop time";
            }
            leaf stop-time  {
                type string;
                mandatory true;
                description "This attribute states that the session stop time should be in absolute
                            format i.e. HH:MM:SS-DD-Mon-YYYY";
            }
            leaf repetition-period  {
                type yang:timeticks {
                    range "6000..4294967295";
                }
                mandatory true;
                description "This object specifies a configurable repetition time between
                            Measurement Intervals in a Measurement session in hundredths of a
                            second";
            }
        }
    }

    rpc cfm-l2-eth-lm-on-demand-start-relative-stop-none {
        if-feature feature-list:Y1731_HW_OFFLOAD;
        if-feature feature-list:HAVE_CFM;
        if-feature feature-list:HAVE_ONMD;
        if-feature feature-list:HAVE_CFM_Y1731;
        description "RPC to start an on-demand Loss Measurement session for an L2 bridge
                    with start time as relative and stop time as none";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM LM Session";
            }
            leaf rmep-id  {
                type ipi-cfm-data-types:cfm_rmep_type_t;
                mandatory true;
                description "The remote MEP can be identified by either a MAC address or a MEP ID";
            }
            leaf start-time-type  {
                type ipi-cfm-data-types:cfm_relative_time_t;
                mandatory true;
                description "Measurement session start time can be immediate, relative or absolute";
            }
            leaf start-time  {
                type string;
                mandatory true;
                description "The time that the current Measurement Interval started";
            }
            leaf stop-time-type  {
                type ipi-cfm-data-types:cfm_stop_time_none_t;
                mandatory true;
                description "Measurement session stop time can be none, relative or absolute";
            }
            leaf repetition-period  {
                type yang:timeticks {
                    range "6000..4294967295";
                }
                mandatory true;
                description "This object specifies a configurable repetition time between
                            Measurement Intervals in a Measurement session in hundredths of a
                            second";
            }
        }
    }

    rpc cfm-l2-eth-lm-on-demand-start-relative-stop-relative {
        if-feature feature-list:Y1731_HW_OFFLOAD;
        if-feature feature-list:HAVE_CFM;
        if-feature feature-list:HAVE_ONMD;
        if-feature feature-list:HAVE_CFM_Y1731;
        description "RPC to start an on-demand Loss Measurement session for an L2 bridge
                    with start time as relative and stop time as relative";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM LM Session";
            }
            leaf rmep-id  {
                type ipi-cfm-data-types:cfm_rmep_type_t;
                mandatory true;
                description "The remote MEP can be identified by either a MAC address or a MEP ID";
            }
            leaf start-time-type  {
                type ipi-cfm-data-types:cfm_relative_time_t;
                mandatory true;
                description "Measurement session start time can be immediate, relative or absolute";
            }
            leaf start-time  {
                type string;
                mandatory true;
                description "The time that the current Measurement Interval started";
            }
            leaf stop-time-type  {
                type ipi-cfm-data-types:cfm_relative_time_t;
                mandatory true;
                description "Measurement session stop time can be none, relative or absolute";
            }
            leaf stop-time  {
                type string;
                mandatory true;
                description "This attribute defines the session stop time";
            }
            leaf repetition-period  {
                type yang:timeticks {
                    range "6000..4294967295";
                }
                mandatory true;
                description "This object specifies a configurable repetition time between
                            Measurement Intervals in a Measurement session in hundredths of a
                            second";
            }
        }
    }

    rpc cfm-l2-eth-lm-on-demand-start-relative-stop-absolute {
        if-feature feature-list:Y1731_HW_OFFLOAD;
        if-feature feature-list:HAVE_CFM;
        if-feature feature-list:HAVE_ONMD;
        if-feature feature-list:HAVE_CFM_Y1731;
        description "RPC to start an on-demand Loss Measurement session for an L2 bridge
                    with start time as relative and stop time as absolute";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM LM Session";
            }
            leaf rmep-id  {
                type ipi-cfm-data-types:cfm_rmep_type_t;
                mandatory true;
                description "The remote MEP can be identified by either a MAC address or a MEP ID";
            }
            leaf start-time-type  {
                type ipi-cfm-data-types:cfm_relative_time_t;
                mandatory true;
                description "Measurement session start time can be immediate, relative or absolute";
            }
            leaf start-time  {
                type string;
                mandatory true;
                description "The time that the current Measurement Interval started";
            }
            leaf stop-time-type  {
                type ipi-cfm-data-types:cfm_absolute_time_t;
                mandatory true;
                description "This attribute defines the session stop time";
            }
            leaf stop-time  {
                type string;
                mandatory true;
                description "This attribute states that the session stop time should be in absolute
                            format i.e. HH:MM:SS-DD-Mon-YYYY";
            }
            leaf repetition-period  {
                type yang:timeticks {
                    range "6000..4294967295";
                }
                mandatory true;
                description "This object specifies a configurable repetition time between
                            Measurement Intervals in a Measurement session in hundredths of a
                            second";
            }
        }
    }

    rpc cfm-l2-eth-lm-on-demand-start-absolute-stop-none {
        if-feature feature-list:Y1731_HW_OFFLOAD;
        if-feature feature-list:HAVE_CFM;
        if-feature feature-list:HAVE_ONMD;
        if-feature feature-list:HAVE_CFM_Y1731;
        description "RPC to start an on-demand Loss Measurement session for an L2 bridge
                    with start time as absolute and stop time as none";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM LM Session";
            }
            leaf rmep-id  {
                type ipi-cfm-data-types:cfm_rmep_type_t;
                mandatory true;
                description "The remote MEP can be identified by either a MAC address or a MEP ID";
            }
            leaf start-time-type  {
                type ipi-cfm-data-types:cfm_absolute_time_t;
                mandatory true;
                description "This attribute defines the session start time";
            }
            leaf start-time  {
                type string;
                mandatory true;
                description "This attribute states that the session start time should be in
                            absolute format i.e. HH:MM:SS-DD-Mon-YYYY";
            }
            leaf stop-time-type  {
                type ipi-cfm-data-types:cfm_stop_time_none_t;
                mandatory true;
                description "Measurement session stop time can be none, relative or absolute";
            }
            leaf repetition-period  {
                type yang:timeticks {
                    range "6000..4294967295";
                }
                mandatory true;
                description "This object specifies a configurable repetition time between
                            Measurement Intervals in a Measurement session in hundredths of a
                            second";
            }
        }
    }

    rpc cfm-l2-eth-lm-on-demand-start-absolute-stop-relative {
        if-feature feature-list:Y1731_HW_OFFLOAD;
        if-feature feature-list:HAVE_CFM;
        if-feature feature-list:HAVE_ONMD;
        if-feature feature-list:HAVE_CFM_Y1731;
        description "RPC to start an on-demand Loss Measurement session for an L2 bridge
                    with start time as absolute and stop time as relative";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM LM Session";
            }
            leaf rmep-id  {
                type ipi-cfm-data-types:cfm_rmep_type_t;
                mandatory true;
                description "The remote MEP can be identified by either a MAC address or a MEP ID";
            }
            leaf start-time-type  {
                type ipi-cfm-data-types:cfm_absolute_time_t;
                mandatory true;
                description "This attribute defines the session start time";
            }
            leaf start-time  {
                type string;
                mandatory true;
                description "This attribute states that the session start time should be in
                            absolute format i.e. HH:MM:SS-DD-Mon-YYYY";
            }
            leaf stop-time-type  {
                type ipi-cfm-data-types:cfm_relative_time_t;
                mandatory true;
                description "Measurement session stop time can be none, relative or absolute";
            }
            leaf stop-time  {
                type string;
                mandatory true;
                description "This attribute defines the session stop time";
            }
            leaf repetition-period  {
                type yang:timeticks {
                    range "6000..4294967295";
                }
                mandatory true;
                description "This object specifies a configurable repetition time between
                            Measurement Intervals in a Measurement session in hundredths of a
                            second";
            }
        }
    }

    rpc cfm-l2-eth-lm-on-demand-start-absolute-stop-absolute {
        if-feature feature-list:Y1731_HW_OFFLOAD;
        if-feature feature-list:HAVE_CFM;
        if-feature feature-list:HAVE_ONMD;
        if-feature feature-list:HAVE_CFM_Y1731;
        description "RPC to start an on-demand Loss Measurement session for an L2 bridge
                    with start time as absolute and stop time as absolute";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM LM Session";
            }
            leaf rmep-id  {
                type ipi-cfm-data-types:cfm_rmep_type_t;
                mandatory true;
                description "The remote MEP can be identified by either a MAC address or a MEP ID";
            }
            leaf start-time-type  {
                type ipi-cfm-data-types:cfm_absolute_time_t;
                mandatory true;
                description "This attribute defines the session start time";
            }
            leaf start-time  {
                type string;
                mandatory true;
                description "This attribute states that the session start time should be in
                            absolute format i.e. HH:MM:SS-DD-Mon-YYYY";
            }
            leaf stop-time-type  {
                type ipi-cfm-data-types:cfm_absolute_time_t;
                mandatory true;
                description "This attribute defines the session start time";
            }
            leaf stop-time  {
                type string;
                mandatory true;
                description "This attribute states that the session stop time should be in absolute
                            format i.e. HH:MM:SS-DD-Mon-YYYY";
            }
            leaf repetition-period  {
                type yang:timeticks {
                    range "6000..4294967295";
                }
                mandatory true;
                description "This object specifies a configurable repetition time between
                            Measurement Intervals in a Measurement session in hundredths of a
                            second";
            }
        }
    }

    rpc cfm-l2-abort-eth-lm-test {
        if-feature feature-list:HAVE_CFM_Y1731;
        if-feature feature-list:HAVE_CFM;
        if-feature feature-list:HAVE_ONMD;
        if-feature feature-list:Y1731_HW_OFFLOAD_OR_HAVE_SWFWDR;
        description "RPC to abort an on-going Loss Measurement session for an L2 bridge";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
        }
    }

    rpc cfm-l2-clear-eth-lm-history-stats {
        if-feature feature-list:HAVE_CFM_Y1731;
        if-feature feature-list:HAVE_CFM;
        if-feature feature-list:HAVE_ONMD;
        if-feature feature-list:Y1731_HW_OFFLOAD_OR_HAVE_SWFWDR;
        description "RPC to clear the Loss Measurement history for an L2 bridge";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
        }
    }

    rpc cfm-l2-eth-dm-start-proactive {
        if-feature feature-list:HAVE_CFM_Y1731;
        if-feature feature-list:HAVE_CFM;
        if-feature feature-list:HAVE_ONMD;
        if-feature feature-list:Y1731_HW_OFFLOAD_OR_HAVE_SWFWDR;
        description "RPC to start a proactive Delay Measurement session for an L2 bridge";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM DM Session";
            }
            leaf rmep-id  {
                type ipi-cfm-data-types:cfm_rmep_type_t;
                mandatory true;
                description "The remote MEP can be identified by either a MAC address or a MEP ID";
            }
        }
    }

    rpc cfm-l2-eth-dm-on-demand-start-immediate-stop-none {
        if-feature feature-list:HAVE_CFM_Y1731;
        if-feature feature-list:HAVE_CFM;
        if-feature feature-list:HAVE_ONMD;
        if-feature feature-list:Y1731_HW_OFFLOAD_OR_HAVE_SWFWDR;
        description "RPC to start an on-demand Delay Measurement session for an L2 bridge
                    with start time as immediate and stop time as none";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM DM Session";
            }
            leaf rmep-id  {
                type ipi-cfm-data-types:cfm_rmep_type_t;
                mandatory true;
                description "The remote MEP can be identified by either a MAC address or a MEP ID";
            }
            leaf start-time-type  {
                type ipi-cfm-data-types:cfm_start_time_immediate_t;
                mandatory true;
                description "Measurement session start time can be immediate, relative or absolute";
            }
            leaf stop-time-type  {
                type ipi-cfm-data-types:cfm_stop_time_none_t;
                mandatory true;
                description "Measurement session stop time can be none, relative or absolute";
            }
            leaf repetition-period  {
                type yang:timeticks {
                    range "6000..4294967295";
                }
                mandatory true;
                description "This object specifies a configurable repetition time between
                            Measurement Intervals in a Measurement session in hundredths of a
                            second";
            }
        }
    }

    rpc cfm-l2-eth-dm-on-demand-start-immediate-stop-relative {
        if-feature feature-list:HAVE_CFM_Y1731;
        if-feature feature-list:HAVE_CFM;
        if-feature feature-list:HAVE_ONMD;
        if-feature feature-list:Y1731_HW_OFFLOAD_OR_HAVE_SWFWDR;
        description "RPC to start an on-demand Delay Measurement session for an L2 bridge
                    with start time as immediate and stop time as relative";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM DM Session";
            }
            leaf rmep-id  {
                type ipi-cfm-data-types:cfm_rmep_type_t;
                mandatory true;
                description "The remote MEP can be identified by either a MAC address or a MEP ID";
            }
            leaf start-time-type  {
                type ipi-cfm-data-types:cfm_start_time_immediate_t;
                mandatory true;
                description "Measurement session start time can be immediate, relative or absolute";
            }
            leaf stop-time-type  {
                type ipi-cfm-data-types:cfm_relative_time_t;
                mandatory true;
                description "Measurement session stop time can be none, relative or absolute";
            }
            leaf stop-time  {
                type string;
                mandatory true;
                description "This attribute defines the session stop time";
            }
            leaf repetition-period  {
                type yang:timeticks {
                    range "6000..4294967295";
                }
                mandatory true;
                description "This object specifies a configurable repetition time between
                            Measurement Intervals in a Measurement session in hundredths of a
                            second";
            }
        }
    }

    rpc cfm-l2-eth-dm-on-demand-start-immediate-stop-absolute {
        if-feature feature-list:HAVE_CFM_Y1731;
        if-feature feature-list:HAVE_CFM;
        if-feature feature-list:HAVE_ONMD;
        if-feature feature-list:Y1731_HW_OFFLOAD_OR_HAVE_SWFWDR;
        description "RPC to start an on-demand Delay Measurement session for an L2 bridge
                    with start time as immediate and stop time as absolute";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM DM Session";
            }
            leaf rmep-id  {
                type ipi-cfm-data-types:cfm_rmep_type_t;
                mandatory true;
                description "The remote MEP can be identified by either a MAC address or a MEP ID";
            }
            leaf start-time-type  {
                type ipi-cfm-data-types:cfm_start_time_immediate_t;
                mandatory true;
                description "Measurement session start time can be immediate, relative or absolute";
            }
            leaf stop-time-type  {
                type ipi-cfm-data-types:cfm_absolute_time_t;
                mandatory true;
                description "This attribute defines the session stop time";
            }
            leaf stop-time  {
                type string;
                mandatory true;
                description "This attribute states that the session stop time should be in absolute
                            format i.e. HH:MM:SS-DD-Mon-YYYY";
            }
            leaf repetition-period  {
                type yang:timeticks {
                    range "6000..4294967295";
                }
                mandatory true;
                description "This object specifies a configurable repetition time between
                            Measurement Intervals in a Measurement session in hundredths of a
                            second";
            }
        }
    }

    rpc cfm-l2-eth-dm-on-demand-start-relative-stop-none {
        if-feature feature-list:HAVE_CFM_Y1731;
        if-feature feature-list:HAVE_CFM;
        if-feature feature-list:HAVE_ONMD;
        if-feature feature-list:Y1731_HW_OFFLOAD_OR_HAVE_SWFWDR;
        description "RPC to start an on-demand Delay Measurement session for an L2 bridge
                    with start time as relative and stop time as none";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM DM Session";
            }
            leaf rmep-id  {
                type ipi-cfm-data-types:cfm_rmep_type_t;
                mandatory true;
                description "The remote MEP can be identified by either a MAC address or a MEP ID";
            }
            leaf start-time-type  {
                type ipi-cfm-data-types:cfm_relative_time_t;
                mandatory true;
                description "Measurement session start time can be immediate, relative or absolute";
            }
            leaf start-time  {
                type string;
                mandatory true;
                description "The time that the current Measurement Interval started";
            }
            leaf stop-time-type  {
                type ipi-cfm-data-types:cfm_stop_time_none_t;
                mandatory true;
                description "Measurement session stop time can be none, relative or absolute";
            }
            leaf repetition-period  {
                type yang:timeticks {
                    range "6000..4294967295";
                }
                mandatory true;
                description "This object specifies a configurable repetition time between
                            Measurement Intervals in a Measurement session in hundredths of a
                            second";
            }
        }
    }

    rpc cfm-l2-eth-dm-on-demand-start-relative-stop-relative {
        if-feature feature-list:HAVE_CFM_Y1731;
        if-feature feature-list:HAVE_CFM;
        if-feature feature-list:HAVE_ONMD;
        if-feature feature-list:Y1731_HW_OFFLOAD_OR_HAVE_SWFWDR;
        description "RPC to start an on-demand Delay Measurement session for an L2 bridge
                    with start time as relative and stop time as relative";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM DM Session";
            }
            leaf rmep-id  {
                type ipi-cfm-data-types:cfm_rmep_type_t;
                mandatory true;
                description "The remote MEP can be identified by either a MAC address or a MEP ID";
            }
            leaf start-time-type  {
                type ipi-cfm-data-types:cfm_relative_time_t;
                mandatory true;
                description "Measurement session start time can be immediate, relative or absolute";
            }
            leaf start-time  {
                type string;
                mandatory true;
                description "The time that the current Measurement Interval started";
            }
            leaf stop-time-type  {
                type ipi-cfm-data-types:cfm_relative_time_t;
                mandatory true;
                description "Measurement session stop time can be none, relative or absolute";
            }
            leaf stop-time  {
                type string;
                mandatory true;
                description "This attribute defines the session stop time";
            }
            leaf repetition-period  {
                type yang:timeticks {
                    range "6000..4294967295";
                }
                mandatory true;
                description "This object specifies a configurable repetition time between
                            Measurement Intervals in a Measurement session in hundredths of a
                            second";
            }
        }
    }

    rpc cfm-l2-eth-dm-on-demand-start-relative-stop-absolute {
        if-feature feature-list:HAVE_CFM_Y1731;
        if-feature feature-list:HAVE_CFM;
        if-feature feature-list:HAVE_ONMD;
        if-feature feature-list:Y1731_HW_OFFLOAD_OR_HAVE_SWFWDR;
        description "RPC to start an on-demand Delay Measurement session for an L2 bridge
                    with start time as relative and stop time as absolute";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM DM Session";
            }
            leaf rmep-id  {
                type ipi-cfm-data-types:cfm_rmep_type_t;
                mandatory true;
                description "The remote MEP can be identified by either a MAC address or a MEP ID";
            }
            leaf start-time-type  {
                type ipi-cfm-data-types:cfm_relative_time_t;
                mandatory true;
                description "Measurement session start time can be immediate, relative or absolute";
            }
            leaf start-time  {
                type string;
                mandatory true;
                description "The time that the current Measurement Interval started";
            }
            leaf stop-time-type  {
                type ipi-cfm-data-types:cfm_absolute_time_t;
                mandatory true;
                description "This attribute defines the session start time";
            }
            leaf stop-time  {
                type string;
                mandatory true;
                description "This attribute states that the session stop time should be in absolute
                            format i.e. HH:MM:SS-DD-Mon-YYYY";
            }
            leaf repetition-period  {
                type yang:timeticks {
                    range "6000..4294967295";
                }
                mandatory true;
                description "This object specifies a configurable repetition time between
                            Measurement Intervals in a Measurement session in hundredths of a
                            second";
            }
        }
    }

    rpc cfm-l2-eth-dm-on-demand-start-absolute-stop-none {
        if-feature feature-list:HAVE_CFM_Y1731;
        if-feature feature-list:HAVE_CFM;
        if-feature feature-list:HAVE_ONMD;
        if-feature feature-list:Y1731_HW_OFFLOAD_OR_HAVE_SWFWDR;
        description "RPC to start an on-demand Delay Measurement session for an L2 bridge
                    with start time as absolute and stop time as none";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM DM Session";
            }
            leaf rmep-id  {
                type ipi-cfm-data-types:cfm_rmep_type_t;
                mandatory true;
                description "The remote MEP can be identified by either a MAC address or a MEP ID";
            }
            leaf start-time-type  {
                type ipi-cfm-data-types:cfm_absolute_time_t;
                mandatory true;
                description "Measurement session start time can be immediate, relative or absolute";
            }
            leaf start-time  {
                type string;
                mandatory true;
                description "This attribute states that the session start time should be in
                            absolute format i.e. HH:MM:SS-DD-Mon-YYYY";
            }
            leaf stop-time-type  {
                type ipi-cfm-data-types:cfm_stop_time_none_t;
                mandatory true;
                description "Measurement session stop time can be none, relative or absolute";
            }
            leaf repetition-period  {
                type yang:timeticks {
                    range "6000..4294967295";
                }
                mandatory true;
                description "This object specifies a configurable repetition time between
                            Measurement Intervals in a Measurement session in hundredths of a
                            second";
            }
        }
    }

    rpc cfm-l2-eth-dm-on-demand-start-absolute-stop-relative {
        if-feature feature-list:HAVE_CFM_Y1731;
        if-feature feature-list:HAVE_CFM;
        if-feature feature-list:HAVE_ONMD;
        if-feature feature-list:Y1731_HW_OFFLOAD_OR_HAVE_SWFWDR;
        description "RPC to start an on-demand Delay Measurement session for an L2 bridge
                    with start time as absolute and stop time as relative";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM DM Session";
            }
            leaf rmep-id  {
                type ipi-cfm-data-types:cfm_rmep_type_t;
                mandatory true;
                description "The remote MEP can be identified by either a MAC address or a MEP ID";
            }
            leaf start-time-type  {
                type ipi-cfm-data-types:cfm_absolute_time_t;
                mandatory true;
                description "This attribute defines the session start time";
            }
            leaf start-time  {
                type string;
                mandatory true;
                description "This attribute states that the session start time should be in
                            absolute format i.e. HH:MM:SS-DD-Mon-YYYY";
            }
            leaf stop-time-type  {
                type ipi-cfm-data-types:cfm_relative_time_t;
                mandatory true;
                description "Measurement session stop time can be none, relative or absolute";
            }
            leaf stop-time  {
                type string;
                mandatory true;
                description "This attribute states that the session stop time should be in
                            relativve format i.e. HH:MM:SS";
            }
            leaf repetition-period  {
                type yang:timeticks {
                    range "6000..4294967295";
                }
                mandatory true;
                description "This object specifies a configurable repetition time between
                            Measurement Intervals in a Measurement session in hundredths of a
                            second";
            }
        }
    }

    rpc cfm-l2-eth-dm-on-demand-start-absolute-stop-absolute {
        if-feature feature-list:HAVE_CFM_Y1731;
        if-feature feature-list:HAVE_CFM;
        if-feature feature-list:HAVE_ONMD;
        if-feature feature-list:Y1731_HW_OFFLOAD_OR_HAVE_SWFWDR;
        description "RPC to start an on-demand Delay Measurement session for an L2 bridge
                    with start time as absolute and stop time as absolute";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf profile-name  {
                type string {
                    length "0..64";

                    pattern "[a-zA-Z0-9_-]*";
                }
                mandatory true;
                description "This attribute contains the profile name for the SOAM DM Session";
            }
            leaf rmep-id  {
                type ipi-cfm-data-types:cfm_rmep_type_t;
                mandatory true;
                description "The remote MEP can be identified by either a MAC address or a MEP ID";
            }
            leaf start-time-type  {
                type ipi-cfm-data-types:cfm_absolute_time_t;
                mandatory true;
                description "This attribute defines the session start time";
            }
            leaf start-time  {
                type string;
                mandatory true;
                description "This attribute states that the session start time should be in
                            absolute format i.e. HH:MM:SS-DD-Mon-YYYY";
            }
            leaf stop-time-type  {
                type ipi-cfm-data-types:cfm_absolute_time_t;
                mandatory true;
                description "This attribute defines the session stop time";
            }
            leaf stop-time  {
                type string;
                mandatory true;
                description "This attribute states that the session stop time should be in absolute
                            format i.e. HH:MM:SS-DD-Mon-YYYY";
            }
            leaf repetition-period  {
                type yang:timeticks {
                    range "6000..4294967295";
                }
                mandatory true;
                description "This object specifies a configurable repetition time between
                            Measurement Intervals in a Measurement session in hundredths of a
                            second";
            }
        }
    }

    rpc cfm-l2-abort-eth-dm-test {
        if-feature feature-list:HAVE_CFM_Y1731;
        if-feature feature-list:HAVE_CFM;
        if-feature feature-list:HAVE_ONMD;
        if-feature feature-list:Y1731_HW_OFFLOAD_OR_HAVE_SWFWDR;
        description "RPC to abort an on-going Delay Measurement session for an L2 bridge";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
        }
    }

    rpc cfm-l2-clear-eth-dm-history-stats {
        if-feature feature-list:HAVE_CFM_Y1731;
        if-feature feature-list:HAVE_CFM;
        if-feature feature-list:HAVE_ONMD;
        if-feature feature-list:Y1731_HW_OFFLOAD_OR_HAVE_SWFWDR;
        description "RPC to clear the Delay Measurement history for an L2 bridge";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
        }
    }

    rpc cfm-l2-clear-eth-csf-stats {
        if-feature feature-list:Y1731_HW_OFFLOAD;
        if-feature feature-list:HAVE_CFM;
        if-feature feature-list:HAVE_ONMD;
        if-feature feature-list:HAVE_CFM_Y1731;
        description "Use this RPC to clear ethernet CSF statistics for the specified MEP";
        input  {
            leaf mep-id  {
                type uint16 {
                    range "1..8191";
                }
                mandatory true;
                description "The MEP ID of the source MEP";
            }
            leaf md-name  {
                type string {
                    length "1..43";
                }
                mandatory true;
                description "A unique identifier of a Maintenance Domain";
            }
            leaf ma-name  {
                type string {
                    length "1..6";
                }
                mandatory true;
                description "A unique identifier of a Maintenance Association";
            }
        }
    }

    rpc cfm-l2-clear-eth-bn-stats {
        if-feature feature-list:Y1731_HW_OFFLOAD;
        if-feature feature-list:HAVE_CFM;
        if-feature feature-list:HAVE_ONMD;
        if-feature feature-list:HAVE_CFM_Y1731;
        description "RPC to clear the ethernent bandwidth notification statistics for
                    specified domain and MEP ID";
        input  {
            leaf mep-id  {
                type uint16 {
                    range "1..8191";
                }
                mandatory true;
                description "The MEP ID of the source MEP";
            }
            leaf md-name  {
                type string {
                    length "1..43";
                }
                mandatory true;
                description "A unique identifier of a Maintenance Domain";
            }
            leaf ma-name  {
                type string {
                    length "1..6";
                }
                mandatory true;
                description "A unique identifier of a Maintenance Association";
            }
        }
    }

    rpc cfm-l2-clear-eth-lck-stats {
        if-feature feature-list:Y1731_HW_OFFLOAD;
        if-feature feature-list:HAVE_CFM;
        if-feature feature-list:HAVE_ONMD;
        if-feature feature-list:HAVE_CFM_Y1731;
        description "Use this RPC to clear ethernet LCK statistics for the specified MEP";
        input  {
            leaf mep-id  {
                type uint16 {
                    range "1..8191";
                }
                mandatory true;
                description "The MEP ID of the source MEP";
            }
            leaf md-name  {
                type string {
                    length "1..43";
                }
                mandatory true;
                description "A unique identifier of a Maintenance Domain";
            }
            leaf ma-name  {
                type string {
                    length "1..6";
                }
                mandatory true;
                description "A unique identifier of a Maintenance Association";
            }
        }
    }

    rpc cfm-l2-clear-eth-test-signal-stats {
        if-feature feature-list:Y1731_HW_OFFLOAD;
        if-feature feature-list:HAVE_CFM;
        if-feature feature-list:HAVE_ONMD;
        if-feature feature-list:HAVE_CFM_Y1731;
        description "Use this RPC to clear ethernet test signal statistics for the
                    specified MEP";
        input  {
            leaf md-name  {
                type string {
                    length "1..43";
                }
                mandatory true;
                description "A unique identifier of a Maintenance Domain";
            }
            leaf ma-name  {
                type string {
                    length "1..6";
                }
                mandatory true;
                description "A unique identifier of a Maintenance Association";
            }
            leaf mep-id  {
                type uint16 {
                    range "1..8191";
                }
                mandatory true;
                description "The MEP ID of the source MEP";
            }
            leaf stats-type  {
                type ipi-cfm-data-types:cfm_test_stats_type_t;
                mandatory true;
                description "Type of the Ethernet TST frame stats";
            }
        }
    }

    rpc cfm-l2-clear-ethernet-remote-meps {
        if-feature feature-list:HAVE_CFM;
        if-feature feature-list:HAVE_ONMD;
        description "Use this RPC to clear ethernet CFM remote MEPs of specified domain and
                    L2 bridge";
        input  {
            leaf domain-name  {
                type string;
                mandatory true;
                description "A unique identifier of a Maintenance Domain";
            }
        }
    }

    rpc cfm-clear-all-mep-stats {
        if-feature feature-list:HAVE_CFM;
        if-feature feature-list:HAVE_ONMD;
        description "Clear CFM statistics of all MEPs";
    }

    rpc cfm-l2-clear-mep-stats {
        if-feature feature-list:HAVE_CFM;
        if-feature feature-list:HAVE_ONMD;
        description "Clear CFM statistics of specified MEP for specific domain, VLAN and L2
                    bridge";
        input  {
            leaf domain-name  {
                type string;
                mandatory true;
                description "A unique identifier of a Maintenance Domain";
            }
            leaf mep-id  {
                type uint16 {
                    range "1..8191";
                }
                mandatory true;
                description "Integer that is unique among all the MEPs in the same MA. Other
                            definition is: a small integer, unique over a given Maintenance
                            Association, identifying a specific Maintenance association End Point";
            }
            leaf ma-name  {
                type string {
                    length "1..6";
                }
                mandatory true;
                description "A unique identifier of a Maintenance Association";
            }
        }
    }

    rpc cfm-snmp-restart {
        if-feature feature-list:HAVE_CFM;
        if-feature feature-list:HAVE_ONMD;
        description "CFM SNMP restart";
    }

    rpc cfm-terminal-debug-on {
        if-feature feature-list:HAVE_CFM;
        if-feature feature-list:HAVE_ONMD;
        description "Use this RPC to set CFM debug options in EXEC mode";
        input  {
            leaf terminal-debug-options  {
                type ipi-cfm-data-types:cfm_debug_t;
                mandatory true;
                description "Debug configuration flag";
            }
        }
    }

    rpc cfm-terminal-debug-off {
        if-feature feature-list:HAVE_CFM;
        if-feature feature-list:HAVE_ONMD;
        description "Use this RPC to unset CFM debug options in EXEC mode";
        input  {
            leaf terminal-debug-options  {
                type ipi-cfm-data-types:cfm_debug_t;
                mandatory true;
                description "Debug configuration flag";
            }
        }
    }

    rpc cfm-l2-test-loopback {
        if-feature feature-list:HAVE_CFM;
        if-feature feature-list:HAVE_ONMD;
        description "Use this RPC ping a remote MEP for L2 bridge";
        input  {
            leaf md-name  {
                type string {
                    length "1..43";
                }
                mandatory true;
                description "A unique identifier of a Maintenance Domain";
            }
            leaf ma-name  {
                type string {
                    length "1..43";
                }
                mandatory true;
                description "A unique identifier of a Maintenance Association";
            }
            leaf mep-id  {
                type uint16 {
                    range "1..8191";
                }
                mandatory true;
                description "The MEP ID of the source MEP";
            }
            leaf mac-address  {
                type ipi-cfm-data-types:cfm_lb_mac_addr_t;
                mandatory true;
                description "The remote MEP identified by MAC address";
            }
        }
    }

    rpc cfm-l2-test-linktrace {
        if-feature feature-list:HAVE_CFM;
        if-feature feature-list:HAVE_ONMD;
        description "Use this RPC to start a linktrace test for a L2 bridge";
        input  {
            leaf md-name  {
                type string {
                    length "1..43";
                }
                mandatory true;
                description "A unique identifier of a Maintenance Domain";
            }
            leaf ma-name  {
                type string {
                    length "1..43";
                }
                mandatory true;
                description "A unique identifier of a Maintenance Association";
            }
            leaf mep-id  {
                type uint16 {
                    range "1..8191";
                }
                mandatory true;
                description "The MEP ID of the source MEP";
            }
            leaf mac-address  {
                type ipi-cfm-data-types:cfm_lb_mac_addr_t;
                mandatory true;
                description "The remote MEP identified by MAC address";
            }
        }
        output  {
            leaf transaction-id  {
                type uint32;
                mandatory true;
                description "This attribute specifies the transaction-id of a particular linktrace
                            test";
            }
        }
    }

    rpc cfm-l2-clear-linktrace-cache {
        if-feature feature-list:HAVE_CFM;
        if-feature feature-list:HAVE_ONMD;
        description "Use this RPC to clear the linktrace cache for L2 bridge CFM";
    }

    notification cfm-l2-mep-ccm-highest-fault-info {
        if-feature feature-list:HAVE_CFM;
        if-feature feature-list:HAVE_ONMD;

        description "Notify the highest CCM fault received to all notification clients like CLI, NETCONF and SNMP.";

        leaf severity {
            type cml-data-types:cml_notif_severity_t;
            description "Notification severity level (value: MINOR)";
        }

        leaf eventClass {
            type cml-data-types:cml_notif_class_t;
            description "Notification event class (value: STATE)";
        }

        leaf mep-id {
            type  uint16;
        description
            "Integer that is unique among all the MEPs in the same MA. Other
                    definition is: a small integer, unique over a given Maintenance
                    Association, identifying a specific Maintenance association End Point";
        }

        leaf ma-name {
            type  string;
        description
            "The value union for the Maintenance Association Name.";
        }

        leaf md-name {
            type  string;
        description
            "A unique identifier of a Maintenance Domain";
        }

        leaf highest-priority-defect-found {
            type ipi-cfm-data-types:cfm_mep_highest_fault_defect_t;
        description
            "Value indicating the highest-priority defect that has been present
                    since the MEP Fault Notification Generator state machine was last in
                    the FNG_RESET state. The non-existence of this leaf represents that no
                    defect has been present since the last FNG_RESET state.";
        }
    }

    notification cfm-l2-ethernet-loopback-test-completed {
        if-feature feature-list:HAVE_CFM;
        if-feature feature-list:HAVE_ONMD;

        description "Notify that the last loopback test is complete.";

        leaf severity {
            type cml-data-types:cml_notif_severity_t;
            description "Notification severity level (value: INFO)";
        }

        leaf eventClass {
            type cml-data-types:cml_notif_class_t;
            description "Notification event class (value: STATE)";
        }

        leaf mep-id {
            type  uint16;
        description
            "Integer that is unique among all the MEPs in the same MA. Other
                    definition is: a small integer, unique over a given Maintenance
                    Association, identifying a specific Maintenance association End Point";
        }

        leaf ma-name {
            type  string;
        description
            "The value union for the Maintenance Association Name.";
        }

        leaf md-name {
            type  string;
        description
            "A unique identifier of a Maintenance Domain";
        }

        leaf target-mac-address {
            type ipi-cfm-data-types:cfm_rmep_mac_addr_t;
        description
            "This attribute specifies the target MAC address of last loopback test";
        }
    }

    notification cfm-l2-ethernet-linktrace-test-completed {
        if-feature feature-list:HAVE_CFM;
        if-feature feature-list:HAVE_ONMD;

        description "Notify that the last linktrace test is complete.";

        leaf severity {
            type cml-data-types:cml_notif_severity_t;
            description "Notification severity level (value: INFO)";
        }

        leaf eventClass {
            type cml-data-types:cml_notif_class_t;
            description "Notification event class (value: STATE)";
        }

        leaf transaction-id {
            type  uint32;
        description
            "This attribute specifies the transaction-id of a particular linktrace
                    test";
        }

        leaf mep-id {
            type  uint16;
        description
            "Integer that is unique among all the MEPs in the same MA. Other
                    definition is: a small integer, unique over a given Maintenance
                    Association, identifying a specific Maintenance association End Point";
        }

        leaf ma-name {
            type  string;
        description
            "The value union for the Maintenance Association Name.";
        }

        leaf md-name {
            type  string;
        description
            "A unique identifier of a Maintenance Domain";
        }

        leaf target-mac-address {
            type ipi-cfm-data-types:cfm_rmep_mac_addr_t;
        description
            "This attribute specifies the target MAC address of a particular
                    linktrace test";
        }
    }

    notification cfm-mep-evpn-ccm-defect-condition {
        if-feature feature-list:HAVE_CFM;
        if-feature feature-list:HAVE_ONMD;
        if-feature feature-list:HAVE_VXLAN_OAM;

        description "CCM EVPN defect condition notification.";

        leaf severity {
            type cml-data-types:cml_notif_severity_t;
            description "Notification severity level";
        }

        leaf eventClass {
            type cml-data-types:cml_notif_class_t;
            description "Notification event class (value: STATE)";
        }

        leaf remote-mep-id {
            type  uint32;
        description
            "This attribute represents the CCM remote mep-id";
        }

        leaf mep-id {
            type  uint16;
        description
            "Integer that is unique among all the MEPs in the same MA. Other
                    definition is: a small integer, unique over a given Maintenance
                    Association, identifying a specific Maintenance association End Point";
        }

        leaf ma-name {
            type  string;
        description
            "The value union for the Maintenance Association Name.";
        }

        leaf md-name {
            type  string;
        description
            "A unique identifier of a Maintenance Domain";
        }

        leaf last-good-sequence-number {
            type  uint32;
        description
            "This attribute represents the last good sequence-number of the CCM";
        }

        leaf last-flapped-time {
            type  yang:date-and-time;
        description
            "This attribute represents the time of the last down transition";
        }

        leaf flow-state {
            type ipi-cfm-data-types:cfm_nvo_oam_ccm_flow_status_t;
        description
            "This attribute represents the current flow state";
        }

        leaf last-good-flow-id {
            type  uint32;
        description
            "This attribute represents the CCM flow-id before flap";
        }
    }

    notification cfm-mep-evpn-ccm-defect-cleared {
        if-feature feature-list:HAVE_CFM;
        if-feature feature-list:HAVE_ONMD;
        if-feature feature-list:HAVE_VXLAN_OAM;

        description "CCM EVPN defect cleared notification.";

        leaf severity {
            type cml-data-types:cml_notif_severity_t;
            description "Notification severity level";
        }

        leaf eventClass {
            type cml-data-types:cml_notif_class_t;
            description "Notification event class (value: STATE)";
        }

        leaf remote-mep-id {
            type  uint32;
        description
            "This attribute represents the CCM remote mep-id";
        }

        leaf mep-id {
            type  uint16;
        description
            "Integer that is unique among all the MEPs in the same MA. Other
                    definition is: a small integer, unique over a given Maintenance
                    Association, identifying a specific Maintenance association End Point";
        }

        leaf ma-name {
            type  string;
        description
            "The value union for the Maintenance Association Name.";
        }

        leaf md-name {
            type  string;
        description
            "A unique identifier of a Maintenance Domain";
        }

        leaf first-good-sequence-number {
            type  uint32;
        description
            "This attribute represents the first good sequence-number of the CCM";
        }

        leaf last-recovered-time {
            type  yang:date-and-time;
        description
            "This attribute represents the time of the last up transition";
        }

        leaf flow-state {
            type ipi-cfm-data-types:cfm_nvo_oam_ccm_flow_status_t;
        description
            "This attribute represents the current flow state";
        }

        leaf last-recovered-flow-id {
            type  uint32;
        description
            "This attribute represents the CCM flow-id after flap";
        }
    }

    notification cfm-eth-csf-los-set {
        if-feature feature-list:HAVE_CFM;
        if-feature feature-list:HAVE_CFM_Y1731;
        if-feature feature-list:HAVE_ONMD;
        if-feature feature-list:Y1731_HW_OFFLOAD;

        description "Notify the CSF LOS set received to all notification clients like CLI and NETCONF.";

        leaf severity {
            type cml-data-types:cml_notif_severity_t;
            description "Notification severity level (value: CRITICAL)";
        }

        leaf eventClass {
            type cml-data-types:cml_notif_class_t;
            description "Notification event class (value: STATE)";
        }

        leaf mep-id {
            type  uint16;
        description
            "Integer that is unique among all the MEPs in the same MA. Other
                    definition is: a small integer, unique over a given Maintenance
                    Association, identifying a specific Maintenance association End Point";
        }

        leaf ma-name {
            type  string;
        description
            "The value union for the Maintenance Association Name.";
        }

        leaf md-name {
            type  string;
        description
            "A unique identifier of a Maintenance Domain";
        }

        leaf signal-state {
            type ipi-cfm-data-types:cfm_bn_csf_signal_state_t;
        description
            "This attribute specifies whether the signal is normal, pending or
                    degraded";
        }
    }

    notification cfm-eth-csf-los-reset {
        if-feature feature-list:HAVE_CFM;
        if-feature feature-list:HAVE_CFM_Y1731;
        if-feature feature-list:HAVE_ONMD;
        if-feature feature-list:Y1731_HW_OFFLOAD;

        description "Notify the CSF LOS re-set received to all notification clients like CLI and NETCONF.";

        leaf severity {
            type cml-data-types:cml_notif_severity_t;
            description "Notification severity level (value: CRITICAL)";
        }

        leaf eventClass {
            type cml-data-types:cml_notif_class_t;
            description "Notification event class (value: STATE)";
        }

        leaf mep-id {
            type  uint16;
        description
            "Integer that is unique among all the MEPs in the same MA. Other
                    definition is: a small integer, unique over a given Maintenance
                    Association, identifying a specific Maintenance association End Point";
        }

        leaf ma-name {
            type  string;
        description
            "The value union for the Maintenance Association Name.";
        }

        leaf md-name {
            type  string;
        description
            "A unique identifier of a Maintenance Domain";
        }

        leaf signal-state {
            type ipi-cfm-data-types:cfm_bn_csf_signal_state_t;
        description
            "This attribute specifies whether the signal is normal, pending or
                    degraded";
        }
    }

    notification cfm-eth-bnm-bw-update {
        if-feature feature-list:HAVE_CFM;
        if-feature feature-list:HAVE_CFM_Y1731;
        if-feature feature-list:HAVE_ONMD;
        if-feature feature-list:Y1731_HW_OFFLOAD;

        description "Notify nominal bandwidth is received in ETH-BN packet to all notification clients like CLI and NETCONF.";

        leaf severity {
            type cml-data-types:cml_notif_severity_t;
            description "Notification severity level (value: INFO)";
        }

        leaf eventClass {
            type cml-data-types:cml_notif_class_t;
            description "Notification event class (value: STATE)";
        }

        leaf mep-id {
            type  uint16;
        description
            "Integer that is unique among all the MEPs in the same MA. Other
                    definition is: a small integer, unique over a given Maintenance
                    Association, identifying a specific Maintenance association End Point";
        }

        leaf ma-name {
            type  string;
        description
            "The value union for the Maintenance Association Name.";
        }

        leaf md-name {
            type  string;
        description
            "A unique identifier of a Maintenance Domain";
        }

        leaf nominal-bandwidth {
            type  string;
        description
            "This attribute specifies the nominal bandwidth received in the ETH-BN
                    packet";
        }

        leaf current-bandwidth {
            type  string;
        description
            "This attribute specifies the current bandwidth received in the ETH-BN
                    packet";
        }
    }

}
