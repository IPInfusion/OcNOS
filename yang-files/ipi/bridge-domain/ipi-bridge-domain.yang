/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bridge-domain.yang
*
*/

module ipi-bridge-domain {

    yang-version 1.1;

    namespace   "http://www.ipinfusion.com/yang/ocnos/ipi-bridge-domain";

    prefix "ipi-bridge-domain";

    import cml-data-types {
        prefix cml-data-types;
        revision-date 2026-05-15;
    }

    import ipi-network-instance {
        prefix ipi-network-instance;
        revision-date 2026-08-12;
    }

    import ipi-interface {
        prefix ipi-interface;
        revision-date 2026-03-10;
    }

    import ipi-bridge-types {
        prefix ipi-bridge-types;
        revision-date 2026-07-30;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Bridge-domain configurations";


    revision "2026-07-30" {
        description "For BRIDGE_PROTOCOL_T datatype changed the helpstrings";
        reference " 0.2.7.";
    }

    revision "2025-10-27" {
        description "MAC normalization function for the mac-address attribute.";
        reference " 0.2.6.";
    }

    revision "2025-09-17" {
        description "Blocking Bridge-domain and cross-connect for all XGS (DC) platforms";
        reference " 0.2.5.";
    }

    revision "2025-04-17" {
        description "New data model implementation for netconf sget xpath for dynamic entries in Bridge-Domain and changes entry as static-entry for static entries";
        reference " 0.2.4.";
    }

    revision "2025-02-06" {
        description "Added 'CML_UNIQUE' support for interface name under bridge domain";
        reference " 0.2.3.";
    }

    revision "2024-10-07" {
        description "Added static MAC support for bridge-domain";
        reference " 0.2.2.";
    }

    revision "2023-10-20" {
        description "Changed member-interfaces nodes from leaf-list to list to ease dependency validations";
        reference " 0.2.1.";
    }

    revision "2023-09-26" {
        description "Added missing dependent objects for bridge-domain CLI with encap";
        reference " 0.1.5.";
    }

    revision "2023-07-19" {
        description "Added fix for removing subif from bridge-domain when encap is removed";
        reference " 0.1.4.";
    }

    revision "2023-07-13" {
        description "Added ifndef HAVE_SWFWDR flag to enable bridge-domain only for boards";
        reference " 0.1.3.";
    }

    revision "2023-05-29" {
        description "Added support for BVI interface mapping with bridge-domain";
        reference " 0.1.2.";
    }

    revision "2023-04-25" {
        description "Fixed clear mac address dynamic bridge-domain id cli issue";
        reference " 0.1.1.";
    }

    revision "2023-03-14" {
        description "It was moved from interfaces extended datamodel to network-instances datamodel.";
        reference " 0.1.0.";
    }

    grouping bridge-domain-interface-config {
        description
            "Grouping for Bridge-Domain interface configuration";
        leaf name  {
            type  leafref {
                path  "/ipi-interface:interfaces/ipi-interface:interface/ipi-interface:name";
            }
            description "This attribute specifies the subif for bridge-domain";
        } // END of name definition.

    } // END of bridge-domain-interface-config definition.
    grouping bridge-domain-interface-top {
        description
            "Grouping for Bridge-Domain interface";
        container member-interfaces {
            description
                "Container for Bridge-Domain interfaces";

            list member-interface {
                key "name";
                description
                    "List of Bridge-Domain interfaces";
                leaf name  {
                    type  leafref {
                        path  "../config/name";
                    }
                    description "This attribute specifies the subif for bridge-domain";
                } // END of name definition.

                container config {
                    description
                        "Configuration data for Bridge-Domain interface";
                    uses bridge-domain-interface-config;
                } // END of config-container definition.
                container state {
                    config false;
                    description
                        "Operational state data for Bridge-Domain interface";
                    uses bridge-domain-interface-config;
                } // END of state-container definition.
            } // End of member-interface-list
        } // END of member-interfaces-container definition.
    } // END of bridge-domain-interface-top definition.
    grouping dynamic-entry-state {
        description
            "Dynamic learned MAC information";
        leaf mac-address  {
            type  cml-data-types:cml_mac_addr_t {
                length "1..1965";
            }
            description "Use this attribute to get the dynamic MAC entry for the bridge";
        } // END of mac-address definition.

        leaf interface-name  {
            type  leafref {
                path  "/ipi-network-instance:network-instances/ipi-network-instance:network-instance/bridge-domain/member-interfaces/member-interface/config/name";
            }
            description "The textual name of the interface";
        } // END of interface-name definition.

    } // END of dynamic-entry-state definition.
    grouping dynamic-mac-table-entry-top {
        description
            "Top level group for dynamic learned MAC address information";

        list dynamic-entry {
            key "mac-address";
            config false;
            description
                "List of dynamic learned MAC entries";
            leaf mac-address  {
                type  leafref {
                    path  "../state/mac-address";
                }
                description "Dynamic learned MAC address";
            } // END of mac-address definition.

            container state {
                config false;
                description
                    "Dynamic learned information operational state data";
                uses dynamic-entry-state;
            } // END of state-container definition.
        } // End of dynamic-entry-list
    } // END of dynamic-mac-table-entry-top definition.
    grouping fdb-entry-config {
        description
            "Configuration data for FDB MAC address";
        leaf mac-address  {
            type  cml-data-types:cml_mac_addr_t {
                length "1..1965";
            }
            description "Use this attribute to configure the static forwarding table MAC entry
                        for the bridge";
        } // END of mac-address definition.

        leaf action  {
            type  ipi-bridge-types:bridge_domain_forward_deny_t;
            mandatory true;
            description "Use this attribute to configure fame discard/forward action for given
                        MAC address";
        } // END of action definition.

        leaf interface-name  {
            type  leafref {
                path  "/ipi-network-instance:network-instances/ipi-network-instance:network-instance/bridge-domain/member-interfaces/member-interface/config/name";
            }
            mandatory true;
            description "The textual name of the interface";
        } // END of interface-name definition.

    } // END of fdb-entry-config definition.
    grouping bridge-domain-fdb-top {
        description
            "Grouping for Sub-interface bridge-domain configurations";
        container bridge-domain-mac-table {
            description
                "MAC table information";

            list static-entry {
                key "mac-address";
                description
                    "List of FDB MAC entries";
                leaf mac-address  {
                    type  leafref {
                        path  "../config/mac-address";
                    }
                    description "Use this attribute to configure the static forwarding table MAC entry
                                for the bridge";
                } // END of mac-address definition.

                container config {
                    description
                        "Configuration data for FDB MAC entries";
                    uses fdb-entry-config;
                } // END of config-container definition.
                container state {
                    config false;
                    description
                        "Operational state data";
                    uses fdb-entry-config;
                } // END of state-container definition.
            } // End of static-entry-list
            uses dynamic-mac-table-entry-top;
        } // END of bridge-domain-mac-table-container definition.
    } // END of bridge-domain-fdb-top definition.
    grouping subif-bridge-config {
        description
            "Grouping for Sub-interface bridge-domain configurations";
        leaf domain-id  {
            type  leafref {
                path  "/ipi-network-instance:network-instances/ipi-network-instance:network-instance/ipi-network-instance:instance-name";
            }
            description "This attribute specifies the bridge domain id.";
        } // END of domain-id definition.

        leaf description  {
            type  cml-data-types:cml_line_t {
                length "1..1965";
            }
            description "This attribute secifies the description for bridge domain";
        } // END of description definition.

        leaf route-interface  {
            type  leafref {
                path  "/ipi-interface:interfaces/ipi-interface:interface/ipi-interface:name";
            }
            description "This attribute specifies the Logical L3 BVI interface for
                        bridge-domain";
        } // END of route-interface definition.

    } // END of subif-bridge-config definition.
    grouping subif-bridge-instance-config {
        description
            "Grouping for Sub-interface bridge-domain configurations";
        leaf instance-id  {
            type  uint8 {
                 range "1..63"  {
                    description "1..63: Supported range 1 - 63";
                 }
            }
            mandatory true;
            description "Value of instance id";
        } // END of instance-id definition.

        leaf bridge-id  {
            type  string {
                length "1..1965";
                pattern "[^?' =,>|]+";
            }
            mandatory true;
            description "Map bridge mst instance to bridge-domain";
        } // END of bridge-id definition.

    } // END of subif-bridge-instance-config definition.

    grouping  bridge-domain-grouping {
    description
        "Global container for bridge domain";
    container bridge-domain {
        if-feature feature-list:HAVE_SUBINTERFACE;
        if-feature feature-list:NOT_HAVE_CUSTOM1_SUBINTERFACE;
        if-feature feature-list:NOT_HAVE_SWFWDR;
        if-feature feature-list:NOT_HAVE_SWFWDR;
        description
            "Global container for bridge domain";
        container config {
            description
                "Global configuration for bridge-domain";
            uses subif-bridge-config;
        } // END of config-container definition.
        container bridge-instance {
            description
                "Global configuration for bridge-domain";
            container config {
                presence "MST instance for bridge-domain";
                description
                    "Configuration for bridge-instance";
                uses subif-bridge-instance-config;
            } // END of config-container definition.
            container state {
                config false;
                description
                    "State data for bridge-domain bridge instance";
                uses subif-bridge-instance-config;
            } // END of state-container definition.
        } // END of bridge-instance-container definition.
        container state {
            config false;
            description
                "State data for bridge-domain";
            uses subif-bridge-config;
        } // END of state-container definition.
        uses bridge-domain-interface-top;
        uses bridge-domain-fdb-top;
    } // END of bridge-domain-container definition.
    } // END of bridge-domain-grouping definition.

    augment /ipi-network-instance:network-instances/ipi-network-instance:network-instance {
    when " /ipi-network-instance:network-instances/ipi-network-instance:network-instance/ipi-network-instance:instance-type = 'bridge-domain' ";
    // when " ipi-bridge-domain:bridge-domain/config ";
        description
            "Global container for bridge domain";
        uses bridge-domain-grouping;
    }


}
