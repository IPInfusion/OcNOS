/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-management-server-types.yang
*
*/

module ipi-management-server-types {

    yang-version 1.1;

    namespace   "http://www.ipinfusion.com/yang/ocnos/ipi-management-server-types";

    prefix "ipi-management-server-types";

    organization
        "IP Infusion Inc.";

    contact
        "Address: 3965 Freedom Circle, Suite 200, Santa Clara, CA 95054
         Phone: +1 408-400-1900
         E-mail: support@ipinfusion.com
         Web: http://www.ipinfusion.com/";

    description
        "Manegement server types";


    revision "2023-05-16" {
        description "Creating a new type for translation mode";
        reference " 0.1.0.";
    }



    typedef  management_server_translation_type_t {
        type enumeration {
            enum openconfig {
                value 1;
                description "Enable translation for OpenConfig";
            }
        }
        description "type definition for MANAGEMENT_SERVER_TRANSLATION_TYPE_T";
    }

}
