/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-management-server.yang
*
*/

module ipi-management-server {

    yang-version 1.1;

    namespace   "http://www.ipinfusion.com/yang/ocnos/ipi-management-server";

    prefix "ipi-management-server";

    import cml-data-types {
        prefix cml-data-types;
        revision-date 2026-05-15;
    }

    import ietf-inet-types {
        prefix inet;
        revision-date 2013-07-15;
    }

    import ipi-management-server-types {
        prefix ipi-management-server-types;
        revision-date 2023-05-16;
    }

    import ipi-network-instance {
        prefix ipi-network-instance;
        revision-date 2026-08-12;
    }

    import ipi-vrf {
        prefix ipi-vrf;
        revision-date 2026-08-12;
    }

    import feature-list {
        prefix feature-list;
        revision-date 2026-09-15;
    }

    include ipi-management-server-notification { revision-date 2023-05-05;}
    organization
        "IP Infusion Inc.";

    contact
        "Address: 3965 Freedom Circle, Suite 200, Santa Clara, CA 95054
         Phone: +1 408-400-1900
         E-mail: support@ipinfusion.com
         Web: http://www.ipinfusion.com/";

    description
        "Data model for management server related configurations";


    revision "2025-09-30" {
        description "Added disable-ssh-port attribute to disable default-ssh port 22";
        reference " 0.1.41.";
    }

    revision "2025-06-17" {
        description "Added disable-default attribute to resolve show running-config issue";
        reference " 0.1.40.";
    }

    revision "2025-04-09" {
        description "Copy right year update ";
        reference " 0.1.39.";
    }

    revision "2025-01-30" {
        description "Introduction of cml bulk-config limit cpu feature";
        reference " 0.1.38.";
    }

    revision "2024-12-04" {
        description "changes for commit-history unset cli to cml commit-history enable";
        reference " 0.1.37.";
    }

    revision "2024-11-25" {
        description "changeg the commit-history cli to cml commit-history";
        reference " 0.1.36.";
    }

    revision "2024-11-20" {
        description "Initial version to include commit-history configs";
        reference " 0.1.35.";
    }

    revision "2024-11-05" {
        description "Add a dependency between netconf callhome debug and callhome enable config";
        reference " 0.1.34.";
    }

    revision "2024-11-04" {
        description "Multiple VRF support added to netconf callhome removing the interface reference";
        reference " 0.1.33.";
    }

    revision "2024-10-14" {
        description "Multiple VRF support added to netconf callhome";
        reference " 0.1.32.";
    }

    revision "2024-10-09" {
        description "Added CML_SKIP_HITLESS_MERGE tag for feature-netconf-ssh and feature-netconf-tls attributes ";
        reference " 0.1.31.";
    }

    revision "2024-10-01" {
        description "Updated when statements to support user-defined VRF in netconf-ssh and netconf-tls";
        reference " 0.1.30.";
    }

    revision "2024-07-04" {
        description "Update to support user-defined VRF in netconf-ssh and netconf-tls";
        reference " 0.1.29.";
    }

    revision "2024-04-19" {
        description "Corrected the unset of callhome feature cli";
        reference " 0.1.28.";
    }

    revision "2024-02-23" {
        description "Corrected when statement condition for callhome, translation and notification-cache feature";
        reference " 0.1.27.";
    }

    revision "2023-12-21" {
        description "Added notification cache configuration";
        reference " 0.1.26.";
    }

    revision "2023-10-16" {
        description "Added implicit delete tag for db-sync issue";
        reference " 0.1.25.";
    }

    revision "2023-10-10" {
        description "Added dependentObject for api ordering issue";
        reference " 0.1.24.";
    }

    revision "2023-09-29" {
        description "Added when expression for callhome";
        reference " 0.1.24.";
    }

    revision "2023-09-04" {
        description "Added separate container for Netconf SSH and Netconf TLS CLI";
        reference " 0.1.23.";
    }

    revision "2023-08-26" {
        description "Removed Netconf CLI and Added new Netconf SSH and Netconf TLS CLI";
        reference " 0.1.22.";
    }

    revision "2023-08-08" {
        description "Commented out when expression temporarily from netcon-translation-config container to unblock ZebmUT translation testing.";
        reference " 0.1.21.";
    }

    revision "2023-08-07" {
        description "Renaming callhome-debug to enable";
        reference " 0.1.20.";
    }

    revision "2023-07-27" {
        description "Update to follow OpenConfig style";
        reference " 0.1.19.";
    }

    revision "2023-07-26" {
        description "Adding HAVE_VRF flag";
        reference " 0.1.18.";
    }

    revision "2023-07-10" {
        description "Adding dependency of callhome and translation with feature netconf";
        reference " 0.1.17.";
    }

    revision "2023-06-15" {
        description "Implementing netconf port feature";
        reference " 0.1.16.";
    }

    revision "2023-06-13" {
        description "Add implicit-delete tag to remove empty config container";
        reference " 0.1.15.";
    }

    revision "2023-05-19" {
        description "Adding translation config and management server type file";
        reference " 0.1.14.";
    }

    revision "2023-05-05" {
        description "Imported cml-data-types for suppress-bulk-notification";
        reference " 0.1.13.";
    }

    revision "2023-01-05" {
        description "Leafref correction for config container";
        reference " 0.1.12.";
    }

    revision "2022-10-17" {
        description "Added netconf-clients empty container as parent for netconf-client list";
        reference " 0.1.11.";
    }

    revision "2022-09-30" {
        description "Move notification severity type to cml-data-types";
        reference " 0.1.10.";
    }

    revision "2022-09-29" {
        description "Updated the name of mrib module in smi-server-modules tag";
        reference " 0.1.9.";
    }

    revision "2022-08-10" {
        description "Debug hierarchy change";
        reference " 0.1.8.";
    }

    revision "2022-07-30" {
        description "Updated implicit delete for config container";
        reference " 0.1.7.";
    }

    revision "2022-07-28" {
        description "Updated smi-server-modules with restructured RIPng module name";
        reference " 0.1.6.";
    }

    revision "2022-07-26" {
        description "Corrected RIP datamodel as per Open Config style";
        reference " 0.1.5.";
    }

    revision "2022-06-20" {
        description "Added the feature tag";
        reference " 0.1.4.";
    }

    revision "2022-06-14" {
        description "Added leafref for management port leaf with interface module and support for retry-max-attemp 0";
        reference " 0.1.3.";
    }

    revision "2022-06-01" {
        description "Updated the yang file with feature";
        reference " 0.1.2.";
    }

    revision "2022-05-13" {
        description "Adding support for non-default management port";
        reference " 0.1.1.";
    }

    revision "2022-04-27" {
        description "Initial version to include callhome configs";
        reference " 0.1.0.";
    }

    grouping debug-config {
        description
            "Grouping for configuration related to debug";
        leaf enable  {
            type  empty;
            description "Enable debugging info for callhome";
        } // END of enable definition.

    } // END of debug-config definition.
    grouping debug-top {
        description
            "Grouping for debug";
        container debug {
            when " /ipi-management-server:netconf-server/ipi-management-server:callhomes/ipi-management-server:callhome/ipi-management-server:config/ipi-management-server:feature-enabled ";
            description
                "NETCONF server debug";
            container config {
                description
                    "Configuration data for debug";
                uses debug-config;
            } // END of config-container definition.
            container state {
                config false;
                description
                    "Operational state data for debug";
                uses debug-config;
            } // END of state-container definition.
        } // END of debug-container definition.
    } // END of debug-top definition.
    grouping netconf-translation-config {
        description
            "Grouping for NETCONF configuration data";
        leaf translation-mode  {
            type  ipi-management-server-types:management_server_translation_type_t;
            description "Enable/disable NETCONF translation";
        } // END of translation-mode definition.

    } // END of netconf-translation-config definition.
    grouping netconf-translation-top {
        description
            "Grouping for NETCONF translation";
        container netconf-translation {
            if-feature feature-list:HAVE_NETCONF;
            if-feature feature-list:HAVE_NETCONF_OC_TRANSLATION;
            description
                "NETCONF translation";
            container config {
                description
                    "Configuration data for NETCONF translation";
                uses netconf-translation-config;
            } // END of config-container definition.
            container state {
                config false;
                description
                    "Operational state data for NETCONF translation";
                uses netconf-translation-config;
            } // END of state-container definition.
        } // END of netconf-translation-container definition.
    } // END of netconf-translation-top definition.
    grouping reconnect-config {
        description
            "Grouping for reconnect related configuration";
        leaf enable  {
            type  empty;
            mandatory true;
            description "specifies whether server will reconnect after client closes the
                        session";
        } // END of enable definition.

        leaf retry-max-attempts  {
            type  uint8 {
                 range "0..255"  {
                    description "0..255: Supported range 0 - 255";
                 }
            }
            default "3";
            description "Specifies the number of retry attempts the server should attempt to
                        the callhome server before giving up. Set 0 to retry infinitely.";
        } // END of retry-max-attempts definition.

        leaf retry-interval  {
            type  uint32 {
                 range "1..86400"  {
                    description "1..86400: Supported range 1 - 86400";
                 }
            }
            units "seconds";
            default "300";
            description "Specifies the number of seconds to wait after a connect attempt to the
                        callhome server has failed";
        } // END of retry-interval definition.

    } // END of reconnect-config definition.
    grouping reconnect-top {
        description
            "Grouping for reconnect";
        container reconnect {
            when " /ipi-management-server:netconf-server/ipi-management-server:callhomes/ipi-management-server:callhome/ipi-management-server:config/ipi-management-server:feature-enabled ";
            description
                "NETCONF server reconnect";
            container config {
                presence "yes";
                description
                    "Configuration data for reconnect";
                uses reconnect-config;
            } // END of config-container definition.
            container state {
                config false;
                description
                    "Operation state data for reconnect";
                uses reconnect-config;
            } // END of state-container definition.
        } // END of reconnect-container definition.
    } // END of reconnect-top definition.
    grouping callhome-endpoint-config {
        description
            "Grouping for endpoint configuration data";
        leaf name  {
            type  string {
                length "1..64";
                pattern "[^?' =,>|]+";
            }
            description "An arbitrary name for the NETCONF listen endpoint";
        } // END of name definition.

        leaf address  {
            type  string {
                length "1..63";
                pattern "[^?' =,>|]+";
            }
            mandatory true;
            description "The host address of the callhome server (IPv4/IPv6 address or Hostname
                        or DNS name)";
        } // END of address definition.

        leaf port  {
            type  inet:port-number {
                 range "1..65535"  {
                    description "1..65535: Supported range 1 - 65535";
                 }
            }
            default "4334";
            description "Callhome server listening port number";
        } // END of port definition.

    } // END of callhome-endpoint-config definition.
    grouping netconf-clients-top {
        description
            "Grouping for NETCONF client data";
        container netconf-clients {
            description
                "NETCONF client data";

            list netconf-client {
            when " /ipi-management-server:netconf-server/ipi-management-server:callhomes/ipi-management-server:callhome/ipi-management-server:config/ipi-management-server:feature-enabled ";
                key "name";
                description
                    "Object list for configuring callhome servers";
                leaf name  {
                    type  leafref {
                        path  "../config/name";
                    }
                    description "An arbitrary name for the NETCONF listen endpoint";
                } // END of name definition.

                container config {
                    description
                        "Configuration data for NETCONF client";
                    uses callhome-endpoint-config;
                } // END of config-container definition.
                container state {
                    config false;
                    description
                        "Operational state data for NETCONF client";
                    uses callhome-endpoint-config;
                } // END of state-container definition.
            } // End of netconf-client-list
        } // END of netconf-clients-container definition.
    } // END of netconf-clients-top definition.
    grouping callhome-config {
        description
            "Grouping for callhome configuration data";
        leaf vrf-name  {
            if-feature feature-list:HAVE_VRF;
            type  leafref {
                path  "/ipi-network-instance:network-instances/ipi-network-instance:network-instance/ipi-vrf:vrf/ipi-vrf:config/ipi-vrf:vrf-name";
            }
            description "VRF Name associated with this instance";
        } // END of vrf-name definition.

        leaf feature-enabled  {
            type  empty;
            mandatory true;
            description "Enable callhome feature on the NETCONF server";
        } // END of feature-enabled definition.

    } // END of callhome-config definition.
    grouping callhome-top {
        description
            "Grouping for callhome";
        container callhomes {
            if-feature feature-list:HAVE_NETCONF;
            description
                "Callhome related data";

            list callhome {
            // when " ipi-management-server:netconf-server/callhomes/callhome/config/feature-enabled ";
                key "vrf-name";
                max-elements 8;
                description
                    "List of callhomes";
                leaf vrf-name  {
                    type  leafref {
                        path  "../config/vrf-name";
                    }
                    description "Use this attribute to specify the VRF for which NETCONF callhome
                                feature is enabled";
                } // END of vrf-name definition.

                container config {
                    description
                        "Configuration data for callhome attributes";
                    uses callhome-config;
                } // END of config-container definition.
                container state {
                    config false;
                    description
                        "Operational state data for callhome callhome related attributes";
                    uses callhome-config;
                } // END of state-container definition.
                uses netconf-clients-top;
                uses reconnect-top;
                uses debug-top;
            } // End of callhome-list
        } // END of callhomes-container definition.
    } // END of callhome-top definition.
    grouping netconf-server-subsystem-config {
        description
            "NETCONF server configuration";
        leaf vrf-name  {
            if-feature feature-list:HAVE_VRF;
            type  leafref {
                path  "/ipi-network-instance:network-instances/ipi-network-instance:network-instance/ipi-vrf:vrf/ipi-vrf:config/ipi-vrf:vrf-name";
            }
            description "VRF Name associated with this instance";
        } // END of vrf-name definition.

    } // END of netconf-server-subsystem-config definition.
    grouping netconf-ssh-server-config {
        description
            "NETCONF SSH server configuration";
        leaf feature-netconf-ssh  {
            if-feature feature-list:HAVE_NETCONF;
            type  empty;
            description "Use this attribute to enable or disable NETCONF SSH feature.";
        } // END of feature-netconf-ssh definition.

        leaf ssh-port  {
            if-feature feature-list:HAVE_NETCONF;
            type  uint32 {
                 range "1024..65535"  {
                    description "1024..65535: Supported range 1024 - 65535";
                 }
            }
            description "Use this attribute to set the ssh-port number on which the NETCONF
                        server listens for connections. The default port on which the
                        netconf-ssh server listens is 830.";
        } // END of ssh-port definition.

        leaf disable-default-ssh-port  {
            if-feature feature-list:HAVE_NETCONF;
            type  empty;
            description "Use this attribute to disable the ssh-port number on which the NETCONF
                        server listens for connections. The default port on which the
                        netconf-ssh server listens is 22/830. Hence disabling 22.";
        } // END of disable-default-ssh-port definition.

    } // END of netconf-ssh-server-config definition.
    grouping netconf-ssh-server-top {
        description
            "NETCONF SSH server configuration";
        container netconf-ssh-config {
            description
                "NETCONF SSH server data";
            container config {
                description
                    "Configuration data for NETCONF SSH SERVER";
                uses netconf-ssh-server-config;
            } // END of config-container definition.
            container state {
                config false;
                description
                    "Operational state data for NETCONF SSH Server";
                uses netconf-ssh-server-config;
            } // END of state-container definition.
        } // END of netconf-ssh-config-container definition.
    } // END of netconf-ssh-server-top definition.
    grouping netconf-tls-server-config {
        description
            "NETCONF TLS server configuration";
        leaf feature-netconf-tls  {
            if-feature feature-list:HAVE_NETCONF;
            type  empty;
            description "Use this attribute to enable or disable NETCONF TLS feature.";
        } // END of feature-netconf-tls definition.

        leaf tls-port  {
            if-feature feature-list:HAVE_NETCONF;
            type  uint32 {
                 range "1024..65535"  {
                    description "1024..65535: Supported range 1024 - 65535";
                 }
            }
            description "Use this attribute to set the tls-port number on which the NETCONF
                        server listens for connections. The default port on which the
                        netconf-tls server listens is 6513.";
        } // END of tls-port definition.

    } // END of netconf-tls-server-config definition.
    grouping netconf-tls-server-top {
        description
            "NETCONF TLS server configuration";
        container netconf-tls-config {
            description
                "NETCONF TLS server data";
            container config {
                description
                    "Configuration data for NETCONF TLS SERVER";
                uses netconf-tls-server-config;
            } // END of config-container definition.
            container state {
                config false;
                description
                    "Operational state data for NETCONF TLS Server";
                uses netconf-tls-server-config;
            } // END of state-container definition.
        } // END of netconf-tls-config-container definition.
    } // END of netconf-tls-server-top definition.
    grouping netconf-server-subsystem-top {
        description
            "Grouping for NETCONF subsystem related configuration";
        container vrfs {
            if-feature feature-list:HAVE_NETCONF;
            if-feature feature-list:HAVE_VRF;
            description
                "NETCONF server VRF configurations";

            list vrf {
                key "vrf-name";
                description
                    "NETCONF server VRF instance configurations";
                leaf vrf-name  {
                    type  leafref {
                        path  "../config/vrf-name";
                    }
                    description "Use this attribute to specify the VRF for which NETCONF feature is
                                enabled";
                } // END of vrf-name definition.

                container config {
                    description
                        "config container for NETCONF server VRF instance configurations";
                    uses netconf-server-subsystem-config;
                } // END of config-container definition.
                container state {
                    config false;
                    description
                        "state container for NETCONF server VRF instance configurations";
                    uses netconf-server-subsystem-config;
                } // END of state-container definition.
                uses netconf-ssh-server-top;
                uses netconf-tls-server-top;
            } // End of vrf-list
        } // END of vrfs-container definition.
    } // END of netconf-server-subsystem-top definition.
    grouping netconf-ssh-default-config {
        description
            "netconf-ssh feature disable default configuration";
        leaf netconf-ssh-disable-default-instance  {
            if-feature feature-list:HAVE_NETCONF;
            type  empty;
            description "Use this attribute to prevent default netconf-ssh server config from
                        being enabled at start up";
        } // END of netconf-ssh-disable-default-instance definition.

    } // END of netconf-ssh-default-config definition.
    grouping netconf-ssh-default-top {
        description
            "netconf-ssh disable default configuration";
        container netconf-ssh-default-instance {
            if-feature feature-list:HAVE_NETCONF;
            description
                "netconf-ssh default container configuration";
            container config {
                if-feature feature-list:HAVE_NETCONF;
                description
                    "Configuration data for netconf-ssh disable-default configuration";
                uses netconf-ssh-default-config;
            } // END of config-container definition.
            container state {
                config false;
                description
                    "Operational state data for netconf-ssh configuration";
                uses netconf-ssh-default-config;
            } // END of state-container definition.
        } // END of netconf-ssh-default-instance-container definition.
    } // END of netconf-ssh-default-top definition.
    grouping netconf-tls-default-config {
        description
            "netconf-tls feature disable default configuration";
        leaf netconf-tls-disable-default-instance  {
            type  empty;
            description "Use this attribute to prevent default netconf-tls server config from
                        being enabled at start up";
        } // END of netconf-tls-disable-default-instance definition.

    } // END of netconf-tls-default-config definition.
    grouping netconf-tls-default-top {
        description
            "netconf-tls disable default configuration";
        container netconf-tls-default-instance {
            if-feature feature-list:HAVE_NETCONF;
            description
                "netconf-tls default container configuration";
            container config {
                description
                    "Configuration data for netconf-tls disable-default configuration";
                uses netconf-tls-default-config;
            } // END of config-container definition.
            container state {
                config false;
                description
                    "Operational state data for netconf-tls configuration";
                uses netconf-tls-default-config;
            } // END of state-container definition.
        } // END of netconf-tls-default-instance-container definition.
    } // END of netconf-tls-default-top definition.
    grouping notification-cache-config {
        description
            "Grouping for notification cache configuration data";
        leaf feature-enabled  {
            type  empty;
            mandatory true;
            description "Enable notification cache feature on the NETCONF server";
        } // END of feature-enabled definition.

        leaf max-cache-notifications  {
            type  uint16 {
                 range "0..10000"  {
                    description "0..10000: Supported range 0 - 10000";
                 }
            }
            default "100";
            description "Specifies the maximum number of notifications those can be stored in
                        cache. Set 0 for infinite notifications.";
        } // END of max-cache-notifications definition.

        leaf cache-period  {
            type  uint32 {
                 range "1..3600"  {
                    description "1..3600: Supported range 1 - 3600";
                 }
            }
            units "seconds";
            default "1200";
            description "Specifies the number of seconds, cmld store notification messages in
                        cache since it started";
        } // END of cache-period definition.

    } // END of notification-cache-config definition.
    grouping notification-cache-top {
        description
            "Grouping for notification cache";
        container notification-cache {
            if-feature feature-list:HAVE_NETCONF;
            description
                "notification cache related data";
            container config {
                presence "yes";
                description
                    "Configuration data for notification cache attributes";
                uses notification-cache-config;
            } // END of config-container definition.
            container state {
                config false;
                description
                    "Operational state data for notification cache related attributes";
                uses notification-cache-config;
            } // END of state-container definition.
        } // END of notification-cache-container definition.
    } // END of notification-cache-top definition.
    grouping commit-history-config {
        description
            "grouping for commit confirmed feature configurations";
        leaf disable-commit-history  {
            type  empty;
            description "This attribute is used to disable features like commit confirmed and
                        commit rollback";
        } // END of disable-commit-history definition.

    } // END of commit-history-config definition.
    grouping commit-history-top {
        description
            "grouping for commit confirmed feature";
        container commit-history {
            description
                "Top level container for commit history configurations";
            container config {
                description
                    "Configuration data for commit-history";
                uses commit-history-config;
            } // END of config-container definition.
            container state {
                config false;
                description
                    "commit-history operational state data";
                uses commit-history-config;
            } // END of state-container definition.
        } // END of commit-history-container definition.
    } // END of commit-history-top definition.
    grouping cml-bulk-config {
        description
            "grouping for cml bulk configurations cpu usage limit";
        leaf bulk-config-cpu-limit-enabled  {
            type  empty;
            description "This attribute is used to enable and disable bulk config cpu limit";
        } // END of bulk-config-cpu-limit-enabled definition.

    } // END of cml-bulk-config definition.
    grouping cml-bulk-config-top {
        description
            "grouping for cml bulk-config limit cpu feature";
        container bulk-config {
            description
                "Top level container for cml bulk-config";
            container config {
                description
                    "Configuration data for cml bulk-config";
                uses cml-bulk-config;
            } // END of config-container definition.
            container state {
                config false;
                description
                    "bulk-config operational state data";
                uses cml-bulk-config;
            } // END of state-container definition.
        } // END of bulk-config-container definition.
    } // END of cml-bulk-config-top definition.

    grouping  netconf-server-grouping {
    description
        "Top level container for NETCONF server configurations";
    container netconf-server {
        if-feature feature-list:HAVE_CMLD;
        description
            "Top level container for NETCONF server configurations";
        uses callhome-top;
        uses netconf-translation-top;
        uses netconf-server-subsystem-top;
        uses netconf-tls-default-top;
        uses netconf-ssh-default-top;
        uses notification-cache-top;
        uses commit-history-top;
        uses cml-bulk-config-top;
    } // END of netconf-server-container definition.
    } // END of netconf-server-grouping definition.

    uses netconf-server-grouping;
    uses management-server-grouping;

    notification suppress-bulk-notification {
        if-feature feature-list:HAVE_CMLD;

        description "Send notification when bulk notifications are suppressed..";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

}
