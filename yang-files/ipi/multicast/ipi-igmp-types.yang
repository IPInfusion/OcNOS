/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-igmp-types.yang
*
*/

module ipi-igmp-types {

    yang-version 1.1;

    namespace   "http://www.ipinfusion.com/yang/ocnos/ipi-igmp-types";

    prefix "ipi-igmp-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "This defines types related to IGMP module";


    revision "2022-06-01" {
        description "Updated the yang file with feature";
        reference " 0.3.0.";
    }

    revision "2022-02-07" {
        description "Renamed CML_YES_NO_T to IGMP_YES_NO_T";
        reference " 0.2.0.";
    }

    revision "2021-11-15" {
        description "Initial Version";
        reference " 0.1.0.";
    }



    typedef  igmp_yes_no_t {
        type enumeration {
            enum no {
                value 0;
                description "no";
            }
            enum yes {
                value 1;
                description "yes";
            }
        }
        description "type definition for IGMP_YES_NO_T";
    }

    typedef  igmp_debug_options_t {
        type bits {
            bit decode {
                position 0;
                description "None";
            }
            bit encode {
                position 1;
                description "None";
            }
            bit events {
                position 2;
                description "None";
            }
            bit fsm {
                position 3;
                description "None";
            }
            bit tib {
                position 4;
                description "None";
            }
        }
        description "type definition for IGMP_DEBUG_OPTIONS_T";
    }

    typedef  igmp_if_oper_status_t {
        type enumeration {
            enum Active {
                value 1;
                description "Active";
            }
            enum Inactive {
                value 2;
                description "Inactive";
            }
        }
        description "type definition for IGMP_IF_OPER_STATUS_T";
    }

    typedef  igmp_proxy_if_oper_status_t {
        type enumeration {
            enum up {
                value 1;
                description "Up";
            }
            enum down {
                value 2;
                description "Down";
            }
        }
        description "type definition for IGMP_PROXY_IF_OPER_STATUS_T";
    }

    typedef  igmp_if_state_t {
        type enumeration {
            enum Active {
                value 1;
                description "Active";
            }
            enum Inactive {
                value 2;
                description "Inactive";
            }
        }
        description "type definition for IGMP_IF_STATE_T";
    }

    typedef  igmp_proxy_grp_membership_state_t {
        type enumeration {
            enum Idle {
                value 1;
                description "Idle";
            }
            enum Delay {
                value 2;
                description "Delay";
            }
        }
        description "type definition for IGMP_PROXY_GRP_MEMBERSHIP_STATE_T";
    }

    typedef  igmp_static_ssm_map_t {
        type enumeration {
            enum ssm-map {
                value 1;
                description "ssm mapping";
            }
        }
        description "type definition for IGMP_STATIC_SSM_MAP_T";
    }

    typedef  igmp_static_ssm_source_t {
        type union {
            type igmp_static_ssm_map_t {

            }
            type inet:ipv4-address {

            }
        }
        description "type definition for IGMP_STATIC_SSM_SOURCE_T";
    }

    typedef  igmp_ssm_group_mode_t {
        type enumeration {
            enum Invalid {
                value 0;
                description "None";
            }
            enum Include {
                value 1;
                description "None";
            }
            enum Exclude {
                value 2;
                description "None";
            }
            enum Max {
                value 3;
                description "None";
            }
        }
        description "type definition for IGMP_SSM_GROUP_MODE_T";
    }

}
