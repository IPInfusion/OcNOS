/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mld-snooping.yang
*
*/

module ipi-mld-snooping {

    yang-version 1.1;

    namespace   "http://www.ipinfusion.com/yang/ocnos/ipi-mld-snooping";

    prefix "ipi-mld-snooping";

    import ipi-mld-snooping-types {
        prefix ipi-mld-snooping-types;
        revision-date 2022-06-01;
    }

    import ipi-interface {
        prefix ipi-interface;
        revision-date 2026-03-10;
    }

    import ipi-bridge {
        prefix ipi-bridge;
        revision-date 2026-07-30;
    }

    import ipi-network-instance {
        prefix ipi-network-instance;
        revision-date 2026-08-12;
    }

    import cml-data-types {
        prefix cml-data-types;
        revision-date 2026-05-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for MLD Snooping object";


    revision "2024-02-02" {
        description "Modified custom-error-code for disable-report-suppression on DUNE platforms";
        reference " 0.7.0.";
    }

    revision "2023-06-01" {
        description "Adding mld snooping report suppression attribute in CONFIG_MODE";
        reference " 0.6.0.";
    }

    revision "2023-02-20" {
        description "Added When tag for no-debug-all command";
        reference " 0.5.0.";
    }

    revision "2022-12-01" {
        description "Updated when expressions";
        reference " 0.4.3.";
    }

    revision "2022-08-10" {
        description "Debug hierarchy change";
        reference " 0.4.2.";
    }

    revision "2022-08-03" {
        description "Removing when expression for mrouter-interface-name,Added notification to remove mrouter-interface-name vlan port is removed";
        reference " 0.4.1.";
    }

    revision "2022-07-30" {
        description "Updated when expressions in yang";
        reference " 0.4.0.";
    }

    revision "2022-06-01" {
        description "Updated the yang file with feature";
        reference " 0.3.0.";
    }

    revision "2022-01-31" {
        description "Restructured module as per OpenConfig style";
        reference " 0.2.0.";
    }

    revision "2018-06-21" {
        description "Initial Version";
        reference " 0.1.0.";
    }

    grouping mld-snooping-global-config {
        description
            "MLD Snooping global configurations";
        leaf disable-mld-snooping  {
            when " /ipi-network-instance:network-instances/ipi-network-instance:network-instance/ipi-bridge:bridge/ipi-bridge:config ";
            type  empty;
            description "Use this attribute to enable MLD Snooping. When this command is given
                        in the Configure mode,
                        MLD Snooping is enabled at the switch level. When this attribute is
                        given at the VLAN interface level,
                        5MLD Snooping is enabled for that VLAN.";
        } // END of disable-mld-snooping definition.

        leaf disable-report-suppression  {
            type  empty;
            description "Use this attribute to enable report suppression for MLD version 1.";
        } // END of disable-report-suppression definition.

    } // END of mld-snooping-global-config definition.
    grouping mld-snooping-debug-config {
        description
            "MLD Snooping debug configurations";
        leaf options  {
            type  ipi-mld-snooping-types:mld_snoop_debug_options_t;
            description "Use this attribute to enable mld snooping debugging configurations";
        } // END of options definition.

    } // END of mld-snooping-debug-config definition.
    grouping mld-snooping-terminal-debug-state {
        description
            "MLD Snooping debug state information";
        leaf terminal-debug-status  {
            type  ipi-mld-snooping-types:mld_snoop_debug_options_t;
            description "Use this attribute to display mld snooping terminal debugging
                        information.";
        } // END of terminal-debug-status definition.

    } // END of mld-snooping-terminal-debug-state definition.
    grouping mld-snooping-interface-config {
        description
            "MLD Snooping interface configurations";
        leaf name  {
            type  leafref {
                path  "/ipi-interface:interfaces/ipi-interface:interface/ipi-interface:name";
            }
            description "This attribute defines the interface where MLD Snooping is configured";
        } // END of name definition.

        leaf mld-snooping  {
            type  cml-data-types:cml_enable_disable_t;
            default "enable";
            description "Use this attribute to enable MLD Snooping. When this attribute is
                        given at the VLAN interface level,
                        MLD Snooping is enabled for that VLAN.";
        } // END of mld-snooping definition.

        leaf enable-fast-leave  {
            type  empty;
            description "Use this attribute to enable MLD Snooping fast-leave processing.
                        Fast-leave processing is analogous to immediateleave processing the
                        MLD group-membership is removed,
                        as soon as an MLD leave group message is received without sending out
                        a group-specific query.";
        } // END of enable-fast-leave definition.

        leaf report-suppression  {
            type  cml-data-types:cml_enable_disable_t;
            description "Use this attribute to enable or disable report suppression for MLD
                        version 1, and 2 reports. By default report suppression is enabled.";
        } // END of report-suppression definition.

        leaf-list mrouter-interface-name  {
            type  leafref {
                path  "/ipi-interface:interfaces/ipi-interface:interface/ipi-interface:name";
            }
            description "Use this attribute to statically configure the specified VLAN
                        constituent interface
                        as a multicast router interface for MLD Snooping in that VLAN";
        } // END of mrouter-interface-name definition.

        leaf enable-querier  {
            type  empty;
            description "Use this attribute to enable MLD querier operation on a subnet (VLAN)
                        when no multicast routing protocol is configured in the subnet VLAN.
                        When enabled, the MLD Snooping querier sends out periodic MLD queries
                        for all interfaces on that VLAN.
                        The MLD Snooping querier uses the 0.0.0.0 source IP address, because
                        it masquerades as a proxy MLD querier for faster network convergence.
                        It does not start or automatically cease the MLD querier operation if
                        it detects a query message from a multicast router.
                        It restarts as MLD snooping querier if no queries are seen within
                        another querier interval";
        } // END of enable-querier definition.

    } // END of mld-snooping-interface-config definition.
    grouping mld-snooping-interfaces-top {
        description
            "MLD Snooping Interface Top Configurations";
        container interfaces {
            description
                "MLD Snooping Interface Configurations";

            list interface {
            // when " not(/ipi-interface:interfaces/ipi-interface:interface/ipi-interface:config/ipi-interface:enable-switchport) ";
                key "name";
                description
                    "MLD Snooping Interface instance configurations";
                leaf name  {
                    type  leafref {
                        path  "../config/name";
                    }
                    description "This attribute defines the interface where MLD Snooping is configured";
                } // END of name definition.

                container config {
                    description
                        "MLD Snooping config container for interface configurations";
                    uses mld-snooping-interface-config;
                } // END of config-container definition.
                container state {
                    config false;
                    description
                        "MLD Snooping state container for interface configurations";
                    uses mld-snooping-interface-config;
                } // END of state-container definition.
            } // End of interface-list
        } // END of interfaces-container definition.
    } // END of mld-snooping-interfaces-top definition.
    grouping mld-snooping-top {
        description
            "MLD Snooping Configurations";
        container global {
            description
                "MLD Snooping Global Configurations";
            container config {
                description
                    "MLD Snooping config container for global configurations";
                uses mld-snooping-global-config;
            } // END of config-container definition.
            container state {
                config false;
                description
                    "MLD Snooping state container for global configurations";
                uses mld-snooping-global-config;
            } // END of state-container definition.
        } // END of global-container definition.
        container debug {
            description
                "MLD Snooping Debug Configurations";
            container config {
                description
                    "MLD Snooping config container for debug configurations";
                uses mld-snooping-debug-config;
            } // END of config-container definition.
            container state {
                config false;
                description
                    "MLD Snooping state container for debug configurations";
                uses mld-snooping-debug-config;
                uses mld-snooping-terminal-debug-state;
            } // END of state-container definition.
        } // END of debug-container definition.
    } // END of mld-snooping-top definition.

    grouping  mld-snooping-grouping {
    description
        "MLD Snooping Top Container";
    container mld-snooping {
        when " /ipi-network-instance:network-instances/ipi-network-instance:network-instance/ipi-bridge:bridge/ipi-bridge:config/ipi-bridge:protocol ";
        if-feature feature-list:HAVE_L2MRIBD;
        if-feature feature-list:HAVE_MLD_SNOOP;
        description
            "MLD Snooping Top Container";
        uses mld-snooping-top;
        uses mld-snooping-interfaces-top;
    } // END of mld-snooping-container definition.
    } // END of mld-snooping-grouping definition.

    uses mld-snooping-grouping;

    rpc mld-snooping-terminal-debug-on {
        if-feature feature-list:HAVE_MLD_SNOOP;
        if-feature feature-list:HAVE_L2MRIBD;
        description "Use this RPC to enable terminal debugging options for MLD Snooping";
        input  {
            leaf terminal-debug-options  {
                type ipi-mld-snooping-types:mld_snoop_debug_options_t;
                mandatory true;
                description "Use this attribute to enable mld snooping debugging configurations";
            }
        }
    }

    rpc mld-snooping-terminal-debug-off {
        if-feature feature-list:HAVE_MLD_SNOOP;
        if-feature feature-list:HAVE_L2MRIBD;
        description "Use this RPC to disable terminal debugging options for MLD Snooping";
        input  {
            leaf terminal-debug-options  {
                type ipi-mld-snooping-types:mld_snoop_debug_options_t;
                mandatory true;
                description "Use this attribute to enable mld snooping debugging configurations";
            }
        }
    }

    rpc mld-snooping-clear-group-on-interface {
        if-feature feature-list:HAVE_MLD_SNOOP;
        if-feature feature-list:HAVE_L2MRIBD;
        description "This RPC is used to clear the given group membership on the specified
                    interface";
        input  {
            leaf group-address  {
                type string;
                mandatory true;
                description "Multicast Group Address";
            }
            leaf interface-name  {
                type string;
                mandatory true;
                description "Interface Name";
            }
        }
    }

    rpc mld-snooping-clear-all-groups-on-interface {
        if-feature feature-list:HAVE_MLD_SNOOP;
        if-feature feature-list:HAVE_L2MRIBD;
        description "Use this RPC to clear all MLD snooping entries for a given interface";
        input  {
            leaf interface-name  {
                type string;
                mandatory true;
                description "Interface Name";
            }
        }
    }

    rpc mld-snooping-clear-group {
        if-feature feature-list:HAVE_MLD_SNOOP;
        if-feature feature-list:HAVE_L2MRIBD;
        description "Use this RPC to clear MLD snooping entry for specified group address";
        input  {
            leaf group-address  {
                type string;
                mandatory true;
                description "Multicast Group Address";
            }
        }
    }

    rpc mld-snooping-clear-all-groups {
        if-feature feature-list:HAVE_MLD_SNOOP;
        if-feature feature-list:HAVE_L2MRIBD;
        description "Use this RPC to clear all MLD snooping entries on the device";
    }

}
