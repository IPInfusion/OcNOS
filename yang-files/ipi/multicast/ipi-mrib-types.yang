/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mrib-types.yang
*
*/

module ipi-mrib-types {

    yang-version 1.1;

    namespace   "http://www.ipinfusion.com/yang/ocnos/ipi-mrib-types";

    prefix "ipi-mrib-types";

    organization
        "IP Infusion Inc.";

    contact
        "Address: 3965 Freedom Circle, Suite 200, Santa Clara, CA 95054
         Phone: +1 408-400-1900
         E-mail: support@ipinfusion.com
         Web: http://www.ipinfusion.com/";

    description
        "Definitions types for the MRIB Datamodel";


    revision "2023-04-06" {
        description "MRIB_ROUTE_TYPE_T Enum updated with reference to IANAipMRouteProtocol";
        reference " 0.4.0.";
    }

    revision "2022-06-01" {
        description "Updated the yang file with feature";
        reference " 0.3.0.";
    }

    revision "2022-05-18" {
        description "Added Netconf GetAPI support for multicast routing table entries";
        reference " 0.2.0.";
    }

    revision "2021-12-02" {
        description "Initial Version";
        reference " 0.1.0.";
    }



    typedef  mrib_debug_t {
        type bits {
            bit event {
                position 0;
                description "None";
            }
            bit vif {
                position 1;
                description "None";
            }
            bit mrt {
                position 2;
                description "None";
            }
            bit stats {
                position 3;
                description "None";
            }
            bit fib-msg {
                position 4;
                description "None";
            }
            bit register-msg {
                position 5;
                description "None";
            }
            bit nsm-msg {
                position 6;
                description "None";
            }
            bit mrib-msg {
                position 7;
                description "None";
            }
            bit mtrace {
                position 8;
                description "None";
            }
            bit mtrace-detail {
                position 9;
                description "None";
            }
        }
        description "type definition for MRIB_DEBUG_T";
    }

    typedef  mrib_route_type_t {
        type enumeration {
            enum OTHER {
                value 1;
                description "OTHER";
            }
            enum LOCAL {
                value 2;
                description "LOCAL";
            }
            enum NETMGMT {
                value 3;
                description "NETMGMT";
            }
            enum DVMRP {
                value 4;
                description "DVMRP";
            }
            enum MOSPF {
                value 5;
                description "MOSPF";
            }
            enum PIM_SPARSE_DENSE {
                value 6;
                description "PIM_SPARSE_DENSE";
            }
            enum CBT {
                value 7;
                description "CBT";
            }
            enum PIM_SPARSE_MODE {
                value 8;
                description "PIM_SPARSE_MODE";
            }
            enum PIM_DENSE_MODE {
                value 9;
                description "PIM_DENSE_MODE";
            }
            enum IGMP_ONLY {
                value 10;
                description "IGMP_ONLY";
            }
            enum BGMP {
                value 11;
                description "BGMP";
            }
            enum MSDP {
                value 12;
                description "MSDP";
            }
        }
        description "type definition for MRIB_ROUTE_TYPE_T";
    }

}
