/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mld.yang
*
*/

module ipi-mld {

    yang-version 1.1;

    namespace   "http://www.ipinfusion.com/yang/ocnos/ipi-mld";

    prefix "ipi-mld";

    import ietf-inet-types {
        prefix inet;
        revision-date 2013-07-15;
    }

    import ietf-yang-types {
        prefix yang;
        revision-date 2013-07-15;
    }

    import ipi-network-instance {
        prefix ipi-network-instance;
        revision-date 2026-08-12;
    }

    import ipi-vrf {
        prefix ipi-vrf;
        revision-date 2026-08-12;
    }

    import ipi-mld-types {
        prefix ipi-mld-types;
        revision-date 2022-06-01;
    }

    import feature-list {
        prefix feature-list;
        revision-date 2026-09-15;
    }

    include ipi-mld-interface { revision-date 2023-02-17;}
    include ipi-mld-groups { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Data model for MLD Module";


    revision "2023-04-20" {
        description "updated arguments for mld-clear-group-on-interface";
        reference " 0.5.0.";
    }

    revision "2023-02-20" {
        description "Added When tag for no-debug-all command";
        reference " 0.4.1.";
    }

    revision "2023-02-17" {
        description "Fixed prependstr warning";
        reference " 0.4.0.";
    }

    revision "2022-07-30" {
        description "Updated when expressions in yang";
        reference " 0.3.2.";
    }

    revision "2022-06-20" {
        description "Added custom-error-code to disable-ssm-map attribute";
        reference " 0.3.1.";
    }

    revision "2022-06-01" {
        description "Updated the yang file with feature";
        reference " 0.3.0.";
    }

    revision "2022-03-09" {
        description "Restructured module in accordance with OpenConfig style";
        reference " 0.2.0.";
    }

    revision "2018-06-21" {
        description "Initial Version";
        reference " 0.1.0.";
    }

    grouping mld-instance-config {
        description
            "MLD Instance Configurations";
        leaf vrf-name  {
            type  leafref {
                path  "/ipi-network-instance:network-instances/ipi-network-instance:network-instance/ipi-vrf:vrf/ipi-vrf:config/ipi-vrf:vrf-name";
            }
            description "VPN routing/forwarding Instance name";
        } // END of vrf-name definition.

        leaf disable-ssm-map  {
            type  empty;
            description "Use this attribute to enable/disable SSM mapping on the router";
        } // END of disable-ssm-map definition.

    } // END of mld-instance-config definition.
    grouping mld-group-membership-config {
        description
            "MLD Group Membership Configurations";
        leaf member-limit  {
            type  uint32 {
                 range "1..2097152"  {
                    description "1..2097152: Supported range 1 - 2097152";
                 }
            }
            default "1";
            description "Use this attribute to set the maximum number of group membership
                        states at the router level.
                        Once the specified number of group memberships is reached, all further
                        local-memberships are ignored.
                        Optionally, an exception access-list can be configured to specify the
                        group-address(es) to be excluded from being subject to the limit.
                        This command applies to interfaces configured for MLD Layer-3
                        multicast protocols and MLD Proxy. The limit applies,
                        individually, to each of its constituent interfaces.";
        } // END of member-limit definition.

        leaf limit-exception-acl  {
            // when " ipi-mld:mld/vrfs/vrf/group-membership-control/config/member-limit ";
            type  string {
                length "1..1965";
                pattern "[^?' =,>|]+";
            }
            description "Use this attribute to set the maximum number of group membership
                        states at the router level.
                        Once the specified number of group memberships is reached, all further
                        local-memberships are ignored.
                        Optionally, an exception access-list can be configured to specify the
                        group-address(es) to be excluded from being subject to the limit.
                        This command applies to interfaces configured for MLD Layer-3
                        multicast protocols and MLD Proxy. The limit applies,
                        individually, to each of its constituent interfaces.";
        } // END of limit-exception-acl definition.

    } // END of mld-group-membership-config definition.
    grouping mld-group-membership-state {
        description
            "MLD Group Membership State Information";
        leaf current-states-count  {
            type  yang:counter32;
            description "Current group membership record states for this MLD instance.";
        } // END of current-states-count definition.

    } // END of mld-group-membership-state definition.
    grouping mld-instance-ssm-map-config {
        description
            "MLD Instance SSM Map Configurations";
        leaf group-ranges-acl  {
            type  string {
                length "1..1965";
                pattern "[^?' =,>|]+";
            }
            description "Use this attribute to specify SSM Static Access List";
        } // END of group-ranges-acl definition.

        leaf source  {
            type  inet:ipv6-address;
            description "Use this attribute to specify the static mcast source for SSM mapping.
                        SSM mapping statically assigns sources to MLDv1 groups to translate
                        such (star G) groups memberships
                        to (S,G) memberships for use with PIM-SSM. This attribute applies to
                        interfaces configured
                        for MLD Layer-3 multicast protocols and MLD Proxy.";
        } // END of source definition.

    } // END of mld-instance-ssm-map-config definition.
    grouping mld-debug-config {
        description
            "MLD debug configurations";
        leaf debug-options  {
            type  ipi-mld-types:mld_debug_options_t;
            description "Use this attribute to enable mld debugging configurations";
        } // END of debug-options definition.

    } // END of mld-debug-config definition.
    grouping mld-debug-state {
        description
            "MLD debug state information";
        leaf terminal-debug-status-on  {
            type  ipi-mld-types:mld_debug_options_t;
            description "Use this attribute to display mld terminal debug options enabled";
        } // END of terminal-debug-status-on definition.

    } // END of mld-debug-state definition.

    grouping  mld-grouping {
    description
        "Top level container for MLD configurations and operational data";
    container mld {
        if-feature feature-list:HAVE_MCAST_IPV6;
        if-feature feature-list:NOT_HAVE_DUNE_OR_HAVE_DNX;
        description
            "Top level container for MLD configurations and operational data";
        container vrfs {
            description
                "MLD VRFs top level container";

            list vrf {
                key "vrf-name";
                description
                    "MLD VRF instance configurations";
                leaf vrf-name  {
                    type  leafref {
                        path  "../config/vrf-name";
                    }
                    description "VPN routing/forwarding Instance name";
                } // END of vrf-name definition.

                container config {
                    description
                        "config container for MLD vrf instance configurations";
                    uses mld-instance-config;
                } // END of config-container definition.
                container state {
                    config false;
                    description
                        "state container for MLD vrf instance configurations";
                    uses mld-instance-config;
                } // END of state-container definition.
                container group-membership-control {
                    description
                        "MLD Group Membership Control Configurations";
                    container config {
                        description
                            "config container for MLD group membership control configurations";
                        uses mld-group-membership-config;
                    } // END of config-container definition.
                    container state {
                        config false;
                        description
                            "state container for MLD group membership control configurations";
                        uses mld-group-membership-config;
                        uses mld-group-membership-state;
                    } // END of state-container definition.
                } // END of group-membership-control-container definition.
                container ssm {
                    description
                        "MLD SSM Configurations";
                    container static-mappings {
                        description
                            "MLD Static-Mappings Container";

                        list static-mapping {
                            key "group-ranges-acl source";
                            description
                                "MLD Static-Mapping Instance configurations";
                            leaf group-ranges-acl  {
                                type  leafref {
                                    path  "../config/group-ranges-acl";
                                }
                                description "Use this attribute to specify SSM Static Access List";
                            } // END of group-ranges-acl definition.

                            leaf source  {
                                type  leafref {
                                    path  "../config/source";
                                }
                                description "Use this attribute to specify the static mcast source for SSM mapping.
                                            SSM mapping statically assigns sources to MLDv1 groups to translate
                                            such (star G) groups memberships
                                            to (S,G) memberships for use with PIM-SSM.This attribute applies to
                                            interfaces configured
                                            for MLD Layer-3 multicast protocols and MLD Proxy.";
                            } // END of source definition.

                            container config {
                                description
                                    "config container for MLD static-mapping configurations";
                                uses mld-instance-ssm-map-config;
                            } // END of config-container definition.
                            container state {
                                config false;
                                description
                                    "state container for MLD static-mapping configurations";
                                uses mld-instance-ssm-map-config;
                            } // END of state-container definition.
                        } // End of static-mapping-list
                    } // END of static-mappings-container definition.
                } // END of ssm-container definition.
                container debug {
                    description
                        "MLD Debug Configurations";
                    container config {
                        description
                            "config container for MLD debug configurations";
                        uses mld-debug-config;
                    } // END of config-container definition.
                    container state {
                        config false;
                        description
                            "state container for MLD debug configurations";
                        uses mld-debug-config;
                        uses mld-debug-state;
                    } // END of state-container definition.
                } // END of debug-container definition.
            } // End of vrf-list
        } // END of vrfs-container definition.
        uses interfaces-grouping;
        uses group-membership-tree-grouping;
    } // END of mld-container definition.
    } // END of mld-grouping definition.

    uses mld-grouping;

    rpc mld-terminal-debug-on {
        if-feature feature-list:HAVE_MCAST_IPV6;
        if-feature feature-list:NOT_HAVE_DUNE_OR_HAVE_DNX;
        description "Use this RPC to enable terminal debugging options for MLD";
        input  {
            leaf vrf-name  {
                type string;
                default "default";
                description "VPN routing/forwarding Instance name";
            }
            leaf term-debug-options  {
                type ipi-mld-types:mld_debug_options_t;
                mandatory true;
                description "Use this attribute to enable MLD terminal debugging options";
            }
        }
    }

    rpc mld-terminal-debug-off {
        if-feature feature-list:HAVE_MCAST_IPV6;
        if-feature feature-list:NOT_HAVE_DUNE_OR_HAVE_DNX;
        description "Use this RPC to disable terminal debugging options for MLD";
        input  {
            leaf vrf-name  {
                type string;
                default "default";
                description "VPN routing/forwarding Instance name";
            }
            leaf term-debug-options  {
                type ipi-mld-types:mld_debug_options_t;
                mandatory true;
                description "Use this attribute to disable MLD terminal debugging options";
            }
        }
    }

    rpc mld-clear-all-groups {
        if-feature feature-list:HAVE_MCAST_IPV6;
        if-feature feature-list:NOT_HAVE_DUNE_OR_HAVE_DNX;
        description "Use this attribute to clear all MLD local-memberships on all
                    interfaces. This applies to interfaces configured for MLD Layer-3
                    multicast protocols, or MLD Proxy.";
        input  {
            leaf vrf-name  {
                type string;
                default "default";
                description "VPN routing/forwarding Instance name";
            }
            leaf clear-all  {
                type empty;
                mandatory true;
                description "Use this attribute to clear all MLD local-memberships on all interface";
            }
        }
    }

    rpc mld-clear-group-on-interface {
        if-feature feature-list:HAVE_MCAST_IPV6;
        if-feature feature-list:NOT_HAVE_DUNE_OR_HAVE_DNX;
        description "Use this RPC to MLD group membership for given interface based on
                    Group Address.             This attributes applies to interfaces
                    configured for MLD Layer-3 multicast protocols, or MLD Proxy";
        input  {
            leaf vrf-name  {
                type string;
                default "default";
                description "VPN routing/forwarding Instance name";
            }
            leaf if-name  {
                type string;
                mandatory true;
                description "Interface Name";
            }
            leaf group-address  {
                type inet:ipv6-address;
                mandatory true;
                description "Group Address";
            }
        }
    }

    rpc mld-clear-all-groups-on-interface {
        if-feature feature-list:HAVE_MCAST_IPV6;
        if-feature feature-list:NOT_HAVE_DUNE_OR_HAVE_DNX;
        description "Use this RPC to clear all MLD local group memberships on the given
                    interface. This applies to interfaces configured for MLD Layer-3
                    multicast protocols, or MLD Proxy.";
        input  {
            leaf vrf-name  {
                type string;
                default "default";
                description "VPN routing/forwarding Instance name";
            }
            leaf if-name  {
                type string;
                mandatory true;
                description "Interface Name";
            }
        }
    }

    rpc mld-clear-group {
        if-feature feature-list:HAVE_MCAST_IPV6;
        if-feature feature-list:NOT_HAVE_DUNE_OR_HAVE_DNX;
        description "Use this RPC to clear all MLD local-memberships for group. This
                    applies to interfaces configured for MLD Layer-3 multicast protocols,
                    or MLD Proxy.";
        input  {
            leaf vrf-name  {
                type string;
                default "default";
                description "VPN routing/forwarding Instance name";
            }
            leaf group-address  {
                type inet:ipv6-address;
                mandatory true;
                description "Group Address";
            }
        }
    }

}
