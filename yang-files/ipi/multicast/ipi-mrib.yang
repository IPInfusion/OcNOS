/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mrib.yang
*
*/

module ipi-mrib {

    yang-version 1.1;

    namespace   "http://www.ipinfusion.com/yang/ocnos/ipi-mrib";

    prefix "ipi-mrib";

    import ipi-mrib-types {
        prefix ipi-mrib-types;
        revision-date 2023-04-06;
    }

    import ietf-inet-types {
        prefix inet;
        revision-date 2013-07-15;
    }

    import feature-list {
        prefix feature-list;
        revision-date 2026-09-15;
    }

    include ipi-mrib-ipv4 { revision-date 2026-08-14;}
    include ipi-mrib-ipv6 { revision-date 2023-04-05;}
    include ipi-mrib-common { revision-date 2023-04-06;}
    organization
        "IP Infusion Inc.";

    contact
        "Address: 3965 Freedom Circle, Suite 200, Santa Clara, CA 95054
         Phone: +1 408-400-1900
         E-mail: support@ipinfusion.com
         Web: http://www.ipinfusion.com/";

    description
        "Datamodel for MRIB object";


    revision "2026-08-14" {
        description "Added rpf-prefer-longest-prefix-match command";
        reference " 0.7.0.";
    }

    revision "2023-04-06" {
        description "MRIB_ROUTE_TYPE_T Enum updated with reference to IANAipMRouteProtocol";
        reference " 0.6.3.";
    }

    revision "2023-04-05" {
        description "CML_SET_ONLY flag added in mrib-ip-vrf-common-route-limit-config for multicast-routes";
        reference " 0.6.2.";
    }

    revision "2023-02-20" {
        description "Added When tag for no-debug-all command in ipv4, ipv6, igmp, mld debug container";
        reference " 0.6.1.";
    }

    revision "2023-02-17" {
        description "Fixed prependstr warning";
        reference " 0.6.0.";
    }

    revision "2023-01-10" {
        description "Supress CLI 'ipv6 multicast ttl-threshold', not supported in kernel";
        reference " 0.5.3.";
    }

    revision "2022-11-03" {
        description "Updated debug container description in sub-modules";
        reference " 0.5.2.";
    }

    revision "2022-08-10" {
        description "Debug hierarchy change";
        reference " 0.5.1.";
    }

    revision "2022-07-30" {
        description "Updated when expressions in yang";
        reference " 0.5.0.";
    }

    revision "2022-07-15" {
        description "Adding CML_CONFIG_RUNTIME flag to mrib-ipv6 interface objectlist";
        reference " 0.4.4.";
    }

    revision "2022-07-06" {
        description "Adding CML_CONFIG_RUNTIME flag to mrib-ipv4 interface objectlist, and correcting outgoing-interface heirarchy";
        reference " 0.4.3.";
    }

    revision "2022-06-28" {
        description "Updated debug object with when tag dependency validation";
        reference " 0.4.2.";
    }

    revision "2022-06-07" {
        description "Added 'rpa-id' attribute to ipi-mrib-common";
        reference " 0.4.1.";
    }

    revision "2022-06-01" {
        description "Updated the yang file with feature";
        reference " 0.4.0.";
    }

    revision "2022-05-23" {
        description "Added Netconf GetAPI support for IPv4 multicast routing table entries";
        reference " 0.3.2.";
    }

    revision "2022-05-18" {
        description "Added Netconf GetAPI support for IPv6 multicast routing table entries";
        reference " 0.3.1.";
    }

    revision "2022-03-17" {
        description "Added restructured MRIB IPv6 datamodel as submodule";
        reference " 0.3.0.";
    }

    revision "2021-12-02" {
        description "Restructured module as per open-config style";
        reference " 0.2.0.";
    }

    revision "2018-06-21" {
        description "Initial Version";
        reference " 0.1.0.";
    }


    grouping  mrib-grouping {
    description
        "Top level container for all multicast RIB configuration and state data";
    container mrib {
        if-feature feature-list:HAVE_MRIBD;
        description
            "Top level container for all multicast RIB configuration and state data";
        uses ipv4-grouping;
        uses ipv6-grouping;
    } // END of mrib-container definition.
    } // END of mrib-grouping definition.

    uses mrib-grouping;

    rpc mrib-ipv4-terminal-debug-on {
        if-feature feature-list:HAVE_MRIBD;
        if-feature feature-list:HAVE_VRF;
        description "RPC to enable IPv4 MRIB terminal debug options";
        input  {
            leaf vrf-name  {
                type string;
                description "vrf name";
            }
            leaf terminal-debug-options  {
                type ipi-mrib-types:mrib_debug_t;
                mandatory true;
                description "Enable IP MRIB debug options";
            }
        }
    }

    rpc mrib-ipv4-terminal-debug-off {
        if-feature feature-list:HAVE_MRIBD;
        if-feature feature-list:HAVE_VRF;
        description "RPC to disable IPv4 MRIB terminal debug options";
        input  {
            leaf vrf-name  {
                type string;
                description "vrf name";
            }
            leaf terminal-debug-options  {
                type ipi-mrib-types:mrib_debug_t;
                mandatory true;
                description "Disable IP MRIB debug options";
            }
        }
    }

    rpc mrib-ipv4-clear-mroute-all {
        if-feature feature-list:HAVE_MRIBD;
        if-feature feature-list:HAVE_VRF;
        description "RPC to to delete entries from the IP multicast routing table.
                    This RPC clears the multicast route entries in the multicast route
                    table and removes the entries from the multicast forwarder.
                    MRIB sends a clear message to the multicast protocols. Each multicast
                    protocol has its own clear multicast route command.
                    The protocol-specific clear command clears multicast routes from the
                    protocol and clears the routes from the MRIB";
        input  {
            leaf vrf-name  {
                type string;
                description "VRF Name";
            }
            leaf all-routes  {
                type empty;
                mandatory true;
                description "All IPv4 multicast route entries";
            }
        }
    }

    rpc mrib-ipv4-clear-mroute-group {
        if-feature feature-list:HAVE_MRIBD;
        if-feature feature-list:HAVE_VRF;
        description "Use this RPC to delete entries from the IP multicast routing table
                    based on Group Address. This attribute clears the multicast route
                    entries in the multicast route table and removes the entries from the
                    multicast forwarder. MRIB sends a clear message to the multicast
                    protocols. Each multicast protocol has its own clear multicast route
                    command. The protocol-specific clear command clears multicast routes
                    from the protocol and clears the routes from the MRIB.";
        input  {
            leaf vrf-name  {
                type string;
                description "VRF Name";
            }
            leaf group-address  {
                type inet:ipv4-address;
                mandatory true;
                description "IPv4 Group Address";
            }
        }
    }

    rpc mrib-ipv4-clear-mroute-source-group {
        if-feature feature-list:HAVE_MRIBD;
        if-feature feature-list:HAVE_VRF;
        description "Use this RPC to delete entries from the IP multicast routing table
                    based on Group Address and Source Address. This attribute clears the
                    multicast route entries in the multicast route table and removes the
                    entries from the multicast forwarder. MRIB sends a clear message to
                    the multicast protocols. Each multicast protocol has its own clear
                    multicast route command. The protocol-specific clear command clears
                    multicast routes from the protocol and clears the routes from the MRIB";
        input  {
            leaf vrf-name  {
                type string;
                description "VRF Name";
            }
            leaf source-address  {
                type inet:ipv4-address;
                mandatory true;
                description "IPv4 Source Address";
            }
            leaf group-address  {
                type inet:ipv4-address;
                mandatory true;
                description "IPv4 Group Address";
            }
        }
    }

    rpc mrib-ipv4-clear-mroute-statistics-all {
        if-feature feature-list:HAVE_MRIBD;
        if-feature feature-list:HAVE_VRF;
        description "Use this RPC to delete entries from the IP multicast routing table.
                    This attribute clears the multicast route entries in the multicast
                    route table and removes the entries from the multicast forwarder. MRIB
                    sends a clear message to the multicast protocols. Each multicast
                    protocol has its own clear multicast route command. The
                    protocol-specific clear command clears multicast routes from the
                    protocol and clears the routes from the MRIB";
        input  {
            leaf vrf-name  {
                type string;
                description "VRF Name";
            }
            leaf all-routes  {
                type empty;
                mandatory true;
                description "All IPv4 multicast route entries";
            }
        }
    }

    rpc mrib-ipv4-clear-mroute-statistics-group {
        if-feature feature-list:HAVE_MRIBD;
        if-feature feature-list:HAVE_VRF;
        description "Use this RPC to delete entries from the IP multicast routing table
                    statistics based on Group Address. This attribute clears the multicast
                    route entries in the multicast route table and removes the entries
                    from the multicast forwarder. MRIB sends a clear message to the
                    multicast protocols. Each multicast protocol has its own clear
                    multicast route command. The protocol-specific clear command clears
                    multicast routes from the protocol and clears the routes from the MRIB";
        input  {
            leaf vrf-name  {
                type string;
                description "VRF Name";
            }
            leaf group-address  {
                type inet:ipv4-address;
                mandatory true;
                description "IPv4 Group Address";
            }
        }
    }

    rpc mrib-ipv4-clear-mroute-statistics-source-group {
        if-feature feature-list:HAVE_MRIBD;
        if-feature feature-list:HAVE_VRF;
        description "Use this RPC to delete entries from the IP multicast routing table
                    statistics based on Group and Source Address. This attribute clears
                    the multicast route entries in the multicast route table and removes
                    the entries from the multicast forwarder. MRIB sends a clear message
                    to the multicast protocols. Each multicast protocol has its own clear
                    multicast route command. The protocol-specific clear command clears
                    multicast routes from the protocol and clears the routes from the MRIB";
        input  {
            leaf vrf-name  {
                type string;
                description "VRF Name";
            }
            leaf source-address  {
                type inet:ipv4-address;
                mandatory true;
                description "IPv4 Source Address";
            }
            leaf group-address  {
                type inet:ipv4-address;
                mandatory true;
                description "IPv4 Group Address";
            }
        }
    }

    rpc mrib-ipv4-snmp-restart {
        if-feature feature-list:HAVE_SNMP;
        if-feature feature-list:HAVE_MRIBD;
        if-feature feature-list:HAVE_VRF;
        description "Use this RPC to restart snmp MRIB";
    }

    rpc mrib-ipv6-terminal-debug-on {
        if-feature feature-list:HAVE_MRIBD;
        if-feature feature-list:HAVE_MCAST_IPV6;
        description "RPC to enable IPv6 MRIB terminal debug options";
        input  {
            leaf vrf-name  {
                type string;
                description "VRF name";
            }
            leaf terminal-debug-options  {
                type ipi-mrib-types:mrib_debug_t;
                mandatory true;
                description "Enable IP MRIB debug options";
            }
        }
    }

    rpc mrib-ipv6-terminal-debug-off {
        if-feature feature-list:HAVE_MRIBD;
        if-feature feature-list:HAVE_MCAST_IPV6;
        description "RPC to disable IPv6 MRIB terminal debug options";
        input  {
            leaf vrf-name  {
                type string;
                description "VRF name";
            }
            leaf terminal-debug-options  {
                type ipi-mrib-types:mrib_debug_t;
                mandatory true;
                description "Disable IP MRIB debug options";
            }
        }
    }

    rpc mrib-ipv6-clear-mroute-all {
        if-feature feature-list:HAVE_MRIBD;
        if-feature feature-list:HAVE_MCAST_IPV6;
        description "RPC to clear all the multicast route entries in the multicast route
                    table.";
        input  {
            leaf vrf-name  {
                type string;
                mandatory true;
                description "VRF name";
            }
            leaf all-routes  {
                type empty;
                mandatory true;
                description "All IPv6 multicast route entries";
            }
        }
    }

    rpc mrib-ipv6-clear-mroute-group {
        if-feature feature-list:HAVE_MRIBD;
        if-feature feature-list:HAVE_MCAST_IPV6;
        description "RPC to delete entries from the IPv6 multicast routing table based on
                    Group Address";
        input  {
            leaf vrf-name  {
                type string;
                mandatory true;
                description "VRF name";
            }
            leaf group-address  {
                type inet:ipv6-address;
                mandatory true;
                description "IPv6 group address";
            }
        }
    }

    rpc mrib-ipv6-clear-mroute-source-group {
        if-feature feature-list:HAVE_MRIBD;
        if-feature feature-list:HAVE_MCAST_IPV6;
        description "RPC to delete entries from the IPv6 multicast routing table based on
                    Group and Source Address.";
        input  {
            leaf vrf-name  {
                type string;
                mandatory true;
                description "VRF name";
            }
            leaf source-address  {
                type inet:ipv6-address;
                mandatory true;
                description "IPv6 source address";
            }
            leaf group-address  {
                type inet:ipv6-address;
                mandatory true;
                description "IPv6 multicast group address";
            }
        }
    }

    rpc mrib-ipv6-clear-mroute-statistics-all {
        if-feature feature-list:HAVE_MRIBD;
        if-feature feature-list:HAVE_MCAST_IPV6;
        description "RPC to clear all entries from the IPv6 multicast routing table
                    statistics.";
        input  {
            leaf vrf-name  {
                type string;
                mandatory true;
                description "VRF name";
            }
            leaf all-routes  {
                type empty;
                mandatory true;
                description "Statistics for all IPv6 multicast route entries";
            }
        }
    }

    rpc mrib-ipv6-clear-mroute-statistics-group {
        if-feature feature-list:HAVE_MRIBD;
        if-feature feature-list:HAVE_MCAST_IPV6;
        description "RPC to delete entries from the IPv6 multicast routing table statistics
                    based on group address.";
        input  {
            leaf vrf-name  {
                type string;
                mandatory true;
                description "VRF name";
            }
            leaf group-address  {
                type inet:ipv6-address;
                mandatory true;
                description "IPv6 multicast group address";
            }
        }
    }

    rpc mrib-ipv6-clear-mroute-statistics-source-group {
        if-feature feature-list:HAVE_MRIBD;
        if-feature feature-list:HAVE_MCAST_IPV6;
        description "RPC to delete entries from the IPv6 multicast routing table statistics
                    based on Group and Source Address.";
        input  {
            leaf vrf-name  {
                type string;
                mandatory true;
                description "VRF name";
            }
            leaf source-address  {
                type inet:ipv6-address;
                mandatory true;
                description "IPv6 source address";
            }
            leaf group-address  {
                type inet:ipv6-address;
                mandatory true;
                description "IPv6 multicast group address";
            }
        }
    }

}
