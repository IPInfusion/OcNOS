/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mrib-common.yang
*
*/

submodule ipi-mrib-common {

    yang-version 1.1;

    belongs-to  ipi-mrib { prefix ipi-mrib; }

    import feature-list {
        prefix feature-list;
        revision-date 2026-09-15;
    }

    import ipi-mrib-types {
        prefix ipi-mrib-types;
        revision-date 2023-04-06;
    }

    import ietf-inet-types {
        prefix inet;
        revision-date 2013-07-15;
    }

    import ietf-yang-types {
        prefix yang;
        revision-date 2013-07-15;
    }

    import ipi-network-instance {
        prefix ipi-network-instance;
        revision-date 2026-08-12;
    }

    import ipi-vrf {
        prefix ipi-vrf;
        revision-date 2026-08-12;
    }

    import ipi-interface {
        prefix ipi-interface;
        revision-date 2026-03-10;
    }

    organization
        "IP Infusion Inc.";

    contact
        "Address: 3965 Freedom Circle, Suite 200, Santa Clara, CA 95054
         Phone: +1 408-400-1900
         E-mail: support@ipinfusion.com
         Web: http://www.ipinfusion.com/";

    description
        "MRIB Datamodel common groupings";


    revision "2023-04-06" {
        description "MRIB_ROUTE_TYPE_T Enum updated with reference to IANAipMRouteProtocol";
        reference " 0.4.1.";
    }

    revision "2023-04-05" {
        description "CML_SET_ONLY flag added for multicast-routes";
        reference " 0.4.0.";
    }

    revision "2022-07-06" {
        description "Corrected heirarchy for mrib-ip-vrf-common-mcast-route-oil-top";
        reference " 0.3.2.";
    }

    revision "2022-06-07" {
        description "Added 'rpa-id' attribute to mrib-ip-vrf-common-mcast-route-state";
        reference " 0.3.1.";
    }

    revision "2022-06-01" {
        description "Updated the yang file with feature";
        reference " 0.3.0.";
    }

    revision "2022-05-23" {
        description "Added 'uptime' attribute to mrib-ip-vrf-common-mcast-route-state";
        reference " 0.2.1.";
    }

    revision "2022-05-18" {
        description "Added Netconf GetAPI support for multicast routing table entries";
        reference " 0.2.0.";
    }

    revision "2021-12-02" {
        description "Initial Version";
        reference " 0.1.0.";
    }

    grouping mrib-ip-vrf-common-config {
        description
            "MRIB VRF level IP configuration";
        leaf vrf-name  {
            type  leafref {
                path  "/ipi-network-instance:network-instances/ipi-network-instance:network-instance/ipi-vrf:vrf/ipi-vrf:config/ipi-vrf:vrf-name";
            }
            description "Use this attribute to specify the VRF";
        } // END of vrf-name definition.

        leaf multicast-routing-enable  {
            type  empty;
            description "Use this attribute to turn on/off multicast routing on the router when
                        turned off, the multicast protocol daemon remains present, but does
                        not perform multicast functions. When multicast routing is enabled,
                        the MRIB re-creates tunnels, and starts processing any VIF
                        addition/deletion requests, MRT addition/deletion requests, and any
                        multicast forwarding events.";
        } // END of multicast-routing-enable definition.

    } // END of mrib-ip-vrf-common-config definition.
    grouping mrib-ip-vrf-common-route-limit-config {
        description
            "MRIB VRF level route limit configuration";
        leaf maximum-routes  {
            type  uint32 {
                 range "1..2147483647"  {
                    description "1..2147483647: Supported range 1 - 2147483647";
                 }
            }
            description "Use this attribute to limit the number of multicast routes that can be
                        added to a multicast routing table. It generates an error message when
                        the limit is exceeded.";
        } // END of maximum-routes definition.

        leaf warning-threshold  {
            // when " ../maximum-routes ";
            type  uint32 {
                 range "1..2147483647"  {
                    description "1..2147483647: Supported range 1 - 2147483647";
                 }
            }
            description "Use this attribute to limit the number of multicast routes that can be
                        added to a multicast routing table. It generates an error message when
                        the limit is exceeded. If the threshold parameter is set, a threshold
                        warning message is generated when this threshold is exceeded and the
                        message continues to occur until the number of mroutes reaches the
                        limit set by the limit argument.";
        } // END of warning-threshold definition.

    } // END of mrib-ip-vrf-common-route-limit-config definition.
    grouping mrib-ip-vrf-common-debug-config {
        description
            "MRIB VRF level debug configuration";
        leaf options  {
            type  ipi-mrib-types:mrib_debug_t;
            description "Use this attribute to specify debug options";
        } // END of options definition.

    } // END of mrib-ip-vrf-common-debug-config definition.
    grouping mrib-ip-vrf-common-state {
        description
            "MRIB VRF Common State";
        leaf stats-poll-expiry-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "Expiry time";
        } // END of stats-poll-expiry-time definition.

    } // END of mrib-ip-vrf-common-state definition.
    grouping mrib-ip-vrf-common-counters-state {
        description
            "MRIB VRF Common Counters State";
        leaf total-multicast-routes  {
            type  yang:counter32;
            description "Total count of multicast routes";
        } // END of total-multicast-routes definition.

        leaf dense-mode-multicast-routes  {
            type  yang:counter32;
            description "Count of dense mode multicast routes";
        } // END of dense-mode-multicast-routes definition.

        leaf sparse-mode-multicast-routes  {
            type  yang:counter32;
            description "Count of sparse mode multicast routes";
        } // END of sparse-mode-multicast-routes definition.

        leaf no-cache-received  {
            type  yang:counter32;
            description "Number of no cache received";
        } // END of no-cache-received definition.

        leaf no-cache-sent  {
            type  yang:counter32;
            description "Count of no cache sent";
        } // END of no-cache-sent definition.

        leaf wrong-VIF-received  {
            type  yang:counter32;
            description "Count of wrong vif received";
        } // END of wrong-VIF-received definition.

        leaf wrong-VIF-sent  {
            type  yang:counter32;
            description "Count of wrong vif receive sent";
        } // END of wrong-VIF-sent definition.

        leaf whole-packet-received  {
            type  yang:counter32;
            description "Count of whole packet received";
        } // END of whole-packet-received definition.

        leaf whole-packet-sent  {
            type  yang:counter32;
            description "Count of whole packet sent";
        } // END of whole-packet-sent definition.

        leaf immediate-stat-updates-sent  {
            type  yang:counter32;
            description "Count of immediate stat updates sent";
        } // END of immediate-stat-updates-sent definition.

        leaf timed-stat-updates-sent  {
            type  yang:counter32;
            description "Count of timed stat updates sent";
        } // END of timed-stat-updates-sent definition.

        leaf register-packets-sent  {
            type  yang:counter32;
            description "Count of register packets sent";
        } // END of register-packets-sent definition.

        leaf register-acks-received  {
            type  yang:counter32;
            description "Count of register acknowledgements received";
        } // END of register-acks-received definition.

        leaf register-nacks-received  {
            type  yang:counter32;
            description "Count of register negative acknowledgements received";
        } // END of register-nacks-received definition.

        leaf no-cache-receive-rate  {
            type  decimal64 {
                 fraction-digits 3;            }
            description "No cache receive rate specified in no-cache-events/sec";
        } // END of no-cache-receive-rate definition.

        leaf register-packet-sent-rate  {
            type  decimal64 {
                 fraction-digits 3;            }
            description "Register packet sent rate specified in pkts/sec";
        } // END of register-packet-sent-rate definition.

    } // END of mrib-ip-vrf-common-counters-state definition.
    grouping mrib-ip-vrf-common-mcast-route-state {
        description
            "MRIB VRF MCAST Route State attributes";
        leaf source  {
            type  inet:ip-address;
            description "Source Address";
        } // END of source definition.

        leaf group  {
            type  inet:ip-address;
            description "Group Address";
        } // END of group definition.

        leaf incoming-interface  {
            type  string {
                length "1..1965";
                pattern "[^?' =,>|]+";
            }
            description "Incoming Interface Name";
        } // END of incoming-interface definition.

        leaf rpa-id  {
            if-feature feature-list:HAVE_PIM_BIDIR;
            type  uint32;
            description "RPA ID";
        } // END of rpa-id definition.

        leaf rpf-address  {
            type  inet:ip-address;
            description "RPF Address";
        } // END of rpf-address definition.

        leaf route-type  {
            type  ipi-mrib-types:mrib_route_type_t;
            description "Route Type";
        } // END of route-type definition.

        leaf uptime  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "Up Time";
        } // END of uptime definition.

        leaf stats-poll-expiry-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "Expiry Time";
        } // END of stats-poll-expiry-time definition.

        leaf immediate-stats  {
            type  empty;
            description "Immediate Stats";
        } // END of immediate-stats definition.

        leaf timed-stats  {
            type  empty;
            description "Timed stats";
        } // END of timed-stats definition.

        leaf forwarder-installed  {
            type  empty;
            description "Forwarder Installed";
        } // END of forwarder-installed definition.

        leaf bidirectional  {
            if-feature feature-list:HAVE_PIM_BIDIR;
            type  empty;
            description "Bidirectional";
        } // END of bidirectional definition.

    } // END of mrib-ip-vrf-common-mcast-route-state definition.
    grouping mrib-ip-vrf-common-mcast-route-counters-state {
        description
            "MRIB VRF MCAST Route Counters State attributes";
        leaf packets-forwarded  {
            type  yang:counter32;
            description "Number of packets forwarded";
        } // END of packets-forwarded definition.

        leaf bytes-forwarded  {
            type  yang:counter32;
            description "Number of bytes forwarded";
        } // END of bytes-forwarded definition.

        leaf wrong-VIF-sent  {
            type  yang:counter32;
            description "Number of wrong vif sent";
        } // END of wrong-VIF-sent definition.

        leaf wrong-VIF-received  {
            type  yang:counter32;
            description "Number of wrong vif received";
        } // END of wrong-VIF-received definition.

    } // END of mrib-ip-vrf-common-mcast-route-counters-state definition.
    grouping mrib-ip-vrf-common-mcast-route-oil-state {
        description
            "MRIB VRF MCAST Outgoing Interface State attributes";
        leaf name  {
            type  leafref {
                path  "/ipi-interface:interfaces/ipi-interface:interface/ipi-interface:name";
            }
            description "Outgoing interface name";
        } // END of name definition.

        leaf time-to-live  {
            type  uint8;
            description "time-to-live counter";
        } // END of time-to-live definition.

    } // END of mrib-ip-vrf-common-mcast-route-oil-state definition.
    grouping mrib-ip-common-interface-state {
        description
            "MRIB VRF Common Interface State attributes";
        leaf local-address  {
            if-feature feature-list:HAVE_MRIB_IPV4;
            type  inet:ip-address;
            description "Local Address for interface";
        } // END of local-address definition.

        leaf remote-address  {
            if-feature feature-list:HAVE_MRIB_IPV4;
            type  inet:ip-address;
            description "Remote Address for interface";
        } // END of remote-address definition.

        leaf uptime  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "Up Time";
        } // END of uptime definition.

        leaf module-name  {
            type  string {
                length "1..1965";
                pattern "[^?' =,>|]+";
            }
            description "Module which installed this multicast route entry[PIM/IGMP/MLD]";
        } // END of module-name definition.

        leaf vif-index  {
            type  uint32;
            description "VIF Index";
        } // END of vif-index definition.

    } // END of mrib-ip-common-interface-state definition.
    grouping mrib-ip-vrf-common-mcast-route-oil-top {
        description
            "MRIB VRF Common Mcast Route Outgoing Interface Top Container";
        container outgoing-interfaces {
            config false;
            description
                "MRIB VRF MCAST Routes OIF operational state container";

            list outgoing-interface {
                key "name";
                config false;
                description
                    "MRIB VRF MCAST Route OIF operational state instance";
                leaf name  {
                    type  leafref {
                        path  "../state/name";
                    }
                    description "Outgoing interface name";
                } // END of name definition.

                container state {
                    config false;
                    description
                        "MRIB VRF MCAST Route OIF State Container";
                    uses mrib-ip-vrf-common-mcast-route-oil-state;
                } // END of state-container definition.
            } // End of outgoing-interface-list
        } // END of outgoing-interfaces-container definition.
    } // END of mrib-ip-vrf-common-mcast-route-oil-top definition.
    grouping mrib-ip-vrf-common-mcast-route-top {
        description
            "MRIB VRF Common Mcast Route Operational State";
        container multicast-routes {
            config false;
            description
                "MRIB VRF MCAST Routes operational state container";

            list multicast-route {
                key "source group";
                config false;
                description
                    "MRIB VRF MCAST Route operational state instance";
                leaf source  {
                    type  leafref {
                        path  "../state/source";
                    }
                    description "IP Multicast Source Address";
                } // END of source definition.

                leaf group  {
                    type  leafref {
                        path  "../state/group";
                    }
                    description "IP Multicast Group Address";
                } // END of group definition.

                container state {
                    config false;
                    description
                        "MRIB VRF MCAST Route State Container";
                    container counters {
                        config false;
                        description
                            "MRIB IP MCAST Route counters";
                        uses mrib-ip-vrf-common-mcast-route-counters-state;
                    } // END of counters-container definition.
                    uses mrib-ip-vrf-common-mcast-route-state;
                } // END of state-container definition.
                uses mrib-ip-vrf-common-mcast-route-oil-top;
            } // End of multicast-route-list
        } // END of multicast-routes-container definition.
    } // END of mrib-ip-vrf-common-mcast-route-top definition.


}
