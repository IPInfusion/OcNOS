/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mld-types.yang
*
*/

module ipi-mld-types {

    yang-version 1.1;

    namespace   "http://www.ipinfusion.com/yang/ocnos/ipi-mld-types";

    prefix "ipi-mld-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "This defines types related to MLD module";


    revision "2022-06-01" {
        description "Updated the yang file with feature";
        reference " 0.2.0.";
    }

    revision "2022-03-09" {
        description "Initial Version";
        reference " 0.1.0.";
    }



    typedef  mld_yes_no_t {
        type enumeration {
            enum no {
                value 0;
                description "no";
            }
            enum yes {
                value 1;
                description "yes";
            }
        }
        description "type definition for MLD_YES_NO_T";
    }

    typedef  mld_debug_options_t {
        type bits {
            bit decode {
                position 0;
                description "None";
            }
            bit encode {
                position 1;
                description "None";
            }
            bit events {
                position 2;
                description "None";
            }
            bit fsm {
                position 3;
                description "None";
            }
            bit tib {
                position 4;
                description "None";
            }
        }
        description "type definition for MLD_DEBUG_OPTIONS_T";
    }

    typedef  mld_if_oper_status_t {
        type enumeration {
            enum Active {
                value 1;
                description "Active";
            }
            enum Inactive {
                value 2;
                description "Inactive";
            }
        }
        description "type definition for MLD_IF_OPER_STATUS_T";
    }

    typedef  mld_proxy_if_oper_status_t {
        type enumeration {
            enum up {
                value 1;
                description "Up";
            }
            enum down {
                value 2;
                description "Down";
            }
        }
        description "type definition for MLD_PROXY_IF_OPER_STATUS_T";
    }

    typedef  mld_if_state_t {
        type enumeration {
            enum Active {
                value 1;
                description "Active";
            }
            enum Inactive {
                value 2;
                description "Inactive";
            }
        }
        description "type definition for MLD_IF_STATE_T";
    }

    typedef  mld_proxy_grp_membership_state_t {
        type enumeration {
            enum Idle {
                value 1;
                description "Idle";
            }
            enum Delay {
                value 2;
                description "Delay";
            }
        }
        description "type definition for MLD_PROXY_GRP_MEMBERSHIP_STATE_T";
    }

    typedef  mld_static_ssm_map_t {
        type enumeration {
            enum ssm-map {
                value 1;
                description "ssm mapping";
            }
        }
        description "type definition for MLD_STATIC_SSM_MAP_T";
    }

    typedef  mld_static_ssm_source_t {
        type union {
            type mld_static_ssm_map_t {

            }
            type inet:ipv6-address {

            }
        }
        description "type definition for MLD_STATIC_SSM_SOURCE_T";
    }

    typedef  mld_ssm_group_mode_t {
        type enumeration {
            enum Invalid {
                value 0;
                description "None";
            }
            enum Include {
                value 1;
                description "None";
            }
            enum Exclude {
                value 2;
                description "None";
            }
            enum Max {
                value 3;
                description "None";
            }
        }
        description "type definition for MLD_SSM_GROUP_MODE_T";
    }

}
