/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-igmp-interface.yang
*
*/

submodule ipi-igmp-interface {

    yang-version 1.1;

    belongs-to  ipi-igmp { prefix ipi-igmp; }

    import feature-list {
        prefix feature-list;
        revision-date 2026-09-15;
    }

    import ietf-inet-types {
        prefix inet;
        revision-date 2013-07-15;
    }

    import ietf-yang-types {
        prefix yang;
        revision-date 2013-07-15;
    }

    import ipi-interface {
        prefix ipi-interface;
        revision-date 2026-03-10;
    }

    import ipi-igmp-types {
        prefix ipi-igmp-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Data model for IGMP Interface Managed object";


    revision "2025-08-08" {
        description "Added igmp offlink log suppression ";
        reference " 0.6.0.";
    }

    revision "2024-09-12" {
        description "Added condition to allow only source attribute with ip to the when tag under ssm-static-group for static-mapping xpath, so that deletion of static group wont be allowed if only ssm-map is configured.";
        reference " 0.5.1.";
    }

    revision "2024-08-07" {
        description "Added when tag under ssm-static-group for static-mapping xpath, so that deletion of static group wont be allowed if ssm-map is configured.";
        reference " 0.5.0.";
    }

    revision "2023-02-17" {
        description "Fixed prependstr warning";
        reference " 0.4.0.";
    }

    revision "2022-07-30" {
        description "Updated when expressions in yang";
        reference " 0.3.0.";
    }

    revision "2022-06-01" {
        description "Updated the yang file with feature";
        reference " 0.2.0.";
    }

    revision "2021-11-15" {
        description "Initial Version";
        reference " 0.1.0.";
    }

    grouping igmp-interface-config {
        description
            "IGMP Interface Configurations";
        leaf name  {
            type  leafref {
                path  "/ipi-interface:interfaces/ipi-interface:interface/ipi-interface:name";
            }
            description "This attribute defines the interface where IGMP is configured";
        } // END of name definition.

        leaf enabled  {
            type  empty;
            description "Use this attribute to enable the IGMP operation on an interface. This
                        attributeenables IGMP operation in standalone mode,
                        and can be used to learn local-membership information prior to
                        enabling a multicast routing protocol on the interface.
                        This attribute will have no effect on interfaces configured for IGMP
                        proxy";
        } // END of enabled definition.

        leaf last-member-query-count  {
            type  uint8 {
                 range "2..7"  {
                    description "2..7: Supported range 2 - 7";
                 }
            }
            default "2";
            description "Use this attribute to set the last-member query-count value. This
                        attribute applies to interfaces configured for IGMP Layer-3 multicast
                        protocols and IGMP Proxy.";
        } // END of last-member-query-count definition.

        leaf last-member-query-interval  {
            type  uint16 {
                 range "1000..25500"  {
                    description "1000..25500: Supported range 1000 - 25500";
                 }
            }
            default "1000";
            description "Use this attribute to configure the frequency at which the router
                        sends IGMP group-specific host query messages.
                        This attribute applies to interfaces configured for IGMP Layer-3
                        multicast protocols and IGMP Proxy.";
        } // END of last-member-query-interval definition.

        leaf querier-timeout  {
            type  uint16 {
                 range "60..300"  {
                    description "60..300: Supported range 60 - 300";
                 }
            }
            units "seconds";
            default "255";
            description "Use this attribute to set the timeout period before the router takes
                        over as the querier for the interface after the previous querier has
                        stopped querying.
                        This attribute applies to interfaces configured for IGMP Layer-3
                        multicast protocols and IGMP Proxy.";
        } // END of querier-timeout definition.

        leaf query-interval  {
            type  uint16 {
                 range "1..18000"  {
                    description "1..18000: Supported range 1 - 18000";
                 }
            }
            default "125";
            description "Use this attribute to set the frequency of sending IGMP host query
                        messages. This attribute applies to interfaces configured for IGMP
                        Layer-3 multicast protocols and IGMP Proxy.";
        } // END of query-interval definition.

        leaf query-max-response-time  {
            type  uint8 {
                 range "1..240"  {
                    description "1..240: Supported range 1 - 240";
                 }
            }
            default "10";
            description "Use this attribute to set the maximum response time advertised in IGMP
                        queries. This attribute applies to interfaces configured for IGMP
                        Layer-3 multicast protocols and IGMP Proxy.";
        } // END of query-max-response-time definition.

        leaf startup-query-interval  {
            type  uint16 {
                 range "1..18000"  {
                    description "1..18000: Supported range 1 - 18000";
                 }
            }
            default "31";
            description "Use this attribute to set a query interval value for IGMP";
        } // END of startup-query-interval definition.

        leaf startup-query-count  {
            type  uint8 {
                 range "2..10"  {
                    description "2..10: Supported range 2 - 10";
                 }
            }
            default "2";
            description "Use this attribute to set a startup query count for IGMP";
        } // END of startup-query-count definition.

        leaf robustness-variable  {
            type  uint8 {
                 range "2..7"  {
                    description "2..7: Supported range 2 - 7";
                 }
            }
            default "2";
            description "Use this attribute to set the robustness variable value on an
                        interface. This attribute applies to interfaces configured for IGMP
                        Layer-3 multicast protocols and IGMP Proxy.";
        } // END of robustness-variable definition.

        leaf version  {
            type  uint8 {
                 range "1..3"  {
                    description "1..3: Supported range 1 - 3";
                 }
            }
            default "3";
            description "Use this attribute to set the current IGMP protocol version on an
                        interface. This attribute applies to interfaces configured for IGMP
                        Layer-3 multicast protocols and IGMP Proxy.";
        } // END of version definition.

        leaf require-router-alert-option  {
            type  empty;
            description "Use this attribute to configure strict Router Advertisement validation
                        for IGMP.";
        } // END of require-router-alert-option definition.

        leaf allow-offlink-host  {
            type  empty;
            description "Use this attribute to configure off-link for IGMP.";
        } // END of allow-offlink-host definition.

        leaf offlink-log-suppress  {
            // when " ../allow-offlink-host ";
            type  empty;
            description "Use this attribute to configure off-link log-suppress for IGMP.";
        } // END of offlink-log-suppress definition.

    } // END of igmp-interface-config definition.
    grouping igmp-interface-state {
        description
            "IGMP Interface State Information";
        leaf internet-address  {
            type  inet:ipv4-address;
            config false;
            description "Interface IP address used by IGMP to communicate with remote peer";
        } // END of internet-address definition.

        leaf oper-status  {
            type  ipi-igmp-types:igmp_if_oper_status_t;
            config false;
            description "Operational status of the IGMP interface";
        } // END of oper-status definition.

        leaf host-version  {
            type  uint8;
            config false;
            description "host-version";
        } // END of host-version definition.

        leaf is-querier  {
            type  boolean;
            config false;
            description "Indicates whether this interface is a IGMP querier or not.";
        } // END of is-querier definition.

        leaf querying-router  {
            type  inet:ipv4-address;
            config false;
            description "IGMP querying router for this subnet";
        } // END of querying-router definition.

        leaf group-membership-interval  {
            type  uint32;
            config false;
            description "Time interval after which the group memberships on this interface will
                        time out.";
        } // END of group-membership-interval definition.

    } // END of igmp-interface-state definition.
    grouping igmp-interface-counters-state {
        description
            "IGMP Interface Counters Information";
        leaf v1-reports-received  {
            type  yang:counter32;
            config false;
            description "Number of IGMPv1 reports received on this interface.";
        } // END of v1-reports-received definition.

        leaf v2-reports-received  {
            type  yang:counter32;
            config false;
            description "Number of IGMPv2 reports received on this interface.";
        } // END of v2-reports-received definition.

        leaf v2-leaves-received  {
            type  yang:counter32;
            config false;
            description "Number of IGMPv2 leaves received on this interface.";
        } // END of v2-leaves-received definition.

        leaf v3-reports-received  {
            type  yang:counter32;
            config false;
            description "Number of IGMPv3 reports received on this interface.";
        } // END of v3-reports-received definition.

        leaf current-group-records  {
            type  yang:counter32;
            config false;
            description "Number of current group membership records on this interface.";
        } // END of current-group-records definition.

    } // END of igmp-interface-counters-state definition.
    grouping igmp-if-proxy-config {
        description
            "IGMP Interface Proxy Configurations";
        leaf enable-proxy-service  {
            type  empty;
            description "Use this attribute to designate an interface to be the IGMP
                        proxy-service (upstream host-side) interface,
                        thus enabling IGMP host-side protocol operation on this interface. All
                        associated downstream router-side interfaces will have their
                        memberships
                        consolidated on this interface, according to IGMP host-side
                        functionality";
        } // END of enable-proxy-service definition.

        leaf mroute-proxy-interface  {
            type  string {
                length "1..1965";
                pattern "[^?' =,>|]+";
            }
            default "NULL";
            description "Use this attribute to specify the IGMP Proxy service interface with
                        which to be associated. IGMP router-side protocol operation is enabled
                        only
                        when the specified upstream proxy-service interface is functional.";
        } // END of mroute-proxy-interface definition.

        leaf unsolicited-report-interval  {
            type  uint16 {
                 range "1000..25500"  {
                    description "1000..25500: Supported range 1000 - 25500";
                 }
            }
            default "1000";
            description "Use this attribute to set an unsolicited report interval for an
                        interface designated as an IGMP proxy";
        } // END of unsolicited-report-interval definition.

    } // END of igmp-if-proxy-config definition.
    grouping igmp-if-proxy-state {
        description
            "IGMP Interface Proxy State Information";
        leaf oper-status  {
            type  ipi-igmp-types:igmp_proxy_if_oper_status_t;
            config false;
            description "IGMP proxy operational status";
        } // END of oper-status definition.

    } // END of igmp-if-proxy-state definition.
    grouping igmp-if-grp-membsership-config {
        description
            "IGMP Inteface Group Membership Configurations";
        leaf access-group-name  {
            type  string {
                length "1..1965";
                pattern "[a-zA-Z0-9][^?' =,>|]*";
            }
            default "NULL";
            description "Use this attribute to control the multicast local-membership groups
                        learned on an interface. This attribute applies to
                        interfaces configured for IGMP Layer-3 multicast protocols, IGMP
                        proxy.";
        } // END of access-group-name definition.

        leaf immediate-leave-groups-list  {
            type  string {
                length "1..1965";
                pattern "[a-zA-Z0-9][^?' =,>|]*";
            }
            default "NULL";
            description "In IGMP version 2, use this attribute to minimize the leave latency of
                        IGMP memberships.
                        This attribute is used when only one receiver host is connected to
                        each interface.
                        This command applies to interfaces configured for IGMP Layer-3
                        multicast protocols, IGMP Proxy.";
        } // END of immediate-leave-groups-list definition.

        leaf member-limit  {
            type  uint32 {
                 range "1..2097152"  {
                    description "1..2097152: Supported range 1 - 2097152";
                 }
            }
            description "Use this attribute to set the maximum number of group membership
                        states, at either the router level or at the interface
                        level. Once the specified number of group memberships is reached, all
                        further local-memberships are ignored.
                        Optionally, an exception access-list can be configured to specify the
                        group-address to be excluded from being subject to the limit.";
        } // END of member-limit definition.

        leaf limit-exception-acl  {
            // when " ipi-igmp-interface:interfaces/interface/group-membership-control/config/member-limit ";
            type  string {
                length "1..1965";
                pattern "[a-zA-Z0-9][^?' =,>|]*";
            }
            description "Use this attribute to set the maximum number of group membership
                        states, at either the router level or at the interface
                        level. Once the specified number of group memberships is reached, all
                        further local-memberships are ignored.
                        Optionally, an exception access-list can be configured to specify the
                        group-address to be excluded from being subject to the limit.";
        } // END of limit-exception-acl definition.

    } // END of igmp-if-grp-membsership-config definition.
    grouping igmp-if-asm-static-grp-config {
        description
            "IGMP Interface ASM Static Group Configurations";
        leaf group-address  {
            type  inet:ipv4-address;
            description "Use this attribute to statically configure group membership entries on
                        an interface. To statically add only a group membership, do not
                        specify any parameters.
                        This attribute applies to IGMP operation on a specific interface to
                        statically add group and/or source records on a VLAN interface to
                        statically
                        add group and/or source records.";
        } // END of group-address definition.

    } // END of igmp-if-asm-static-grp-config definition.
    grouping igmp-if-ssm-static-grp-config {
        description
            "IGMP Interface SSM Static Group Configurations";
        leaf group-address  {
            type  inet:ipv4-address;
            description "Use this attribute to statically configure the group to be joined.";
        } // END of group-address definition.

        leaf source  {
            type  ipi-igmp-types:igmp_static_ssm_source_t;
            description "Use this attribute to statically configure the multicast source for
                        group to be joined.";
        } // END of source definition.

    } // END of igmp-if-ssm-static-grp-config definition.
    grouping igmp-if-asm-join-grp-config {
        description
            "IGMP Interface ASM Join Group Configurations";
        leaf group-address  {
            type  inet:ipv4-address;
            description "Use this attribute to configure a locally joined multicast group.";
        } // END of group-address definition.

    } // END of igmp-if-asm-join-grp-config definition.
    grouping igmp-if-ssm-join-grp-config {
        description
            "IGMP Interface SSM Join Group Configurations";
        leaf group-address  {
            type  inet:ipv4-address;
            description "Use this attribute to configure a locally joined multicast group.";
        } // END of group-address definition.

        leaf source  {
            type  inet:ipv4-address;
            description "Use this attribute to configure the multicast source for a locally
                        joined group.";
        } // END of source definition.

    } // END of igmp-if-ssm-join-grp-config definition.

    grouping  interfaces-grouping {
    description
        "Top level container for IGMP interfaces";
    container interfaces {
        if-feature feature-list:HAVE_MRIBD;
        description
            "Top level container for IGMP interfaces";

        list interface {
            key "name";
            description
                "IGMP interface instance configurations";
            leaf name  {
                type  leafref {
                    path  "../config/name";
                }
                description "This attribute defines the interface where IGMP is configured";
            } // END of name definition.

            container config {
                description
                    "config container for IGMP interface instance configurations";
                uses igmp-interface-config;
            } // END of config-container definition.
            container state {
                config false;
                description
                    "state container for IGMP interface instance configurations";
                container counters {
                    config false;
                    description
                        "container for IGMP interface counters";
                    uses igmp-interface-counters-state;
                } // END of counters-container definition.
                uses igmp-interface-state;
                uses igmp-interface-config;
            } // END of state-container definition.
            container proxy {
                description
                    "IGMP inteface proxy configurations";
                container config {
                    description
                        "config container for IGMP proxy configurations";
                    uses igmp-if-proxy-config;
                } // END of config-container definition.
                container state {
                    config false;
                    description
                        "state container for IGMP proxy configurations";
                    uses igmp-if-proxy-config;
                    uses igmp-if-proxy-state;
                } // END of state-container definition.
            } // END of proxy-container definition.
            container group-membership-control {
                description
                    "IGMP inteface group membership control configurations";
                container config {
                    description
                        "config container for IGMP group membership control configurations";
                    uses igmp-if-grp-membsership-config;
                } // END of config-container definition.
                container state {
                    config false;
                    description
                        "state container for IGMP group membership control configurations";
                    uses igmp-if-grp-membsership-config;
                } // END of state-container definition.
            } // END of group-membership-control-container definition.
            container asm-static-groups {
                description
                    "IGMP inteface asm static groups configurations";

                list asm-static-group {
                    key "group-address";
                    description
                        "IGMP interface asm static group instance configurations";
                    leaf group-address  {
                        type  leafref {
                            path  "../config/group-address";
                        }
                        description "Use this attribute to statically configure group membership entries on
                                    an interface. To statically add only a group membership, do not
                                    specify any parameters.
                                    This attribute applies to IGMP operation on a specific interface to
                                    statically add group and/or source records on a VLAN interface to
                                    statically
                                    add group and/or source records.";
                    } // END of group-address definition.

                    container config {
                        description
                            "config container for IGMP asm static group configurations";
                        uses igmp-if-asm-static-grp-config;
                    } // END of config-container definition.
                    container state {
                        config false;
                        description
                            "state container for IGMP asm static group configurations";
                        uses igmp-if-asm-static-grp-config;
                    } // END of state-container definition.
                } // End of asm-static-group-list
            } // END of asm-static-groups-container definition.
            container ssm-static-groups {
                description
                    "IGMP inteface ssm static groups configurations";

                list ssm-static-group {
                // when " ../ssm-static-group/config/source != 'ssm-map' + ipi-igmp:igmp/vrfs/vrf/ssm/static-mappings/static-mapping ";
                    key "group-address source";
                    description
                        "IGMP interface ssm static group instance configurations";
                    leaf group-address  {
                        type  leafref {
                            path  "../config/group-address";
                        }
                        description "Use this attribute to statically configure the group to be joined.";
                    } // END of group-address definition.

                    leaf source  {
                        type  leafref {
                            path  "../config/source";
                        }
                        description "Use this attribute to statically configure the group to be joined.";
                    } // END of source definition.

                    container config {
                        description
                            "config container for IGMP ssm static group configurations";
                        uses igmp-if-ssm-static-grp-config;
                    } // END of config-container definition.
                    container state {
                        config false;
                        description
                            "state container for IGMP ssm static group configurations";
                        uses igmp-if-ssm-static-grp-config;
                    } // END of state-container definition.
                } // End of ssm-static-group-list
            } // END of ssm-static-groups-container definition.
            container asm-join-groups {
                description
                    "IGMP inteface asm join groups configurations";

                list asm-join-group {
                    key "group-address";
                    description
                        "IGMP interface asm join group instance configurations";
                    leaf group-address  {
                        type  leafref {
                            path  "../config/group-address";
                        }
                        description "Use this attribute to configure a join multicast group.";
                    } // END of group-address definition.

                    container config {
                        description
                            "config container for IGMP asm join group configurations";
                        uses igmp-if-asm-join-grp-config;
                    } // END of config-container definition.
                    container state {
                        config false;
                        description
                            "state container for IGMP asm join group configurations";
                        uses igmp-if-asm-join-grp-config;
                    } // END of state-container definition.
                } // End of asm-join-group-list
            } // END of asm-join-groups-container definition.
            container ssm-join-groups {
                description
                    "IGMP inteface ssm join groups configurations";

                list ssm-join-group {
                    key "group-address source";
                    description
                        "IGMP interface ssm static join group instance configurations";
                    leaf group-address  {
                        type  leafref {
                            path  "../config/group-address";
                        }
                        description "Use this attribute to configure a join multicast group.";
                    } // END of group-address definition.

                    leaf source  {
                        type  leafref {
                            path  "../config/source";
                        }
                        description "Use this attribute to statically configure the group to be joined.";
                    } // END of source definition.

                    container config {
                        description
                            "config container for IGMP ssm join group configurations";
                        uses igmp-if-ssm-join-grp-config;
                    } // END of config-container definition.
                    container state {
                        config false;
                        description
                            "state container for IGMP ssm join group configurations";
                        uses igmp-if-ssm-join-grp-config;
                    } // END of state-container definition.
                } // End of ssm-join-group-list
            } // END of ssm-join-groups-container definition.
        } // End of interface-list
    } // END of interfaces-container definition.
    } // END of interfaces-grouping definition.


}
