/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mac-limit-types.yang
*
*/

module ipi-mac-limit-types {

    yang-version 1.1;

    namespace   "http://www.ipinfusion.com/yang/ocnos/ipi-mac-limit-types";

    prefix "ipi-mac-limit-types";

    organization
        "IP Infusion Inc.";

    contact
        "Address: 3965 Freedom Circle, Suite 200, Santa Clara, CA 95054
         Phone: +1 408-400-1900
         E-mail: support@ipinfusion.com
         Web: http://www.ipinfusion.com/";

    description
        "MAC limit data types";


    revision "2025-04-08" {
        description "Initial version - add MAC limit types";
        reference " 0.1.0.";
    }



    typedef  mac_limit_action_t {
        type enumeration {
            enum log-only {
                value 1;
                description "Logging only support";
            }
            enum log-errdisable {
                value 2;
                description "Logging and errdisable support";
            }
        }
        description "type definition for MAC_LIMIT_ACTION_T";
    }

}
