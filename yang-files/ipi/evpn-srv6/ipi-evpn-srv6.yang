/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-evpn-srv6.yang
*
*/

module ipi-evpn-srv6 {

    yang-version 1.1;

    namespace   "http://www.ipinfusion.com/yang/ocnos/ipi-evpn-srv6";

    prefix "ipi-evpn-srv6";

    import cml-data-types {
        prefix cml-data-types;
        revision-date 2026-05-15;
    }

    import ietf-inet-types {
        prefix inet;
        revision-date 2013-07-15;
    }

    import ipi-vrf {
        prefix ipi-vrf;
        revision-date 2026-08-12;
    }

    import ipi-network-instance {
        prefix ipi-network-instance;
        revision-date 2026-08-12;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for EVPN-SRV6 protocol";


    revision "2025-03-24" {
        description "Added 'CML_UNIQUE' for attributes 'vpws-identifier' and 'tenant-description'";
        reference " 0.7.0.";
    }

    revision "2024-01-11" {
        description "SRv6 ELAN feature";
        reference " 0.6.0.";
    }

    revision "2023-02-17" {
        description "Fixed prependstr warning";
        reference " 0.5.0.";
    }

    revision "2023-01-20" {
        description "Added helpstring for tunnel-select-policy";
        reference " 0.4.0.";
    }

    revision "2022-08-16" {
        description "Updated the service mapping FLAG";
        reference " 0.3.1.";
    }

    revision "2022-08-12" {
        description "Removed dependency on HAVE_SRV6_EVPN";
        reference " 0.3.0.";
    }

    revision "2022-06-01" {
        description "Updated the yang file with feature";
        reference " 0.2.0.";
    }

    revision "2022-05-13" {
        description "Initial Version";
        reference " 0.1.0.";
    }

    grouping evpn-srv6-global-config {
        description
            "Grouping for global evpn-srv6 configuration";
        leaf enabled  {
            type  empty;
            mandatory true;
            description "Use this attribute to enable EVPN-SRV6 module. Without this
                        attribute evpn srv6 functionality can not be achieved";
        } // END of enabled definition.

        leaf vtep-ipv6-address  {
            type  inet:ipv6-address;
            description "Use this attribute to set source vtep global ip address.
                        This will be treated at evpn srv6 tunnel source address";
        } // END of vtep-ipv6-address definition.

        leaf mac-ageing-timer  {
            // when " ipi-evpn-srv6:evpn-srv6/global/config/enabled ";
            type  uint32 {
                 range "10..572"  {
                    description "10..572: Supported range 10 - 572";
                 }
            }
            units "seconds";
            description "Use this attribute to set the time till a learned mac
                        address will persist after last update";
        } // END of mac-ageing-timer definition.

    } // END of evpn-srv6-global-config definition.
    grouping evpn-srv6-tenant-top {
        description
            "Grouping for EVPN-SRV6 tenant top";
        container tenants {
            description
                "EVPN-SRV6 tenant list enclosing container";

            list tenant {
            when " /ipi-evpn-srv6:evpn-srv6/ipi-evpn-srv6:global/ipi-evpn-srv6:config ";
                key "tenant-identifier";
                unique "config/vpws-identifier config/tenant-description";
                description
                    "Tenant configurations for EVPN-SRV6";
                leaf tenant-identifier  {
                    type  leafref {
                        path  "../config/tenant-identifier";
                    }
                    description "Tenant Identifier";
                } // END of tenant-identifier definition.

                container config {
                    description
                        "Configuration data";
                    uses evpn-srv6-tenant-global-config;
                    uses evpn-srv6-tenant-config;
                } // END of config-container definition.
                container state {
                    config false;
                    description
                        "Operational state data";
                    uses evpn-srv6-tenant-global-config;
                    uses evpn-srv6-tenant-config;
                } // END of state-container definition.
            } // End of tenant-list
        } // END of tenants-container definition.
    } // END of evpn-srv6-tenant-top definition.
    grouping evpn-srv6-tenant-global-config {
        description
            "Grouping for EVPN-SRV6 tenant global configuration";
        leaf tenant-identifier  {
            type  uint32 {
                 range "1..16777215"  {
                    description "1..16777215: Supported range 1 - 16777215";
                 }
            }
            description "Tenant Identifier";
        } // END of tenant-identifier definition.

        leaf vpws-identifier  {
            if-feature feature-list:HAVE_EVPN_VPWS;
            type  uint32 {
                 range "1..16777215"  {
                    description "1..16777215: Supported range 1 - 16777215";
                 }
            }
            description "Use this attribute to create vpws tenant";
        } // END of vpws-identifier definition.

    } // END of evpn-srv6-tenant-global-config definition.
    grouping evpn-srv6-tenant-config {
        description
            "Grouping for EVPN-SRV6 tenant configuration";
        leaf vrf-name  {
            type  leafref {
                path  "/ipi-network-instance:network-instances/ipi-network-instance:network-instance/ipi-vrf:vrf/ipi-vrf:config/ipi-vrf:vrf-name";
            }
            description "Use this attribute to map vrf to carry EVPN routes";
        } // END of vrf-name definition.

        leaf mac-holdtime  {
            type  int32 {
                 range "-1..300"  {
                    description "-1..300: Supported range -1 - 300";
                 }
            }
            units "seconds";
            default "0";
            description "Use this attribute to set the time a host mac entry will persist after
                        unconfig";
        } // END of mac-holdtime definition.

        leaf tenant-description  {
            type  string {
                length "1..1965";
                pattern "[^?' =,>|]+";
            }
            description "Use this attribute to set evpn-srv6 tenant identifier name";
        } // END of tenant-description definition.

        leaf tunnel-policy-name  {
            if-feature feature-list:HAVE_SERVICE_MAPPING_OR_HAVE_SRV6;
            type  string {
                length "1..127";
                pattern "[^?' =,>|]+";
            }
            description "Transport Tunnel Selection Policy";
        } // END of tunnel-policy-name definition.

        leaf srv6-locator-name  {
            type  string {
                length "1..1965";
                pattern "[^?' =,>|]+";
            }
            description "Locator name";
        } // END of srv6-locator-name definition.

    } // END of evpn-srv6-tenant-config definition.
    grouping arp-nd-global-grouping {
        description
            "Grouping for configuring global ARP-ND configs";
        leaf arp-nd-refresh-time  {
            when " /ipi-evpn-srv6:evpn-srv6/ipi-evpn-srv6:global/ipi-evpn-srv6:config/ipi-evpn-srv6:enabled ";
            type  uint32 {
                 range "3..190"  {
                    description "3..190: Supported range 3 - 190";
                 }
            }
            units "seconds";
            description "Use this attribute to configure aging out the arp-cache and
                        nd-cache entries";
        } // END of arp-nd-refresh-time definition.

    } // END of arp-nd-global-grouping definition.

    grouping  evpn-srv6-grouping {
    description
        "EVPN-SRV6 global level container";
    container evpn-srv6 {
        if-feature feature-list:HAVE_NVO;
        if-feature feature-list:HAVE_SRV6;
        if-feature feature-list:HAVE_BGP_EVPN;
        description
            "EVPN-SRV6 global level container";
        container global {
            // when " ipi-evpn-srv6:evpn-srv6/global/config ";
            description
                "Configuration data for EVPN-SRV6 global capability configuration";
            container config {
                presence "Enable EVPN-SRV6";
                description
                    "Configuration data";
                uses evpn-srv6-global-config;
            } // END of config-container definition.
            container state {
                config false;
                description
                    "Operational state data";
                uses evpn-srv6-global-config;
            } // END of state-container definition.
        } // END of global-container definition.
        container arp-nd-global {
            description
                "ARP-ND global data";
            container config {
                description
                    "ARP-ND global configuration data";
                uses arp-nd-global-grouping;
            } // END of config-container definition.
            container state {
                config false;
                description
                    "Operational state data";
                uses arp-nd-global-grouping;
            } // END of state-container definition.
        } // END of arp-nd-global-container definition.
        uses evpn-srv6-tenant-top;
    } // END of evpn-srv6-container definition.
    } // END of evpn-srv6-grouping definition.

    uses evpn-srv6-grouping;

    rpc clear-nvo-srv6-dynamic-mac-address-table {
        if-feature feature-list:HAVE_SRV6;
        if-feature feature-list:HAVE_SUBINTERFACE;
        if-feature feature-list:HAVE_NVO;
        if-feature feature-list:HAVE_BGP_EVPN;
        description "Use this RPC to clear the dynamic entries from mac address table";
    }

    rpc clear-nvo-srv6-dynamic-mac-address-table-evid {
        if-feature feature-list:HAVE_SRV6;
        if-feature feature-list:HAVE_SUBINTERFACE;
        if-feature feature-list:HAVE_NVO;
        if-feature feature-list:HAVE_BGP_EVPN;
        description "Use this RPC to clear the dynamic entries from mac address table with
                    evid or evid+mac";
        input  {
            leaf tenant-identifier  {
                type uint32 {
                    range "1..16777215";
                }
                mandatory true;
                description "Use this attribute to include a tenant";
            }
            leaf mac-address  {
                type cml-data-types:cml_mac_addr_t;
                description "Interface MAC address";
            }
        }
    }

    rpc clear-evpn-srv6-egress-counters {
        if-feature feature-list:HAVE_SRV6;
        if-feature feature-list:HAVE_SUBINTERFACE;
        if-feature feature-list:HAVE_NVO;
        if-feature feature-list:HAVE_BGP_EVPN;
        description "Use this RPC to clear the counters";
        input  {
            leaf tenant-identifier  {
                type uint32 {
                    range "1..16777215";
                }
                description "Use this attribute to include a tenant";
            }
            leaf egress-direction  {
                type cml-data-types:evpn_egress_dir_t;
                mandatory true;
                description "Use this attribute to include Tunnel direction";
            }
            leaf destination-ip  {
                type inet:ipv6-address;
                description "Use this attribute to include Tunnel destination IP";
            }
        }
    }

    rpc clear-evpn-srv6-ingress-counters {
        if-feature feature-list:HAVE_SRV6;
        if-feature feature-list:HAVE_SUBINTERFACE;
        if-feature feature-list:HAVE_NVO;
        if-feature feature-list:HAVE_BGP_EVPN;
        description "Use this RPC to clear the ingress side counters";
        input  {
            leaf tenant-identifier  {
                type uint32 {
                    range "1..16777215";
                }
                description "Use this attribute to include a tenant";
            }
            leaf ingress-direction  {
                type cml-data-types:evpn_ingress_dir_t;
                mandatory true;
                description "Use this attribute to include Tunnel direction";
            }
        }
    }

}
