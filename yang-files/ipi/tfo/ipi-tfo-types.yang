/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-tfo-types.yang
*
*/

module ipi-tfo-types {

    yang-version 1.1;

    namespace   "http://www.ipinfusion.com/yang/ocnos/ipi-tfo-types";

    prefix "ipi-tfo-types";

    organization
        "IP Infusion Inc.";

    contact
        "Address: 3965 Freedom Circle, Suite 200, Santa Clara, CA 95054
         Phone: +1 408-400-1900
         E-mail: support@ipinfusion.com
         Web: http://www.ipinfusion.com/";

    description
        "TFO module Datatypes";


    revision "2022-06-01" {
        description "Updated the yang file with feature";
        reference " 0.2.0.";
    }

    revision "2021-07-28" {
        description "Initial Version";
        reference " 0.1.0.";
    }



    typedef  tfo_fog_group_type_t {
        type enumeration {
            enum mpg {
                value 1;
                description "Monitor Port Group";
            }
            enum cpg {
                value 2;
                description "Control Port Group";
            }
        }
        description "type definition for TFO_FOG_GROUP_TYPE_T";
    }

    typedef  tfo_fog_link_type_t {
        type enumeration {
            enum uplink {
                value 1;
                description "Configure Port as Uplink";
            }
            enum downlink {
                value 2;
                description "Configure Port as Downlink";
            }
        }
        description "type definition for TFO_FOG_LINK_TYPE_T";
    }

}
