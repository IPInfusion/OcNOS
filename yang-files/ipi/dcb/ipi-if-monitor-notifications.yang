/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-if-monitor-notifications.yang
*
*/

submodule ipi-if-monitor-notifications {

    yang-version 1.1;

    belongs-to  ipi-dcb { prefix ipi-dcb; }

    organization
        "IP Infusion Inc.";

    contact
        "Address: 3965 Freedom Circle, Suite 200, Santa Clara, CA 95054
         Phone: +1 408-400-1900
         E-mail: support@ipinfusion.com
         Web: http://www.ipinfusion.com/";

    description
        "Interface monitor notifications";


    revision "2025-09-10" {
        description "Initial revision";
        reference " 0.1.0.";
    }



}
