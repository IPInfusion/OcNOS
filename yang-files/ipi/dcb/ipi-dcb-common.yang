/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dcb-common.yang
*
*/

submodule ipi-dcb-common {

    yang-version 1.1;

    belongs-to  ipi-dcb { prefix ipi-dcb; }

    import ipi-dcb-types {
        prefix ipi-dcb-types;
        revision-date 2025-08-20;
    }

    organization
        "IP Infusion Inc.";

    contact
        "Address: 3965 Freedom Circle, Suite 200, Santa Clara, CA 95054
         Phone: +1 408-400-1900
         E-mail: support@ipinfusion.com
         Web: http://www.ipinfusion.com/";

    description
        "Data model for common configuration and operational state for DCB and
                DCB interface config";


    revision "2022-10-27" {
        description "Initial Version";
        reference " 0.1.0.";
    }

    grouping dcb-qcn-defense-common-config {
        description
            "Grouping for DCB QCN defense attributes";
        leaf priority-value  {
            type  leafref {
                path  "/ipi-dcb:dcb/ipi-dcb:bridges/ipi-dcb:bridge/ipi-dcb:qcn/ipi-dcb:config/ipi-dcb:cnpv-priorities";
            }
            description "Use this attribute to configure priority";
        } // END of priority-value definition.

        leaf qcn-mode  {
            type  ipi-dcb-types:dcb_qcn_mode_t;
            mandatory true;
            description "Use this attribute to configure QCN mode";
        } // END of qcn-mode definition.

        leaf admin-defense-mode  {
            type  ipi-dcb-types:dcb_qcn_admin_defense_mode_t;
            description "Use this attribute to configure defense mode";
        } // END of admin-defense-mode definition.

        leaf alternate-priority  {
            type  uint8 {
                 range "0..7"  {
                    description "0..7: Supported range 0 - 7";
                 }
            }
            description "Use this attribute to configure alternate-priority";
        } // END of alternate-priority definition.

    } // END of dcb-qcn-defense-common-config definition.


}
