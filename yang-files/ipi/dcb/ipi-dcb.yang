/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dcb.yang
*
*/

module ipi-dcb {

    yang-version 1.1;

    namespace   "http://www.ipinfusion.com/yang/ocnos/ipi-dcb";

    prefix "ipi-dcb";

    import ipi-network-instance {
        prefix ipi-network-instance;
        revision-date 2026-08-12;
    }

    import cml-data-types {
        prefix cml-data-types;
        revision-date 2026-05-15;
    }

    import feature-list {
        prefix feature-list;
        revision-date 2026-09-15;
    }

    include ipi-dcb-common { revision-date 2022-10-27;}
    include ipi-dcb-interface { revision-date 2026-01-19;}
    include ipi-pfc-notifications { revision-date 2025-07-05;}
    include ipi-if-monitor-notifications { revision-date 2025-09-10;}
    organization
        "IP Infusion Inc.";

    contact
        "Address: 3965 Freedom Circle, Suite 200, Santa Clara, CA 95054
         Phone: +1 408-400-1900
         E-mail: support@ipinfusion.com
         Web: http://www.ipinfusion.com/";

    description
        "Data model for IPI DCB Configuration and Operational state";


    revision "2026-01-19" {
        description "Changed enabled priorities command to configure all values at once";
        reference " 0.5.6.";
    }

    revision "2025-12-17" {
        description "Fixed dbsync inssue in  PFC deadlock recovery";
        reference " 0.5.5.";
    }

    revision "2025-09-22" {
        description "Fixed dbsync inssue in  PFC deadlock recovery";
        reference " 0.5.4.";
    }

    revision "2025-09-10" {
        description "Added PFC and ECN monitoring";
        reference " 0.5.3.";
    }

    revision "2025-09-01" {
        description "Added PFC deadlock recovery CML error when passing a recovery-time argument when mode is not timer";
        reference " 0.5.2.";
    }

    revision "2025-08-26" {
        description "Added support for application-priority delete db-synch issue";
        reference " 0.5.1.";
    }

    revision "2025-08-20" {
        description "Added PFC deadlock detection";
        reference " 0.5.0.";
    }

    revision "2025-08-08" {
        description "Added support for switchport ETS and application-priority";
        reference " 0.4.11.";
    }

    revision "2025-07-30" {
        description "Removed bridge dependency for ETS and application-priority";
        reference " 0.4.10.";
    }

    revision "2025-06-07" {
        description "When Mlag is added with switchport, PFC config should not be removed";
        reference " 0.4.9.";
    }

    revision "2025-05-28" {
        description "When Mlag is mapped to PO, PFC configs are removed in PO";
        reference " 0.4.8.";
    }

    revision "2025-05-22" {
        description "PFC configs are changed with HITLESS so that it calls everytime";
        reference " 0.4.7.";
    }

    revision "2025-05-19" {
        description "data-center-bridging global command disability dependecy removed for PFC";
        reference " 0.4.6.";
    }

    revision "2025-05-13" {
        description "Increasing maximum PFC link-delay-allowance";
        reference " 0.4.5.";
    }

    revision "2025-05-12" {
        description "When swithport is removed, PFC also removed";
        reference " 0.4.4.";
    }

    revision "2025-04-28" {
        description "Removed the bridge dependency for PFC";
        reference " 0.4.3.";
    }

    revision "2025-02-09" {
        description "Removed the bridge dependency for DCBX";
        reference " 0.4.2.";
    }

    revision "2025-01-27" {
        description "Increase maximum PFC link-delay-allowance";
        reference " 0.4.1.";
    }

    revision "2024-09-11" {
        description "validation is not proper in cli-command";
        reference " 0.4.0.";
    }

    revision "2024-06-03" {
        description "Masking dcb-enabled parameter for Marvell platform ";
        reference " 0.3.7.";
    }

    revision "2024-05-21" {
        description "Added missing platform check for application-priority";
        reference " 0.3.6.";
    }

    revision "2024-05-09" {
        description "Added when tag for the attribute pfc-mode";
        reference " 0.3.5.";
    }

    revision "2023-03-17" {
        description "Added when tag dependency for debug container on system level debug disable command";
        reference " 0.3.4.";
    }

    revision "2023-02-08" {
        description "Added proper platform check for DCB";
        reference " 0.3.3.";
    }

    revision "2023-01-25" {
        description "Leafref added instead of when tag for network-instance";
        reference " 0.3.2.";
    }

    revision "2022-12-20" {
        description "Added missing cliprependstr tags";
        reference " 0.3.1.";
    }

    revision "2022-12-19" {
        description "Added flag to handle replace  operation";
        reference " 0.3.0.";
    }

    revision "2022-11-17" {
        description "Handling for platform support check";
        reference " 0.2.0.";
    }

    revision "2022-11-07" {
        description "Added HAVE_QOS flag in when tag";
        reference " 0.1.1.";
    }

    revision "2022-10-27" {
        description "Initial Version";
        reference " 0.1.0.";
    }

    grouping dcb-debug-config {
        description
            "Grouping for DCB debug attributes";
        leaf enable  {
            type  empty;
            description "This attribute enables debugging for DCB";
        } // END of enable definition.

    } // END of dcb-debug-config definition.
    grouping dcb-debug-top {
        description
            "Grouping for DCB debug attributes";
        container debug {
            description
                "debug container";
            container config {
                description
                    "DCB debug Configuration data";
                uses dcb-debug-config;
            } // END of config-container definition.
            container state {
                config false;
                description
                    "DCB debug Operational data";
                uses dcb-debug-config;
            } // END of state-container definition.
        } // END of debug-container definition.
    } // END of dcb-debug-top definition.
    grouping dcb-bridge-qcn-defense-top {
        description
            "Grouping for DCB QCN defense attributes";
        container cnpv-defenses {
            description
                "enclosing container for list of cnpv defense attributes";

            list cnpv-defense {
            when " /ipi-dcb:dcb/ipi-dcb:bridges/ipi-dcb:bridge/ipi-dcb:qcn/ipi-dcb:config/ipi-dcb:cnpv-priorities ";
                key "priority-value";
                description
                    "List of cnpv defense";
                leaf priority-value  {
                    type  leafref {
                        path  "../config/priority-value";
                    }
                    description "Use this attribute to configure cnpv defense priority value";
                } // END of priority-value definition.

                container config {
                    description
                        "DCB QCN defence Configuration data";
                    uses dcb-qcn-defense-common-config;
                } // END of config-container definition.
                container state {
                    config false;
                    description
                        "DCB QCN defense Operational data";
                    uses dcb-qcn-defense-common-config;
                } // END of state-container definition.
            } // End of cnpv-defense-list
        } // END of cnpv-defenses-container definition.
    } // END of dcb-bridge-qcn-defense-top definition.
    grouping dcb-bridge-qcn-config {
        description
            "DCB QCN attributes";
        leaf enabled  {
            type  empty;
            mandatory true;
            description "Use this attribute to enable QCN for a bridge";
        } // END of enabled definition.

        leaf cnm-transmit-priority  {
            type  uint8 {
                 range "0..7"  {
                    description "0..7: Supported range 0 - 7";
                 }
            }
            default "6";
            description "Use this attribute to set CNM transmit priority";
        } // END of cnm-transmit-priority definition.

        leaf-list cnpv-priorities  {
            type  uint8 {
                 range "0..7"  {
                    description "0..7: Supported range 0 - 7";
                 }
            }
            description "Use this attribute to set Congestion Notification Priority Value";
        } // END of cnpv-priorities definition.

    } // END of dcb-bridge-qcn-config definition.
    grouping dcb-bridge-qcn-top {
        description
            "Grouping for DCB QCN attributes";
        container qcn {
            description
                "qcn container";
            container config {
                presence "enable QCN";
                description
                    "DCB QCN Configuration data";
                uses dcb-bridge-qcn-config;
            } // END of config-container definition.
            container state {
                config false;
                description
                    "DCB QCN Operational data";
                uses dcb-bridge-qcn-config;
            } // END of state-container definition.
            uses dcb-bridge-qcn-defense-top;
        } // END of qcn-container definition.
    } // END of dcb-bridge-qcn-top definition.
    grouping dcb-bridge-config {
        description
            "DCB bridge attributes";
        leaf bridge-id  {
            type  leafref {
                path  "/ipi-network-instance:network-instances/ipi-network-instance:network-instance/ipi-network-instance:instance-name";
            }
            description "bridge-id";
        } // END of bridge-id definition.

        leaf dcb-enabled  {
            if-feature feature-list:NOT_HAVE_MARVELL;
            type  boolean;
            mandatory true;
            description "Enable Data-Center-Bridging";
        } // END of dcb-enabled definition.

        leaf enable-ets  {
            type  empty;
            description "Enhanced-Transmission-Selection";
        } // END of enable-ets definition.

        leaf enable-pfc  {
            type  empty;
            description "enable Priority-Flow-Control";
        } // END of enable-pfc definition.

        leaf enable-application-priority  {
            type  empty;
            description "enable Application-Priority";
        } // END of enable-application-priority definition.

    } // END of dcb-bridge-config definition.
    grouping pfc-dlr-config {
        description
            "Grouping for Priority-Flow-Control Deadlock Recovery Config";
        leaf action-drop  {
            if-feature feature-list:HAVE_DCB;
            type  empty;
            description "Priority-Flow-Control Deadlock Recovery Action";
        } // END of action-drop definition.

    } // END of pfc-dlr-config definition.
    grouping dcb-pfc-dlr-top {
        description
            "Grouping for Priority-Flow-Control Deadlock Recovery Top";
        container pfc-dlr {
            description
                "Priority-Flow-Control Deadlock Recovery";
            container config {
                description
                    "Priority Flow-Control Deadlock Recovery Config";
                uses pfc-dlr-config;
            } // END of config-container definition.
            container state {
                config false;
                description
                    "PFC Deadlock Recovery Action state";
                uses pfc-dlr-config;
            } // END of state-container definition.
        } // END of pfc-dlr-container definition.
    } // END of dcb-pfc-dlr-top definition.
    grouping dcb-bridge-top {
        description
            "Grouping for";
        container bridges {
            description
                "enclosing container for list of bridges";

            list bridge {
                key "bridge-id";
                description
                    "List of bridges";
                leaf bridge-id  {
                    type  leafref {
                        path  "../config/bridge-id";
                    }
                    description "Use this attribute to";
                } // END of bridge-id definition.

                container config {
                    description
                        "Configuration data for Data center bridging";
                    uses dcb-bridge-config;
                } // END of config-container definition.
                container state {
                    config false;
                    description
                        "Operational data for Data center bridging";
                    uses dcb-bridge-config;
                } // END of state-container definition.
                uses dcb-bridge-qcn-top;
            } // End of bridge-list
        } // END of bridges-container definition.
    } // END of dcb-bridge-top definition.

    grouping  dcb-grouping {
    description
        "Top level container for DCB";
    container dcb {
        if-feature feature-list:HAVE_DCB;
        description
            "Top level container for DCB";
        uses dcb-bridge-top;
        uses dcb-debug-top;
        uses dcb-pfc-dlr-top;
        uses interfaces-grouping;
    } // END of dcb-container definition.
    } // END of dcb-grouping definition.

    uses dcb-grouping;

    rpc pfc-if-deadlock-manual-recovery-start {
        if-feature feature-list:HAVE_DCB;
        description "Starts Priority-Flow-Control manual deadlock recovery on the specified
                    interface";
        input  {
            leaf name  {
                type string;
                mandatory true;
                description "Interface name";
            }
        }
    }

    rpc pfc-if-deadlock-manual-recovery-stop {
        if-feature feature-list:HAVE_DCB;
        description "Starts Priority-Flow-Control manual deadlock recovery on the specified
                    interface";
        input  {
            leaf name  {
                type string;
                mandatory true;
                description "Interface name";
            }
        }
    }

    rpc clear-if-deadlock-status {
        if-feature feature-list:HAVE_DCB;
        description "Clears Priority-Flow-Control interface deadlock status";
        input  {
            leaf name  {
                type string;
                mandatory true;
                description "Name of the interface to clear counters for. Specify NULL to clear
                            counters for all interfaces";
            }
        }
    }

    notification pfc-deadlock-detection {
        if-feature feature-list:HAVE_DCB;
        if-feature feature-list:NOT_HAVE_SWFWDR;
        if-feature feature-list:NOT_HAVE_SWFWDR;

        description "PFC deadlock detected.";

        leaf severity {
            type cml-data-types:cml_notif_severity_t;
            description "Notification severity level (value: MAJOR)";
        }

        leaf eventClass {
            type cml-data-types:cml_notif_class_t;
            description "Notification event class (value: MESSAGE)";
        }

        leaf message {
            type string;
            description " alarm message notification";
        }
    }

    notification pfc-deadlock-recovery {
        if-feature feature-list:HAVE_DCB;
        if-feature feature-list:NOT_HAVE_SWFWDR;
        if-feature feature-list:NOT_HAVE_SWFWDR;

        description "PFC deadlock recovered.";

        leaf severity {
            type cml-data-types:cml_notif_severity_t;
            description "Notification severity level (value: MINOR)";
        }

        leaf eventClass {
            type cml-data-types:cml_notif_class_t;
            description "Notification event class (value: MESSAGE)";
        }

        leaf message {
            type string;
            description " alarm message notification";
        }
    }

    notification pfc-pause-received {
        if-feature feature-list:HAVE_DCB;
        if-feature feature-list:NOT_HAVE_SWFWDR;
        if-feature feature-list:NOT_HAVE_SWFWDR;

        description "PFC pause received.";

        leaf severity {
            type cml-data-types:cml_notif_severity_t;
            description "Notification severity level (value: WARNING)";
        }

        leaf eventClass {
            type cml-data-types:cml_notif_class_t;
            description "Notification event class (value: MESSAGE)";
        }

        leaf message {
            type string;
            description " alarm message notification";
        }
    }

    notification pfc-pause-sent {
        if-feature feature-list:HAVE_DCB;
        if-feature feature-list:NOT_HAVE_SWFWDR;
        if-feature feature-list:NOT_HAVE_SWFWDR;

        description "PFC pause sent.";

        leaf severity {
            type cml-data-types:cml_notif_severity_t;
            description "Notification severity level (value: WARNING)";
        }

        leaf eventClass {
            type cml-data-types:cml_notif_class_t;
            description "Notification event class (value: MESSAGE)";
        }

        leaf message {
            type string;
            description " alarm message notification";
        }
    }

    notification ecn-marked-packets {
        if-feature feature-list:HAVE_DCB;
        if-feature feature-list:NOT_HAVE_SWFWDR;
        if-feature feature-list:NOT_HAVE_SWFWDR;

        description "ECN marked packets received.";

        leaf severity {
            type cml-data-types:cml_notif_severity_t;
            description "Notification severity level (value: WARNING)";
        }

        leaf eventClass {
            type cml-data-types:cml_notif_class_t;
            description "Notification event class (value: MESSAGE)";
        }

        leaf message {
            type string;
            description " alarm message notification";
        }
    }

}
