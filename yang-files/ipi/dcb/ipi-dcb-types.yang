/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dcb-types.yang
*
*/

module ipi-dcb-types {

    yang-version 1.1;

    namespace   "http://www.ipinfusion.com/yang/ocnos/ipi-dcb-types";

    prefix "ipi-dcb-types";

    organization
        "IP Infusion Inc.";

    contact
        "Address: 3965 Freedom Circle, Suite 200, Santa Clara, CA 95054
         Phone: +1 408-400-1900
         E-mail: support@ipinfusion.com
         Web: http://www.ipinfusion.com/";

    description
        "This module defines data types related to the DCB module";


    revision "2025-08-20" {
        description "Added PFC deadlock detection";
        reference " 0.2.0.";
    }

    revision "2022-10-27" {
        description "Initial Version";
        reference " 0.1.0.";
    }



    typedef  dcb_qcn_mode_t {
        type enumeration {
            enum admin {
                value 1;
                description "Admin-Mode";
            }
            enum auto {
                value 2;
                description "Automatic mode - LLDP should be enabled";
            }
            enum component {
                value 3;
                description "Defense mode same as the bridge level defense mode";
            }
        }
        description "type definition for DCB_QCN_MODE_T";
    }

    typedef  dcb_ets_mode_t {
        type enumeration {
            enum on {
                value 1;
                description "ON to force enable Enhanced-trasnsmission-selection";
            }
            enum auto {
                value 2;
                description "AUTO to negotiate Enhanced-transmission-selection capabilities";
            }
        }
        description "type definition for DCB_ETS_MODE_T";
    }

    typedef  dcb_pfc_mode_t {
        type enumeration {
            enum on {
                value 1;
                description "force enable priority-flow-control";
            }
            enum auto {
                value 2;
                description "negotiate priority-flow-control capabilities";
            }
        }
        description "type definition for DCB_PFC_MODE_T";
    }

    typedef  dcb_qcn_admin_defense_mode_t {
        type enumeration {
            enum disabled {
                value 1;
                description "Disabled Mode";
            }
            enum interior {
                value 2;
                description "Interior Mode";
            }
            enum interior-ready {
                value 3;
                description "interior-ready";
            }
            enum edge {
                value 4;
                description "Edge Mode";
            }
        }
        description "type definition for DCB_QCN_ADMIN_DEFENSE_MODE_T";
    }

    typedef  dcb_app_prio_protocol_t {
        type enumeration {
            enum tcp {
                value 2;
                description "Protocol Type tcp";
            }
            enum udp {
                value 3;
                description "Protocol Type udp";
            }
            enum both-tcp-udp {
                value 4;
                description "Protocol Type both-tcp-udp";
            }
        }
        description "type definition for DCB_APP_PRIO_PROTOCOL_T";
    }

    typedef  dcb_app_ether_hex_name_t {
        type enumeration {
            enum ip {
                value 2048;
                description "IP (0x0800)";
            }
            enum x25 {
                value 2053;
                description "CCITT X.25 (0x0805)";
            }
            enum arp {
                value 2054;
                description "Address Resolution Protocol (0x0806)";
            }
            enum g8bpqx25 {
                value 2303;
                description "G8BPQ AX.25 (0x08FF)";
            }
            enum ieeepup {
                value 2560;
                description "Xerox IEEE802.3 PUP (0x0a00)";
            }
            enum ieeeaddrtrans {
                value 2561;
                description "Xerox IEEE802.3 PUP Address Translation (0x0a01)";
            }
            enum dec {
                value 24576;
                description "DEC Assigned (0x6000)";
            }
            enum decdnadumpload {
                value 24577;
                description "DEC DNA Dump/Load (0x6001)";
            }
            enum decdnaremoteconsole {
                value 24578;
                description "DEC DNA Remote Console (0x6002)";
            }
            enum decdnarouting {
                value 24579;
                description "DEC DNA Routing (0x6003)";
            }
            enum declat {
                value 24580;
                description "DEC LAT (0x6004)";
            }
            enum decdiagnostics {
                value 24581;
                description "DEC Diagnostics (0x6005)";
            }
            enum rarp {
                value 32821;
                description "Reverse Address Resolution Protocol (0x8035)";
            }
            enum atalkddp {
                value 32923;
                description "Appletalk DDP (0x809B)";
            }
            enum atalkaarp {
                value 33011;
                description "Appletalk AARP (0x80F3)";
            }
            enum ipx {
                value 33079;
                description "IPX (0x8137)";
            }
            enum ipv6 {
                value 34525;
                description "IPv6 (0x86DD)";
            }
            enum atmmulti {
                value 34892;
                description "MultiProtocol Over ATM (0x884c)";
            }
            enum pppdiscovery {
                value 34915;
                description "PPPoE discovery (0x8863)";
            }
            enum pppsession {
                value 34916;
                description "PPPoE session (0x8864)";
            }
            enum atmtransport {
                value 34948;
                description "Frame-based ATM Transport (0x8884)";
            }
        }
        description "type definition for DCB_APP_ETHER_HEX_NAME_T";
    }

    typedef  dcb_app_ether_string_t {
        type string;
        description "type definition for DCB_APP_ETHER_STRING_T";
    }

    typedef  dcb_app_ether_name_t {
        type union {
            type dcb_app_ether_hex_name_t {

            }
            type dcb_app_ether_string_t {

            }
        }
        description "type definition for DCB_APP_ETHER_NAME_T";
    }

    typedef  dcb_app_ether_value_t {
        type string {
            length 5..6;
            pattern "0x[0-9a-fA-F]+";
        }
        description "type definition for DCB_APP_ETHER_VALUE_T";
    }

    typedef  cml_pfc_dlr_mode_t {
        type enumeration {
            enum timer {
                value 1;
                description "Finish PFC deadlock recovery after a configurable recovery-timer";
            }
            enum pfc-state-xon {
                value 2;
                description "Finish PFC deadlock recovery when a XON packet is received";
            }
        }
        description "type definition for CML_PFC_DLR_MODE_T";
    }

    typedef  cml_pfc_dlr_detection_granularity_t {
        type enumeration {
            enum 1 {
                value 1;
                description "1 millisecond";
            }
            enum 10 {
                value 2;
                description "10 millisecond";
            }
            enum 100 {
                value 3;
                description "100 millisecond";
            }
        }
        description "type definition for CML_PFC_DLR_DETECTION_GRANULARITY_T";
    }

}
