/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pfc-notifications.yang
*
*/

submodule ipi-pfc-notifications {

    yang-version 1.1;

    belongs-to  ipi-dcb { prefix ipi-dcb; }

    organization
        "IP Infusion Inc.";

    contact
        "Address: 3965 Freedom Circle, Suite 200, Santa Clara, CA 95054
         Phone: +1 408-400-1900
         E-mail: support@ipinfusion.com
         Web: http://www.ipinfusion.com/";

    description
        "PFC notifications";


    revision "2025-07-05" {
        description "Initial revision";
        reference " 0.1.0.";
    }



}
