/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dcb-interface.yang
*
*/

submodule ipi-dcb-interface {

    yang-version 1.1;

    belongs-to  ipi-dcb { prefix ipi-dcb; }

    import feature-list {
        prefix feature-list;
        revision-date 2026-09-15;
    }

    import ipi-dcb-types {
        prefix ipi-dcb-types;
        revision-date 2025-08-20;
    }

    import ipi-interface {
        prefix ipi-interface;
        revision-date 2026-03-10;
    }

    include ipi-dcb-common { revision-date 2022-10-27;}
    organization
        "IP Infusion Inc.";

    contact
        "Address: 3965 Freedom Circle, Suite 200, Santa Clara, CA 95054
         Phone: +1 408-400-1900
         E-mail: support@ipinfusion.com
         Web: http://www.ipinfusion.com/";

    description
        "Data model for IPI DCB interface related Configuration and Operational
                state";


    revision "2026-01-19" {
        description "Changed enabled priorities command to configure all values at once";
        reference " 0.5.5.";
    }

    revision "2025-12-17" {
        description "Add ordering change for configuration";
        reference " 0.5.4.";
    }

    revision "2025-09-22" {
        description "Fixed dbsync inssue in  PFC deadlock recovery";
        reference " 0.5.3.";
    }

    revision "2025-09-01" {
        description "Added PFC deadlock recovery CML error when passing a recovery-time argument when mode is not timer";
        reference " 0.5.2.";
    }

    revision "2025-08-26" {
        description "Added fix for application-priority delete db-synch issue";
        reference " 0.5.1.";
    }

    revision "2025-08-20" {
        description "Added PFC deadlock detection";
        reference " 0.5.0.";
    }

    revision "2025-08-08" {
        description "Added fix for switchport support for ETS and application-priority";
        reference " 0.4.14.";
    }

    revision "2025-07-30" {
        description "Removed bridge dependency for ETS and application-priority";
        reference " 0.4.13.";
    }

    revision "2025-06-07" {
        description "When Mlag is added with switchport, PFC config should not be removed";
        reference " 0.4.12.";
    }

    revision "2025-05-28" {
        description "When Mlag is mapped to PO, PO PFC configs are cleared";
        reference " 0.4.11.";
    }

    revision "2025-05-22" {
        description "PFC configs are changed with HITLESS so that it calls everytime";
        reference " 0.4.10.";
    }

    revision "2025-05-19" {
        description "data-center-bridging global command disabile dependecy removed for PFC";
        reference " 0.4.9.";
    }

    revision "2025-05-13" {
        description "Increasing maximum PFC link-delay-allowance";
        reference " 0.4.8.";
    }

    revision "2025-05-12" {
        description "Switchport dependency is added so that PFC also removed";
        reference " 0.4.7.";
    }

    revision "2025-04-28" {
        description "Removed the bridge dependency for PFC";
        reference " 0.4.6.";
    }

    revision "2025-02-09" {
        description "Removed the bridge dependency for DCBX";
        reference " 0.4.5.";
    }

    revision "2025-01-27" {
        description "Increase maximum PFC link-delay-allowance";
        reference " 0.4.4.";
    }

    revision "2024-09-11" {
        description "validation is not proper in cli-command";
        reference " 0.4.3.";
    }

    revision "2024-06-03" {
        description "Masking dcb_enabled parameter for Marvell platform ";
        reference " 0.4.2.";
    }

    revision "2024-05-21" {
        description "Added missing platform check for application-priority";
        reference " 0.4.1.";
    }

    revision "2024-05-09" {
        description "Added when tag for the attribute pfc-mode";
        reference " 0.4.0.";
    }

    revision "2022-12-19" {
        description "Added flag to handle replace  operation";
        reference " 0.3.0.";
    }

    revision "2022-11-16" {
        description "adding platform validation function checks for DCB CLI";
        reference " 0.2.0.";
    }

    revision "2022-10-27" {
        description "Initial Version";
        reference " 0.1.0.";
    }

    grouping dcb-app-prio-port-map-config {
        description
            "Grouping for application priority port map attribute";
        leaf protocol-type  {
            type  ipi-dcb-types:dcb_app_prio_protocol_t;
            description "Use this attribute to configure protocol type";
        } // END of protocol-type definition.

        leaf port-number  {
            type  uint16 {
                 range "1..1023"  {
                    description "1..1023: Supported range 1 - 1023";
                 }
            }
            description "Use this attribute to configure port number";
        } // END of port-number definition.

        leaf priority-value  {
            type  uint8 {
                 range "0..7"  {
                    description "0..7: Supported range 0 - 7";
                 }
            }
            description "Use this attribute to set priority value";
        } // END of priority-value definition.

    } // END of dcb-app-prio-port-map-config definition.
    grouping dcb-app-prio-port-map-top {
        description
            "Grouping for application priority port map";
        container port-mappings {
            description
                "enclosing container for list for port mapping";

            list port-mapping {
            // when " ipi-dcb-interface:interfaces/interface/application-priority/config/enabled ";
                key "protocol-type port-number priority-value";
                description
                    "List of port mapping";
                leaf protocol-type  {
                    type  leafref {
                        path  "../config/protocol-type";
                    }
                    description "Use this attribute to configure protocol type";
                } // END of protocol-type definition.

                leaf port-number  {
                    type  leafref {
                        path  "../config/port-number";
                    }
                    description "Use this attribute to configure port number";
                } // END of port-number definition.

                leaf priority-value  {
                    type  leafref {
                        path  "../config/priority-value";
                    }
                    description "Use this attribute to set priority value";
                } // END of priority-value definition.

                container config {
                    description
                        "container for configurable attributes of application priority port map";
                    uses dcb-app-prio-port-map-config;
                } // END of config-container definition.
                container state {
                    config false;
                    description
                        "container for operational attributes of application priority port map";
                    uses dcb-app-prio-port-map-config;
                } // END of state-container definition.
            } // End of port-mapping-list
        } // END of port-mappings-container definition.
    } // END of dcb-app-prio-port-map-top definition.
    grouping dcb-app-prio-svc-map-config {
        description
            "Grouping for application priority serive mapping";
        leaf protocol-type  {
            type  ipi-dcb-types:dcb_app_prio_protocol_t;
            description "Use this attribute to configure protocol type";
        } // END of protocol-type definition.

        leaf service-name  {
            type  string {
                length "1..1965";
                pattern "[^?' =,>|]+";
            }
            description "Use this attribute to configure service name";
        } // END of service-name definition.

        leaf priority-value  {
            type  uint8 {
                 range "0..7"  {
                    description "0..7: Supported range 0 - 7";
                 }
            }
            description "Use this attribute to set priority value of service map";
        } // END of priority-value definition.

    } // END of dcb-app-prio-svc-map-config definition.
    grouping dcb-app-prio-svc-map-top {
        description
            "Grouping for Application priority service map";
        container service-mappings {
            description
                "enclosing container for list Application priority service maps";

            list service-mapping {
            // when " ipi-dcb-interface:interfaces/interface/application-priority/config/enabled ";
                key "protocol-type service-name priority-value";
                description
                    "List of Application priority service map";
                leaf protocol-type  {
                    type  leafref {
                        path  "../config/protocol-type";
                    }
                    description "Use this attribute to configure protocol type";
                } // END of protocol-type definition.

                leaf service-name  {
                    type  leafref {
                        path  "../config/service-name";
                    }
                    description "Use this attribute to configure service name";
                } // END of service-name definition.

                leaf priority-value  {
                    type  leafref {
                        path  "../config/priority-value";
                    }
                    description "Use this attribute to set priority value of service map";
                } // END of priority-value definition.

                container config {
                    description
                        "container for configurational attributes of service mapping";
                    uses dcb-app-prio-svc-map-config;
                } // END of config-container definition.
                container state {
                    config false;
                    description
                        "container for operational attributes of service mapping";
                    uses dcb-app-prio-svc-map-config;
                } // END of state-container definition.
            } // End of service-mapping-list
        } // END of service-mappings-container definition.
    } // END of dcb-app-prio-svc-map-top definition.
    grouping dcb-app-prio-eth-name-map-config {
        description
            "grouping for ether name maps";
        leaf ether-name  {
            type  ipi-dcb-types:dcb_app_ether_name_t;
            description "Use this attribute to configure ether name";
        } // END of ether-name definition.

        leaf priority-value  {
            type  uint8 {
                 range "0..7"  {
                    description "0..7: Supported range 0 - 7";
                 }
            }
            description "Use this attribute to configure priority";
        } // END of priority-value definition.

    } // END of dcb-app-prio-eth-name-map-config definition.
    grouping dcb-app-prio-eth-name-map-top {
        description
            "Grouping for application priority ethernet name map attributes";
        container ethertype-name-mappings {
            description
                "enclosing container for list for ethnet maps";

            list ethertype-name-mapping {
            // when " ipi-dcb-interface:interfaces/interface/application-priority/config/enabled ";
                key "ether-name priority-value";
                description
                    "List of ethernet name maps";
                leaf ether-name  {
                    type  leafref {
                        path  "../config/ether-name";
                    }
                    description "Use this attribute to configure ether name";
                } // END of ether-name definition.

                leaf priority-value  {
                    type  leafref {
                        path  "../config/priority-value";
                    }
                    description "Use this attribute to configure priority";
                } // END of priority-value definition.

                container config {
                    description
                        "container for configurable attributes for ether name maps";
                    uses dcb-app-prio-eth-name-map-config;
                } // END of config-container definition.
                container state {
                    config false;
                    description
                        "container for operation attribute for ether name maps";
                    uses dcb-app-prio-eth-name-map-config;
                } // END of state-container definition.
            } // End of ethertype-name-mapping-list
        } // END of ethertype-name-mappings-container definition.
    } // END of dcb-app-prio-eth-name-map-top definition.
    grouping dcb-app-prio-eth-val-map-config {
        description
            "grouping for ether value maps";
        leaf ether-value  {
            type  ipi-dcb-types:dcb_app_ether_value_t;
            description "Use this attribute to configure ether value";
        } // END of ether-value definition.

        leaf priority-value  {
            type  uint8 {
                 range "0..7"  {
                    description "0..7: Supported range 0 - 7";
                 }
            }
            description "Use this attribute to configure priority";
        } // END of priority-value definition.

    } // END of dcb-app-prio-eth-val-map-config definition.
    grouping dcb-app-prio-eth-val-map-top {
        description
            "Grouping for application priority ethernet value map attributes";
        container ethertype-value-mappings {
            description
                "enclosing container for list for ethnet value maps";

            list ethertype-value-mapping {
            // when " ipi-dcb-interface:interfaces/interface/application-priority/config/enabled ";
                key "ether-value priority-value";
                description
                    "List of ethernet value maps";
                leaf ether-value  {
                    type  leafref {
                        path  "../config/ether-value";
                    }
                    description "Use this attribute to configure ether value";
                } // END of ether-value definition.

                leaf priority-value  {
                    type  leafref {
                        path  "../config/priority-value";
                    }
                    description "Use this attribute to configure priority";
                } // END of priority-value definition.

                container config {
                    description
                        "container for configurable attributes for ether value maps";
                    uses dcb-app-prio-eth-val-map-config;
                } // END of config-container definition.
                container state {
                    config false;
                    description
                        "container for operation attribute for ether value maps";
                    uses dcb-app-prio-eth-val-map-config;
                } // END of state-container definition.
            } // End of ethertype-value-mapping-list
        } // END of ethertype-value-mappings-container definition.
    } // END of dcb-app-prio-eth-val-map-top definition.
    grouping dcb-if-app-priority-config {
        description
            "Grouping for application priority attributes";
        leaf enabled  {
            type  empty;
            mandatory true;
            description "Use this attribute to enable application priority";
        } // END of enabled definition.

        leaf accept-peer-config  {
            // when " ipi-dcb-interface:interfaces/interface/application-priority/config/enabled ";
            type  empty;
            description "Use this attribute to accept peer configuration";
        } // END of accept-peer-config definition.

        leaf advertise-local-config  {
            // when " ipi-dcb-interface:interfaces/interface/application-priority/config/enabled ";
            type  empty;
            description "Use this attribute to advertise local configuration to peer";
        } // END of advertise-local-config definition.

    } // END of dcb-if-app-priority-config definition.
    grouping dcb-if-app-priority-top {
        description
            "Grouping of app priority attributes";
        container application-priority {
            description
                "enclosing container for application priority";
            container config {
                // when " ipi-dcb-interface:interfaces/interface/application-priority/config/enabled ";
                presence "To enable application-priority";
                description
                    "configurational attribute for application priority";
                uses dcb-if-app-priority-config;
            } // END of config-container definition.
            container state {
                config false;
                description
                    "Operational attribute for application priority";
                uses dcb-if-app-priority-config;
            } // END of state-container definition.
            uses dcb-app-prio-port-map-top;
            uses dcb-app-prio-svc-map-top;
            uses dcb-app-prio-eth-name-map-top;
            uses dcb-app-prio-eth-val-map-top;
        } // END of application-priority-container definition.
    } // END of dcb-if-app-priority-top definition.
    grouping dcb-if-ets-tcg-config {
        description
            "Grouping for ets traffic class group attributes";
        leaf group-index  {
            type  uint8 {
                 range "0..7"  {
                    description "0..7:Feature : HAVE_BROADCOM Supported range 0 - 1Not Feature :
                            HAVE_BROADCOM  Supported range 0 - 7";
                 }
            }
            description "Use this attribute to configure group index";
        } // END of group-index definition.

        leaf-list mapped-priorities  {
            type  uint8 {
                 range "0..7"  {
                    description "0..7: Supported range 0 - 7";
                 }
            }
            description "Use this attribute to configure/unconfigure priority";
        } // END of mapped-priorities definition.

        leaf bandwidth-percentage  {
            // when " ipi-dcb-interface:interfaces/interface/enhanced-transmission-selection/traffic-class-groups/traffic-class-group/config/mapped-priorities ";
            type  uint8 {
                 range "0..100"  {
                    description "0..100: Supported range 0 - 100";
                 }
            }
            description "Use this attrribute to set bandwidth percentage";
        } // END of bandwidth-percentage definition.

    } // END of dcb-if-ets-tcg-config definition.
    grouping dcb-if-ets-config {
        description
            "Grouping for enhanced transmission selection attributes";
        leaf advertise-local-config  {
            type  empty;
            description "Use this attribute to advertise local configuration to peer";
        } // END of advertise-local-config definition.

        leaf accept-peer-config  {
            type  empty;
            description "Use this attribute to accept peer configuration";
        } // END of accept-peer-config definition.

        leaf max-traffic-class-groups  {
            type  uint8 {
                 range "0..7"  {
                    description "0..7:Feature : HAVE_BROADCOM Supported range 0 - 2Not Feature :
                            HAVE_BROADCOM  Supported range 0 - 7";
                 }
            }
            description "Use this attrribute to set maximum traffic class groups";
        } // END of max-traffic-class-groups definition.

    } // END of dcb-if-ets-config definition.
    grouping dcb-if-ets-top {
        description
            "Grouping of enhanced transmission selection attributes";
        container enhanced-transmission-selection {
            description
                "enclosing container for enhanced transmission selection attributes";
            container config {
                // when " ipi-dcb-interface:interfaces/interface/config/ets-mode ";
                description
                    "Container for configuration attributes of enhanced transmission
                            selection";
                uses dcb-if-ets-config;
            } // END of config-container definition.
            container state {
                config false;
                description
                    "Container for Operational attributes of enhanced transmission
                            selection";
                uses dcb-if-ets-config;
            } // END of state-container definition.
            container traffic-class-groups {
                description
                    "enclosing container for traffic class groups";

                list traffic-class-group {
                // when " ipi-dcb-interface:interfaces/interface/config/ets-mode ";
                    key "group-index";
                    description
                        "List of traffic class group";
                    leaf group-index  {
                        type  leafref {
                            path  "../config/group-index";
                        }
                        description "Use this attribute to configure group index";
                    } // END of group-index definition.

                    container config {
                        description
                            "configuration attribute of traffic class group";
                        uses dcb-if-ets-tcg-config;
                    } // END of config-container definition.
                    container state {
                        config false;
                        description
                            "Operational attribute of traffic class group";
                        uses dcb-if-ets-tcg-config;
                    } // END of state-container definition.
                } // End of traffic-class-group-list
            } // END of traffic-class-groups-container definition.
        } // END of enhanced-transmission-selection-container definition.
    } // END of dcb-if-ets-top definition.
    grouping dcb-if-pfc-config {
        description
            "Grouping for Priority flow control attributes";
        leaf accept-peer-config  {
            type  empty;
            description "Use this attribute to accept peer configuration";
        } // END of accept-peer-config definition.

        leaf advertise-local-config  {
            type  empty;
            description "Use this attribute to advertise local configuration to peer";
        } // END of advertise-local-config definition.

        leaf cap  {
            type  uint8 {
                 range "0..8"  {
                    description "0..8: Supported range 0 - 8";
                 }
            }
            description "Use this attribute to set cap value";
        } // END of cap definition.

        leaf link-delay-allowance  {
            type  uint32 {
                 range "0..4294967295"  {
                    description "0..4294967295:Feature : HAVE_BROADCOM Supported range 0 - 8388608Not
                            Feature : HAVE_BROADCOM  Supported range 0 - 4294967295";
                 }
            }
            description "Use this attribute to set link delay allowance";
        } // END of link-delay-allowance definition.

    } // END of dcb-if-pfc-config definition.
    grouping dcb-if-pfc-enabled-priorities-config {
        description
            "Grouping for PFC priorities";
        leaf zero  {
            type  empty;
            description "";
        } // END of zero definition.

        leaf one  {
            type  empty;
            description "";
        } // END of one definition.

        leaf two  {
            type  empty;
            description "";
        } // END of two definition.

        leaf three  {
            type  empty;
            description "";
        } // END of three definition.

        leaf four  {
            type  empty;
            description "";
        } // END of four definition.

        leaf five  {
            type  empty;
            description "";
        } // END of five definition.

        leaf six  {
            type  empty;
            description "";
        } // END of six definition.

        leaf seven  {
            type  empty;
            description "";
        } // END of seven definition.

    } // END of dcb-if-pfc-enabled-priorities-config definition.
    grouping dcb-if-pfc-dlr-config {
        description
            "Grouping for Priority flow control deadlock recovery attributes";
        leaf recovery-mode  {
            type  ipi-dcb-types:cml_pfc_dlr_mode_t;
            description "Priority-Flow-Control deadlock detection and recovery";
        } // END of recovery-mode definition.

        leaf detection-multiplier  {
            // when " ../recovery-mode ";
            type  uint32 {
                 range "1..1599"  {
                    description "1..1599: Supported range 1 - 1599";
                 }
            }
            description "PFC deadlock detection multiplier. Range depends on granularity:
                        100-1599 for 100ms granularity; 10-159 for 10 ms granularity; 1-15 for
                        1 ms granularity";
        } // END of detection-multiplier definition.

        leaf time-granularity  {
            // when " ../recovery-mode ";
            type  ipi-dcb-types:cml_pfc_dlr_detection_granularity_t;
            description "PFC deadlock detection time granularity";
        } // END of time-granularity definition.

        leaf recovery-time  {
            type  uint32 {
                 range "100..1599"  {
                    description "100..1599: Supported range 100 - 1599";
                 }
            }
            description "PFC deadlock recovery time";
        } // END of recovery-time definition.

    } // END of dcb-if-pfc-dlr-config definition.
    grouping dcb-if-pfc-top {
        description
            "Grouping of priority flow control attributes";
        container priority-flow-control {
            description
                "enclosing container for priority flow control";
            container config {
                // when " ipi-dcb-interface:interfaces/interface/config/pfc-mode ";
                description
                    "Container for configuration attributes of Priority flow control";
                uses dcb-if-pfc-config;
            } // END of config-container definition.
            container state {
                config false;
                description
                    "Container for Operational attributes of Priority flow control";
                uses dcb-if-pfc-config;
            } // END of state-container definition.
            container enabled-priorities {
                description
                    "Use this attrribute to set traffic priority";
                container config {
                    // when " ipi-dcb-interface:interfaces/interface/config/pfc-mode ";
                    description
                        "Container for configuration attributes of traffic priorities";
                    uses dcb-if-pfc-enabled-priorities-config;
                } // END of config-container definition.
                container state {
                    config false;
                    description
                        "Container for Operational attributes of traffic priorities";
                    uses dcb-if-pfc-enabled-priorities-config;
                } // END of state-container definition.
            } // END of enabled-priorities-container definition.
            container deadlock-recovery {
                if-feature feature-list:HAVE_DCB;
                description
                    "enclosing container for priority flow control deadlock recovery";
                container config {
                    // when " ipi-dcb-interface:interfaces/interface/config/pfc-mode ";
                    description
                        "Container for configuration attributes of Priority flow control
                                deadlock recovery";
                    uses dcb-if-pfc-dlr-config;
                } // END of config-container definition.
                container state {
                    config false;
                    description
                        "Container for Operational attributes of Priority flow control deadlock
                                recovery";
                    uses dcb-if-pfc-dlr-config;
                } // END of state-container definition.
            } // END of deadlock-recovery-container definition.
        } // END of priority-flow-control-container definition.
    } // END of dcb-if-pfc-top definition.
    grouping dcb-if-qcn-cp-config {
        description
            "DCB QCN cp config";
        leaf cnpv-value  {
            type  leafref {
                path  "/ipi-dcb:dcb/ipi-dcb:bridges/ipi-dcb:bridge/ipi-dcb:qcn/ipi-dcb:config/ipi-dcb:cnpv-priorities";
            }
            description "Use this attribute to configure cnpv value";
        } // END of cnpv-value definition.

        leaf sample-base  {
            type  uint32 {
                 range "1024..4294967295"  {
                    description "1024..4294967295:Not Feature : HAVE_BROADCOM  Supported range 10000 -
                            4294967295Feature : HAVE_BROADCOM Supported range 1024 - 10240";
                 }
            }
            description "Use this attribute to configure sample base value";
        } // END of sample-base definition.

        leaf weight  {
            type  int8;
            description "Use this attribute to configure weight";
        } // END of weight definition.

        leaf min-header-octet  {
            if-feature feature-list:NOT_HAVE_BROADCOM;
            type  uint8 {
                 range "0..64"  {
                    description "0..64: Supported range 0 - 64";
                 }
            }
            description "Use this attribute to configure minimum header octet";
        } // END of min-header-octet definition.

    } // END of dcb-if-qcn-cp-config definition.
    grouping dcb-if-qcn-cp-top {
        description
            "Grouping for QCN Congestion Point";
        container congestion-points {
            description
                "enclosing container for list for Congestion points";

            list congestion-point {
                key "cnpv-value";
                description
                    "List of Congestion points";
                leaf cnpv-value  {
                    type  leafref {
                        path  "../config/cnpv-value";
                    }
                    description "Use this attribute to configure cnpv value";
                } // END of cnpv-value definition.

                container config {
                    description
                        "container for configurable attributes of congestion points";
                    uses dcb-if-qcn-cp-config;
                } // END of config-container definition.
                container state {
                    config false;
                    description
                        "container for operational attribute for congestion points";
                    uses dcb-if-qcn-cp-config;
                } // END of state-container definition.
            } // End of congestion-point-list
        } // END of congestion-points-container definition.
    } // END of dcb-if-qcn-cp-top definition.
    grouping dcb-if-qcn-defense-top {
        description
            "Grouping for DCB QCN attributes";
        container qcn {
            description
                "qcn container";
            container cnpv-defenses {
                description
                    "enclosing container for List of cnpv defense";

                list cnpv-defense {
                    key "priority-value";
                    description
                        "List of cnpv defense";
                    leaf priority-value  {
                        type  leafref {
                            path  "../config/priority-value";
                        }
                        description "Use this attribute to configure cnpv defense priority value";
                    } // END of priority-value definition.

                    container config {
                        description
                            "DCB QCN Configuration data";
                        uses dcb-qcn-defense-common-config;
                    } // END of config-container definition.
                    container state {
                        config false;
                        description
                            "DCB QCN Operational data";
                        uses dcb-qcn-defense-common-config;
                    } // END of state-container definition.
                } // End of cnpv-defense-list
            } // END of cnpv-defenses-container definition.
            uses dcb-if-qcn-cp-top;
        } // END of qcn-container definition.
    } // END of dcb-if-qcn-defense-top definition.
    grouping dcb-interface-config {
        description
            "DCB bridge attributes";
        leaf name  {
            type  leafref {
                path  "/ipi-interface:interfaces/ipi-interface:interface/ipi-interface:name";
            }
            description "Interface name";
        } // END of name definition.

        leaf pfc-mode  {
            type  ipi-dcb-types:dcb_pfc_mode_t;
            description "Enable Data-Center-Bridging";
        } // END of pfc-mode definition.

        leaf ets-mode  {
            type  ipi-dcb-types:dcb_ets_mode_t;
            description "Use this attribute to set Enhanced Transmission Selection mode";
        } // END of ets-mode definition.

    } // END of dcb-interface-config definition.

    grouping  interfaces-grouping {
    description
        "Top level container for DCB interface";
    container interfaces {
        if-feature feature-list:HAVE_DCB;
        description
            "Top level container for DCB interface";

        list interface {
            if-feature feature-list:HAVE_DCB;
            key "name";
            description
                "List of interfaces";
            leaf name  {
                type  leafref {
                    path  "../config/name";
                }
                description "Interface name";
            } // END of name definition.

            container config {
                description
                    "Configuration data for interace related DCB config";
                uses dcb-interface-config;
            } // END of config-container definition.
            container state {
                config false;
                description
                    "Operational data for interace related DCB config";
                uses dcb-interface-config;
            } // END of state-container definition.
            uses dcb-if-qcn-defense-top;
            uses dcb-if-pfc-top;
            uses dcb-if-ets-top;
            uses dcb-if-app-priority-top;
        } // End of interface-list
    } // END of interfaces-container definition.
    } // END of interfaces-grouping definition.


}
