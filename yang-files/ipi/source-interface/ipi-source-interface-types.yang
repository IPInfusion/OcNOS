/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-source-interface-types.yang
*
*/

module ipi-source-interface-types {

    yang-version 1.1;

    namespace   "http://www.ipinfusion.com/yang/ocnos/ipi-source-interface-types";

    prefix "ipi-source-interface-types";

    organization
        "IP Infusion Inc.";

    contact
        "Address: 3965 Freedom Circle, Suite 200, Santa Clara, CA 95054
         Phone: +1 408-400-1900
         E-mail: support@ipinfusion.com
         Web: http://www.ipinfusion.com/";

    description
        "Source Interface types";


    revision "2025-03-19" {
        description "Removed 0 option and Added default port numbers for TACACS+, NTP, SNMP, Rsyslog, and RADIUS.";
        reference " 0.4.0.";
    }

    revision "2024-09-26" {
        description "Updated snmp port number ";
        reference " 0.3.0.";
    }

    revision "2022-06-01" {
        description "Updated the yang file with feature";
        reference " 0.2.0.";
    }

    revision "2021-08-27" {
        description "Initial version";
        reference "Initial Version";
    }



    typedef  src_intf_status_t {
        type enumeration {
            enum Inactive {
                value 0;
                description "Source Interface inactive";
            }
            enum Active {
                value 1;
                description "Source Interface is active";
            }
        }
        description "type definition for SRC_INTF_STATUS_T";
    }

    typedef  src_intf_proto_types_t {
        type enumeration {
            enum tacacs+ {
                value 49;
                description "Protocol TACACS+";
            }
            enum ntp {
                value 123;
                description "Protocol NTP";
            }
            enum snmp {
                value 162;
                description "Protocol SNMP";
            }
            enum syslog {
                value 514;
                description "Protocol Rsyslog";
            }
            enum radius {
                value 1812;
                description "Protocol RADIUS";
            }
        }
        description "type definition for SRC_INTF_PROTO_TYPES_T";
    }

    typedef  src_intf_port_number_default_t {
        type enumeration {
            enum 49 {
                value 49;
                description "Default Source Interface Protocol Port Number for TACACS+";
            }
            enum 123 {
                value 123;
                description "Default Source Interface Protocol Port Number for NTP";
            }
            enum 162 {
                value 162;
                description "Default Source Interface Protocol Port Number for SNMP";
            }
            enum 514 {
                value 514;
                description "Default Source Interface Protocol Port Number for Rsyslog";
            }
            enum 1812 {
                value 1812;
                description "Default Source Interface Protocol Port Number for RADIUS";
            }
        }
        description "type definition for SRC_INTF_PORT_NUMBER_DEFAULT_T";
    }

    typedef  src_intf_port_number_t {
        type union {
            type src_intf_port_number_default_t {

            }
            type uint16 {
                range "1025..65535";

            }
        }
        description "type definition for SRC_INTF_PORT_NUMBER_T";
    }

}
