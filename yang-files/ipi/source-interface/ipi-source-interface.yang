/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-source-interface.yang
*
*/

module ipi-source-interface {

    yang-version 1.1;

    namespace   "http://www.ipinfusion.com/yang/ocnos/ipi-source-interface";

    prefix "ipi-source-interface";

    import ietf-inet-types {
        prefix inet;
        revision-date 2013-07-15;
    }

    import ipi-interface {
        prefix ipi-interface;
        revision-date 2026-03-10;
    }

    import ipi-network-instance {
        prefix ipi-network-instance;
        revision-date 2026-08-12;
    }

    import ipi-vrf {
        prefix ipi-vrf;
        revision-date 2026-08-12;
    }

    import ipi-source-interface-types {
        prefix ipi-source-interface-types;
        revision-date 2025-03-19;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Source Interface Rules";


    revision "2025-05-20" {
        description "moved unset to correct xpath and updated cli-delete-sequence";
        reference " 0.6.1.";
    }

    revision "2025-03-19" {
        description "Added support for multiple ports per protocol and made port number as RDN";
        reference " 0.6.0.";
    }

    revision "2024-09-29" {
        description "Enable Source Interface service on user defined VRFs";
        reference " 0.5.2.";
    }

    revision "2024-09-26" {
        description "Changed port number for snmp";
        reference " 0.5.1.";
    }

    revision "2024-07-08" {
        description "Changed vrf-name as RDN attribute";
        reference " 0.5.0.";
    }

    revision "2022-11-16" {
        description "Removed unwanted cliprependstr tag";
        reference " 0.4.0.";
    }

    revision "2022-06-01" {
        description "Updated the yang file with feature";
        reference " 0.2.3.";
    }

    revision "2022-01-31" {
        description "Change attributes port-number and vrf-name from container source-nat-mappings to be mandatory";
        reference " 0.2.2.";
    }

    revision "2021-10-12" {
        description "Review corrections";
        reference " 0.2.1.";
    }

    revision "2021-08-27" {
        description "Restructured module in accordance with OpenConfig style";
        reference " 0.2.0.";
    }

    revision "2020-10-07" {
        description "Initial Version";
        reference " 0.3.0.";
    }

    grouping source-interface-address-family-source-nat-mapping-state {
        description
            "Source Interface Address Family Source NAT Mapping State Grouping";
        leaf address  {
            type  inet:ip-address;
            description "Source Interface Address";
        } // END of address definition.

        leaf status  {
            type  ipi-source-interface-types:src_intf_status_t;
            description "Source Iterface Address";
        } // END of status definition.

    } // END of source-interface-address-family-source-nat-mapping-state definition.
    grouping source-interface-address-family-source-nat-mapping-config {
        description
            "Source Interface Address Family Source NAT Mapping Configuration
                        Grouping";
        leaf interface-name  {
            type  leafref {
                path  "/ipi-interface:interfaces/ipi-interface:interface/ipi-interface:name";
            }
            description "Interface name";
        } // END of interface-name definition.

        leaf protocol-type  {
            type  ipi-source-interface-types:src_intf_proto_types_t;
            description "Protocol type to apply the source-interface.";
        } // END of protocol-type definition.

        leaf port-number  {
            type  ipi-source-interface-types:src_intf_port_number_t;
            description "Protocol port number to apply the source-interface.";
        } // END of port-number definition.

        leaf vrf-name  {
            if-feature feature-list:HAVE_VRF;
            type  leafref {
                path  "/ipi-network-instance:network-instances/ipi-network-instance:network-instance/ipi-vrf:vrf/ipi-vrf:config/ipi-vrf:vrf-name";
            }
            description "VRF to apply the source-interface.";
        } // END of vrf-name definition.

    } // END of source-interface-address-family-source-nat-mapping-config definition.
    grouping source-interface-address-family-source-nat-mappings-top {
        description
            "Source Interface Address Family Source NAT Mapping Grouping";
        container source-nat-mappings {
            description
                "Source NAT Mappings";

            list source-nat-mapping {
                key "interface-name protocol-type port-number vrf-name";
                description
                    "Source NAT Mapping";
                leaf interface-name  {
                    type  leafref {
                        path  "../config/interface-name";
                    }
                    description "Interface name";
                } // END of interface-name definition.

                leaf protocol-type  {
                    type  leafref {
                        path  "../config/protocol-type";
                    }
                    description "Protocol type to apply the source-interface.";
                } // END of protocol-type definition.

                leaf port-number  {
                    type  leafref {
                        path  "../config/port-number";
                    }
                    description "Protocol port number to apply the source-interface.";
                } // END of port-number definition.

                leaf vrf-name  {
                    type  leafref {
                        path  "../config/vrf-name";
                    }
                    description "VPN routing/forwarding Instance name";
                } // END of vrf-name definition.

                container config {
                    description
                        "Configuration data for Source Interface Address Family Source NAT
                                Mapping";
                    uses source-interface-address-family-source-nat-mapping-config;
                } // END of config-container definition.
                container state {
                    config false;
                    description
                        "Operational state data for Source Interface Address Family Source NAT
                                Mapping";
                    uses source-interface-address-family-source-nat-mapping-config;
                    uses source-interface-address-family-source-nat-mapping-state;
                } // END of state-container definition.
            } // End of source-nat-mapping-list
        } // END of source-nat-mappings-container definition.
    } // END of source-interface-address-family-source-nat-mappings-top definition.
    grouping source-interface-address-family-ipv6-top {
        description
            "Source Interface Address Family IPv6 Grouping";
        container address-family-ipv6 {
            if-feature feature-list:HAVE_IPV6;
            description
                "Source Interface Address Family IPv6";
            uses source-interface-address-family-source-nat-mappings-top;
        } // END of address-family-ipv6-container definition.
    } // END of source-interface-address-family-ipv6-top definition.
    grouping source-interface-address-family-ipv4-top {
        description
            "Source Interface Address Family IPv4 Grouping";
        container address-family-ipv4 {
            description
                "Source Interface Address Family IPv4";
            uses source-interface-address-family-source-nat-mappings-top;
        } // END of address-family-ipv4-container definition.
    } // END of source-interface-address-family-ipv4-top definition.

    grouping  source-interface-grouping {
    description
        "Source Interface Rules";
    container source-interface {
        if-feature feature-list:HAVE_HOSTPD;
        description
            "Source Interface Rules";
        uses source-interface-address-family-ipv4-top;
        uses source-interface-address-family-ipv6-top;
    } // END of source-interface-container definition.
    } // END of source-interface-grouping definition.

    uses source-interface-grouping;

}
