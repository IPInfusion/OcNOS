/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-host.yang
*
*/

module ipi-host {

    yang-version 1.1;

    namespace   "http://www.ipinfusion.com/yang/ocnos/ipi-host";

    prefix "ipi-host";

    import cml-data-types {
        prefix cml-data-types;
        revision-date 2026-05-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Top level HOST configuration module";


    revision "2026-01-20" {
        description "Removed skip yang and skip-dependency-validation flag from banner-motd and banner-motd-file attr. Adder error message";
        reference " 0.7.0.";
    }

    revision "2025-02-18" {
        description "Added utils api to handle upgrade scenario of banner motd file configuration";
        reference " 0.6.0.";
    }

    revision "2025-01-24" {
        description "Added CML_SKIP_HITLESS_MERGE flag for proper password encryption";
        reference " 0.5.4.";
    }

    revision "2025-01-15" {
        description "Removed include-input-for-unset cliflag from enable password";
        reference " 0.5.3.";
    }

    revision "2024-09-05" {
        description "Add support for CLI prompt timestamping";
        reference " 0.5.2.";
    }

    revision "2024-09-03" {
        description "Update terminal monitor default behavior CLI command syntax";
        reference " 0.5.1.";
    }

    revision "2024-08-26" {
        description "Add support to control terminal monitor default behavior";
        reference " 0.5.0.";
    }

    revision "2024-05-30" {
        description "Password Encryption to be enabled by default";
        reference " 0.4.0.";
    }

    revision "2024-01-02" {
        description "Disabling default auto enable for remote authentication";
        reference " 0.3.2.";
    }

    revision "2023-11-06" {
        description "Multiline banner feature";
        reference " 0.3.1.";
    }

    revision "2023-10-16" {
        description "Updated service-passwd-encryption flag";
        reference " 0.3.0.";
    }

    revision "2023-05-08" {
        description "Changed system container name to system-host";
        reference " 0.2.0.";
    }

    revision "2023-02-03" {
        description "Initial Version";
        reference " 0.1.0.";
    }

    grouping host-config {
        description
            "Grouping for host config objects";
        leaf banner-motd  {
            type  cml-data-types:cml_banner_t;
            description "Use this attribute to set the login banner for the OcNOS device.";
        } // END of banner-motd definition.

        leaf banner-motd-file  {
            type  cml-data-types:cml_file_t;
            description "Use this attribute to set the filename containing the banner message";
        } // END of banner-motd-file definition.

        leaf service-passwd-encryption  {
            type  boolean;
            default true;
            description "Use this attribute to enable password encryption.";
        } // END of service-passwd-encryption definition.

        leaf service-term-length  {
            type  uint16 {
                 range "0..512"  {
                    description "0..512: Supported range 0 - 512";
                 }
            }
            description "Use this attribute to set system wide terminal length.";
        } // END of service-term-length definition.

        leaf system-enable-passwd  {
            type  cml-data-types:cml_line_t {
                length "1..1965";
            }
            description "Use this attribute to set enable password for the system.";
        } // END of system-enable-passwd definition.

        leaf passwd-encrypted  {
            // when " ../system-enable-passwd ";
            type  empty;
            description "Use this attribute to provide encrypted password.";
        } // END of passwd-encrypted definition.

        leaf disable-default-autoenable  {
            type  empty;
            description "Use this attribute to disable auto enable feature based on the user
                        role which is happening by default for remote authentication.";
        } // END of disable-default-autoenable definition.

        leaf disable-service-advanced-vty  {
            type  empty;
            description "Use this attribute to enable advanced mode vty interface.";
        } // END of disable-service-advanced-vty definition.

        leaf term-monitor-default-behavior-disable  {
            type  empty;
            description "Use this attribute to control terminal monitor initial behavior as
                        disable when user session starts.
                        The executive command terminal monitor has precedence over
                        configuration command.";
        } // END of term-monitor-default-behavior-disable definition.

        leaf term-timestamping  {
            type  empty;
            description "Use this attribute to enable CLI prompt timestamping during terminal
                        initialization.";
        } // END of term-timestamping definition.

    } // END of host-config definition.

    grouping  system-host-grouping {
    description
        "Top level container for system host related configuration common for
                all modules";
    container system-host {
        if-feature feature-list:HAVE_IMI;
        description
            "Top level container for system host related configuration common for
                    all modules";
        container config {
            description
                "This container defines host configuration.";
            uses host-config;
        } // END of config-container definition.
        container state {
            config false;
            description
                "This container defines host Operational states.";
            uses host-config;
        } // END of state-container definition.
    } // END of system-host-container definition.
    } // END of system-host-grouping definition.

    uses system-host-grouping;

}
