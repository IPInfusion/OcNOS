/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-snmp.yang
*
*/

module ipi-snmp {

    yang-version 1.1;

    namespace   "http://www.ipinfusion.com/yang/ocnos/ipi-snmp";

    prefix "ipi-snmp";

    import ipi-snmp-types {
        prefix ipi-snmp-types;
        revision-date 2025-08-08;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Top level SNMP configuration module";


    revision "2025-08-08" {
        description "Added SNMP Traps support for ALARMS";
        reference " 0.8.0.";
    }

    revision "2025-02-03" {
        description "Added SNMP Traps support for TWAMP";
        reference " 0.7.0.";
    }

    revision "2024-11-20" {
        description "Set the flag CML_FORCE_SET to enable-link-down-trap and enable-link-up-trap";
        reference " 0.6.2.";
    }

    revision "2024-09-07" {
        description "Changed maximum cached traps range";
        reference " 0.6.1.";
    }

    revision "2024-09-05" {
        description "Added support for SYSLOG over SNMP traps";
        reference " 0.6.0.";
    }

    revision "2024-08-26" {
        description "Added configuration for trap caching";
        reference " 0.5.0.";
    }

    revision "2022-10-07" {
        description "Added attributes to enable linktrap with ifname";
        reference " 0.4.6.";
    }

    revision "2022-09-29" {
        description "Updated the name of mrib module in smi-server-modules tag";
        reference " 0.4.5.";
    }

    revision "2022-09-07" {
        description "Added if-feature AGENTX for snmp-types datatype";
        reference " 0.4.4.";
    }

    revision "2022-08-23" {
        description "Added if-feature in datatype";
        reference " 0.4.3.";
    }

    revision "2022-08-10" {
        description "Updated smi-server-modules tag paramters";
        reference " 0.4.2.";
    }

    revision "2022-07-28" {
        description "Updated smi-server-modules with restructured RIPng module name";
        reference " 0.4.1.";
    }

    revision "2022-07-26" {
        description "Corrected RIP datamodel as per Open Config style";
        reference " 0.4.0.";
    }

    revision "2022-07-21" {
        description "Updated in its sub-module ipi-snmp-server-extended";
        reference " 0.3.2.";
    }

    revision "2022-06-28" {
        description "Enable SNMP trap for PIM and PIM-BSR";
        reference " 0.3.1.";
    }

    revision "2022-06-01" {
        description "Updated the yang file with feature";
        reference " 0.3.0.";
    }

    revision "2022-03-11" {
        description "Updated basetypes for datatype SNMP_TRAP_PROTOCOLS from enum to bits";
        reference " 0.2.0.";
    }

    revision "2021-07-28" {
        description "Initial Version";
        reference " 0.1.0.";
    }

    grouping snmp-server-trap-config {
        description
            "Grouping for snmp-server trap config objects.";
        leaf enable-traps  {
            type  ipi-snmp-types:snmp_trap_protocols;
            description "Use this attribute to enable or disable SNMP traps and inform
                        requests.";
        } // END of enable-traps definition.

        leaf enable-link-down-trap  {
            type  boolean;
            description "Use this attribute to enable or disable SNMP linkdown traps.";
        } // END of enable-link-down-trap definition.

        leaf enable-link-up-trap  {
            type  boolean;
            description "Use this attribute to enable or disable SNMP linkup traps.";
        } // END of enable-link-up-trap definition.

        leaf include-interface-name  {
            type  empty;
            description "Use this attribute to include ifname with SNMP linkdown traps.";
        } // END of include-interface-name definition.

    } // END of snmp-server-trap-config definition.
    grouping snmp-server-trap-cache-config {
        description
            "Group for SNMP trap caching configuration";
        leaf enable-trap-cache  {
            if-feature feature-list:HAVE_SNMP_AGENT;
            type  empty;
            mandatory true;
            description "Enables trap caching";
        } // END of enable-trap-cache definition.

        leaf timeout  {
            type  int8 {
                 range "1..20"  {
                    description "1..20: Supported range 1 - 20";
                 }
            }
            units "minutes";
            default "10";
            description "Sets timeout before sending traps";
        } // END of timeout definition.

        leaf disable-ping  {
            type  empty;
            description "Disables pings to check host reachability";
        } // END of disable-ping definition.

        leaf max-count  {
            type  int16 {
                 range "1..500"  {
                    description "1..500: Supported range 1 - 500";
                 }
            }
            default "200";
            description "Sets the maximum number of traps that can be cached";
        } // END of max-count definition.

    } // END of snmp-server-trap-cache-config definition.
    grouping snmp-server-trap-cache-top {
        description
            "SNMP server trap cache configuration";
        container trap-cache {
            description
                "SNMP server default container configuration";
            container config {
                presence "trap-cache";
                description
                    "Configuration data for SNMP server trap cache configuration";
                uses snmp-server-trap-cache-config;
            } // END of config-container definition.
            container state {
                config false;
                description
                    "Operational state data for SNMP server trap cache";
                uses snmp-server-trap-cache-config;
            } // END of state-container definition.
        } // END of trap-cache-container definition.
    } // END of snmp-server-trap-cache-top definition.

    grouping  snmp-grouping {
    description
        "Top level container for snmp configuration common for all modules";
    container snmp {
        if-feature feature-list:HAVE_SNMP_AGENT;
        description
            "Top level container for snmp configuration common for all modules";
        container server-traps {
            description
                "Top level container for snmp-server trap configuration common for all
                        modules";
            container config {
                description
                    "This container defines snmp-server traps configuration.";
                uses snmp-server-trap-config;
            } // END of config-container definition.
            container state {
                config false;
                description
                    "This container defines snmp-server traps Operational states.";
                uses snmp-server-trap-config;
            } // END of state-container definition.
            uses snmp-server-trap-cache-top;
        } // END of server-traps-container definition.
    } // END of snmp-container definition.
    } // END of snmp-grouping definition.

    uses snmp-grouping;

    rpc snmp-agentx-enable-terminal-debugging {
        if-feature feature-list:HAVE_AGENTX;
        description "Use this attribute to enable agentx debug options.";
        input  {
            leaf debug  {
                type ipi-snmp-types:snmp_agentx_debug_type_t;
                mandatory true;
                description "Use this attribute to enable agentx debug options.";
            }
        }
    }

    rpc snmp-agentx-disable-terminal-debugging {
        if-feature feature-list:HAVE_AGENTX;
        description "Use this attribute to disable agentx debug options.";
        input  {
            leaf debug  {
                type ipi-snmp-types:snmp_agentx_debug_type_t;
                mandatory true;
                description "Use this attribute to disable agentx debug options.";
            }
        }
    }

}
