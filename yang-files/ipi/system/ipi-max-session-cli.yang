/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-max-session-cli.yang
*
*/

submodule ipi-max-session-cli {

    yang-version 1.1;

    belongs-to  ipi-user-session-management { prefix ipi-user-session-management; }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "IMI max-sesiion limit configuration";


    revision "2025-07-28" {
        description " Added when tag for max-session-limit";
        reference " 0.2.0.";
    }

    revision "2025-02-11" {
        description "Initial Version of ipi-max-session-cli module";
        reference " 0.1.0.";
    }

    grouping max-session-limit-imi-config {
        description
            "Grouping for maximum session limit configuration";
        leaf max-session-limit  {
            type  uint8 {
                 range "1..40"  {
                    description "1..40: Supported range 1 - 40";
                 }
            }
            description "Use this attribute to set maximum session limit for vty.";
        } // END of max-session-limit definition.

    } // END of max-session-limit-imi-config definition.

    grouping  max-session-limit-grouping {
    description
        "This container defines max limit Configuration";
    container max-session-limit {
        if-feature feature-list:HAVE_IMI;
        description
            "This container defines max limit Configuration";
        container config {
            description
                "This container defines max limit Configuration";
            uses max-session-limit-imi-config;
        } // END of config-container definition.
        container state {
            config false;
            description
                "This container defines max limit state";
            uses max-session-limit-imi-config;
        } // END of state-container definition.
    } // END of max-session-limit-container definition.
    } // END of max-session-limit-grouping definition.


}
