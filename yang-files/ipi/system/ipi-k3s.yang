/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-k3s.yang
*
*/

module ipi-k3s {

    yang-version 1.1;

    namespace   "http://www.ipinfusion.com/yang/ocnos/ipi-k3s";

    prefix "ipi-k3s";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for K3s Module";


    revision "2025-10-31" {
        description "Initial Version";
        reference " 0.1.0.";
    }

    grouping k3s-config {
        description
            "K3s configurations";
        leaf enable  {
            type  empty;
            description "Use this attribute to enable the K3s feature.";
        } // END of enable definition.

    } // END of k3s-config definition.

    grouping  k3s-grouping {
    description
        "K3s configurations";
    container k3s {
        if-feature feature-list:HAVE_HOSTPD;
        description
            "K3s configurations";
        container config {
            description
                "Config container for k3s configurations";
            uses k3s-config;
        } // END of config-container definition.
        container state {
            config false;
            description
                "State container for k3s configurations";
            uses k3s-config;
        } // END of state-container definition.
    } // END of k3s-container definition.
    } // END of k3s-grouping definition.

    uses k3s-grouping;

}
