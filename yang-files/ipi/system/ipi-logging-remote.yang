/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-logging-remote.yang
*
*/

submodule ipi-logging-remote {

    yang-version 1.1;

    belongs-to  ipi-logging { prefix ipi-logging; }

    import feature-list {
        prefix feature-list;
        revision-date 2026-09-15;
    }

    import ipi-network-instance {
        prefix ipi-network-instance;
        revision-date 2026-08-12;
    }

    import cml-data-types {
        prefix cml-data-types;
        revision-date 2026-05-15;
    }

    import ipi-logging-types {
        prefix ipi-logging-types;
        revision-date 2025-09-23;
    }

    import ipi-vrf {
        prefix ipi-vrf;
        revision-date 2026-08-12;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for logging configurations";


    revision "2025-12-24" {
        description "Added dependentObject tag for remote-logging feature";
        reference " 0.9.7.";
    }

    revision "2025-05-06" {
        description "Updated when tag to update db when default instance is enabled";
        reference " 0.9.6.";
    }

    revision "2025-02-08" {
        description "Revert the range of logging remote server host udp-port number";
        reference " 0.9.5.";
    }

    revision "2024-11-08" {
        description "Updated the range of logging remote server host udp-port number";
        reference " 0.9.4.";
    }

    revision "2024-08-28" {
        description "Added simultaneous user defined VRF support for remote server";
        reference " 0.9.3.";
    }

    revision "2024-08-22" {
        description "Added flag in when tag to resolve the dependency failure";
        reference " 0.9.2.";
    }

    revision "2024-08-02" {
        description "Remove change lower to upper case validation from hostname. Since hostname are case sensitive";
        reference " 0.9.1.";
    }

    revision "2024-06-25" {
        description "Introduced disable-default attribute to resolve show running-config issue";
        reference " 0.9.0.";
    }

    revision "2023-12-20" {
        description "Added attr for remote server authpriv facility";
        reference " 0.8.0.";
    }

    revision "2023-08-08" {
        description "Added when tag to remove logging facility when syslog service is moved between VRF";
        reference " 0.7.3.";
    }

    revision "2023-06-05" {
        description "Added Custom syslog port feature";
        reference " 0.7.2.";
    }

    revision "2023-05-30" {
        description "Added changes to not allow deletion logging container";
        reference " 0.7.1.";
    }

    revision "2023-05-29" {
        description "Added When tag for no-debug-all command";
        reference " 0.7.0.";
    }

    revision "2022-11-21" {
        description "Added top level container for rsyslog module";
        reference " 0.6.2.";
    }

    revision "2022-11-16" {
        description "Updated missing cliprependstr tags";
        reference " 0.6.1.";
    }

    revision "2022-08-10" {
        description "Debug hierarchy change";
        reference " 0.6.0.";
    }

    revision "2022-07-13" {
        description "Making debug logging host CLI hidden";
        reference " 0.5.2.";
    }

    revision "2022-06-30" {
        description "Updated the ipi-logging-types with severity level description";
        reference " 0.5.1.";
    }

    revision "2022-06-01" {
        description "Updated the yang file with feature";
        reference " 0.5.0.";
    }

    revision "2021-09-03" {
        description "Update descriptions of attribute";
        reference " 0.4.0.";
    }

    revision "2021-01-05" {
        description "Adding this module as submodule of libsyslog after restructuring it";
        reference " 0.3.0.";
    }

    revision "2020-12-15" {
        description "Change to have data-types in lower case instead of camel case";
        reference " 0.2.0.";
    }

    revision "2020-09-03" {
        description "Initial Version: Restructuring according to OpenConfig style";
        reference " 0.1.0.";
    }

    grouping logging-debug-host-config {
        description
            "Grouping for logging debug configuration";
        leaf enable  {
            type  empty;
            description "This attribute enables/disables the logging host debug.";
        } // END of enable definition.

    } // END of logging-debug-host-config definition.
    grouping logging-server-config {
        description
            "Grouping for remote server configuration";
        leaf address  {
            type  cml-data-types:cml_hostname_t;
            description "Use this attribute to set a syslog server. Each syslog server can be
                        configured by address or hostname. You can configure the maximum 8
                        servers.";
        } // END of address definition.

        leaf severity  {
            type  ipi-logging-types:log_severity_t;
            mandatory true;
            description "This atribute is used to specify the kind of messages by severity
                        level. The default value is debug-detail. The possible values for
                        levels are as follows:
                        [Operator] 0-emerg; 1-alert; 2-critical; 3-error; 4-notify; 5-info
                        [Debug] 3-error; 4-warning; 5-notif; 6-debug-info; 7-debug-detail";
        } // END of severity definition.

        leaf port  {
            type  uint16 {
                 range "1024..65535"  {
                    description "1024..65535: Supported range 1024 - 65535";
                 }
            }
            description "Use this attribute to configure the syslog server UDP port. Default
                        value is 514";
        } // END of port definition.

    } // END of logging-server-config definition.
    grouping logging-server-top {
        description
            "Grouping for server configuration";
        container servers {
            description
                "Servers configuration";

            list server {
                key "address";
                max-elements 8;
                description
                    "list of servers";
                leaf address  {
                    type  leafref {
                        path  "../config/address";
                    }
                    description "Use this attribute to set a syslog server. Each sys log server can be
                                configured by address or hostname. You can configure the maximum 8
                                servers.";
                } // END of address definition.

                container config {
                    description
                        "Configuration data";
                    uses logging-server-config;
                } // END of config-container definition.
                container state {
                    config false;
                    description
                        "Operational state data";
                    uses logging-server-config;
                } // END of state-container definition.
            } // End of server-list
        } // END of servers-container definition.
    } // END of logging-server-top definition.
    grouping logging-remote-server-config {
        description
            "Grouping for remote server configuration";
        leaf vrf  {
            if-feature feature-list:HAVE_VRF;
            type  leafref {
                path  "/ipi-network-instance:network-instances/ipi-network-instance:network-instance/ipi-vrf:vrf/ipi-vrf:config/ipi-vrf:vrf-name";
            }
            description "VRF name that is connected to remote server";
        } // END of vrf definition.

    } // END of logging-remote-server-config definition.
    grouping logging-remote-server-top {
        description
            "Grouping for remote server configuration";
        container remote-servers {
            if-feature feature-list:HAVE_VRF;
            description
                "Remote servers configuration";

            list remote-server {
            // when " ipi-logging-remote:remote-logging/remote-servers/remote-server/config + ipi-logging-remote:remote-logging/remote-servers/remote-server/servers/server ";
                key "vrf";
                description
                    "list of servers";
                leaf vrf  {
                    type  leafref {
                        path  "../config/vrf";
                    }
                    description "VRF name for which the feature is being enabled";
                } // END of vrf definition.

                container config {
                    description
                        "Configuration data";
                    uses logging-remote-server-config;
                } // END of config-container definition.
                container state {
                    config false;
                    description
                        "Operational state data";
                    uses logging-remote-server-config;
                } // END of state-container definition.
                uses logging-server-top;
            } // End of remote-server-list
        } // END of remote-servers-container definition.
    } // END of logging-remote-server-top definition.
    grouping logging-rsyslog-default-config {
        description
            "logging disable default configuration";
        leaf disable-default-instance  {
            type  empty;
            description "Use this attribute to prevent default rsyslog config from being
                        enabled at start up";
        } // END of disable-default-instance definition.

    } // END of logging-rsyslog-default-config definition.
    grouping logging-rsyslog-default-top {
        description
            "logging disable default configuration";
        container default-instance {
            description
                "logging default container configuration";
            container config {
                description
                    "Configuration data for logging global configuration";
                uses logging-rsyslog-default-config;
            } // END of config-container definition.
            container state {
                config false;
                description
                    "Operational state data for logging global configuration";
                uses logging-rsyslog-default-config;
            } // END of state-container definition.
        } // END of default-instance-container definition.
    } // END of logging-rsyslog-default-top definition.
    grouping logging-feature-rsyslog-config {
        description
            "Grouping for feature rsyslog configuration";
        leaf enable-rsyslog  {
            type  empty;
            description "Enable/disable the rsyslog feature";
        } // END of enable-rsyslog definition.

    } // END of logging-feature-rsyslog-config definition.
    grouping logging-global-rsyslog-config {
        description
            "Grouping for global rsyslog configuration";
        leaf remote-server-facility  {
            type  ipi-logging-types:log_facility_t;
            default "local7";
            description "This attribute is used to specify the facility level used by syslog
                        messages. The default value is local7. The possible values are local0,
                        local1, local2, local3, local4, local5, local6, local7 and user.";
        } // END of remote-server-facility definition.

        leaf remote-authpriv-facility  {
            type  empty;
            description "Enable/disable logging authpriv facility for remote syslog server.";
        } // END of remote-authpriv-facility definition.

    } // END of logging-global-rsyslog-config definition.

    grouping  remote-logging-grouping {
    description
        "Top level container for remote logging feature";
    container remote-logging {
        if-feature feature-list:HAVE_HOSTPD;
        if-feature feature-list:HAVE_SYSLOG;
        description
            "Top level container for remote logging feature";
        container config {
            description
                "Configuration data";
            uses logging-feature-rsyslog-config;
        } // END of config-container definition.
        container state {
            config false;
            description
                "Operational state data";
            uses logging-feature-rsyslog-config;
        } // END of state-container definition.
        uses logging-remote-server-top;
        uses logging-rsyslog-default-top;
    } // END of remote-logging-container definition.
    } // END of remote-logging-grouping definition.

    grouping  global-grouping {
    description
        "Global rsyslog configuration";
    container global {
        if-feature feature-list:HAVE_HOSTPD;
        if-feature feature-list:HAVE_SYSLOG;
        description
            "Global rsyslog configuration";
        container config {
            description
                "Configuration data";
            uses logging-global-rsyslog-config;
        } // END of config-container definition.
        container state {
            config false;
            description
                "Operational state data";
            uses logging-global-rsyslog-config;
        } // END of state-container definition.
    } // END of global-container definition.
    } // END of global-grouping definition.


}
