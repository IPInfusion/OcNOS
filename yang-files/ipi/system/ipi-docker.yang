/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-docker.yang
*
*/

module ipi-docker {

    yang-version 1.1;

    namespace   "http://www.ipinfusion.com/yang/ocnos/ipi-docker";

    prefix "ipi-docker";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for Docker Module";


    revision "2025-10-31" {
        description "Initial Version";
        reference " 0.1.0.";
    }

    grouping docker-config {
        description
            "Docker configurations";
        leaf enable  {
            type  empty;
            description "Use this attribute to enable the Docker feature.";
        } // END of enable definition.

    } // END of docker-config definition.

    grouping  docker-grouping {
    description
        "docker configurations";
    container docker {
        if-feature feature-list:HAVE_HOSTPD;
        description
            "docker configurations";
        container config {
            description
                "Config container for docker configurations";
            uses docker-config;
        } // END of config-container definition.
        container state {
            config false;
            description
                "State container for docker configurations";
            uses docker-config;
        } // END of state-container definition.
    } // END of docker-container definition.
    } // END of docker-grouping definition.

    uses docker-grouping;

}
