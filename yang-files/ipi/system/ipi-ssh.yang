/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ssh.yang
*
*/

module ipi-ssh {

    yang-version 1.1;

    namespace   "http://www.ipinfusion.com/yang/ocnos/ipi-ssh";

    prefix "ipi-ssh";

    import cml-data-types {
        prefix cml-data-types;
        revision-date 2026-05-15;
    }

    import ipi-ssh-types {
        prefix ipi-ssh-types;
        revision-date 2022-06-01;
    }

    import ipi-network-instance {
        prefix ipi-network-instance;
        revision-date 2026-08-12;
    }

    import ipi-vrf {
        prefix ipi-vrf;
        revision-date 2026-08-12;
    }

    import ipi-user-management {
        prefix ipi-user-management;
        revision-date 2026-01-08;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for SSH Module";


    revision "2026-08-14" {
        description "added the autopopulate tag to populate vrf";
        reference " 0.12.0.";
    }

    revision "2025-10-29" {
        description "Added sntrup761x25519-sha512 to the SSH server KEX list";
        reference " 0.11.0.";
    }

    revision "2025-08-04" {
        description "Added HostKey related algorithms";
        reference " 0.10.2.";
    }

    revision "2025-07-30" {
        description "Added when tag to remove vrfs when none of its child exist";
        reference " 0.10.1.";
    }

    revision "2025-07-04" {
        description "Added disable-default attribute to resolve show running-config issue";
        reference " 0.10.";
    }

    revision "2024-11-07" {
        description "Updated the algorithm list as per debian 12";
        reference " 0.9.";
    }

    revision "2024-10-11" {
        description "Removed custom-algorithm related configs";
        reference " 0.8.2.";
    }

    revision "2024-09-04" {
        description "Added Cipher ,Kex and Macs related algorithms";
        reference " 0.8.1.";
    }

    revision "2024-06-18" {
        description "Enable SSH service on user defined VRFs also instead of only management VRF";
        reference " 0.8.0.";
    }

    revision "2023-05-29" {
        description "Added When tag for no-debug-all command";
        reference " 0.7.0.";
    }

    revision "2022-11-16" {
        description "Updated missing cliprependstr tags";
        reference " 0.6.0.";
    }

    revision "2022-08-10" {
        description "Debug hierarchy change";
        reference " 0.5.0.";
    }

    revision "2022-06-01" {
        description "Updated the yang file with feature";
        reference " 0.4.0.";
    }

    revision "2021-09-03" {
        description "Update descriptions of attribute";
        reference " 0.3.0.";
    }

    revision "2021-08-02" {
        description "Updated default values for SSH key generation RPCs";
        reference " 0.2.0.";
    }

    revision "2021-07-14" {
        description "Initial Version";
        reference " 0.1.0.";
    }

    grouping ssh-server-config {
        description
            "SSH Server Configurations";
        leaf vrf-name  {
            type  leafref {
                path  "/ipi-network-instance:network-instances/ipi-network-instance:network-instance/ipi-vrf:vrf/ipi-vrf:config/ipi-vrf:vrf-name";
            }
            description "VRF Name associated with this instance";
        } // END of vrf-name definition.

        leaf enable  {
            if-feature feature-list:HAVE_SSH_SERVER;
            type  empty;
            description "Use this attribute to enable the SSH server.";
        } // END of enable definition.

        leaf port  {
            if-feature feature-list:HAVE_SSH_SERVER;
            type  uint32 {
                 range "1024..65535"  {
                    description "1024..65535: Supported range 1024 - 65535";
                 }
            }
            description "Use this attribute to set the port number on which the SSH server
                        listens for connections. The default port on which the SSH server
                        listens is 22.";
        } // END of port definition.

        leaf session-limit  {
            if-feature feature-list:HAVE_SSH_SERVER;
            type  uint8 {
                 range "1..40"  {
                    description "1..40: Supported range 1 - 40";
                 }
            }
            description "Use this attribute to set the maximum number of simultaneous sessions
                        allowed. By default, 40 ssh-telnet sessions are allowed";
        } // END of session-limit definition.

        leaf max-login-attempts  {
            if-feature feature-list:HAVE_SSH_SERVER;
            type  uint8 {
                 range "1..3"  {
                    description "1..3: Supported range 1 - 3";
                 }
            }
            default "3";
            description "Use this attribute to set the number of times that a user can try to
                        log in to a SSH session.";
        } // END of max-login-attempts definition.

    } // END of ssh-server-config definition.
    grouping ssh-server-encryption-algorithms-config {
        description
            "SSH Server Enryption Algorithm Configurations";
        leaf aes128-ctr  {
            type  empty;
            description "Use this attribute to set the AES128-CTR Cipher";
        } // END of aes128-ctr definition.

        leaf aes192-ctr  {
            type  empty;
            description "Use this attribute to set the AES192-CTR Cipher";
        } // END of aes192-ctr definition.

        leaf aes256-ctr  {
            type  empty;
            description "Use this attribute to set the AES256-CTR Cipher";
        } // END of aes256-ctr definition.

        leaf aes128-cbc  {
            type  empty;
            description "Use this attribute to set the AES128-CBC Cipher";
        } // END of aes128-cbc definition.

        leaf aes192-cbc  {
            type  empty;
            description "Use this attribute to set the AES192-CBC Cipher";
        } // END of aes192-cbc definition.

        leaf aes256-cbc  {
            type  empty;
            description "Use this attribute to set the AES256-CBC Cipher";
        } // END of aes256-cbc definition.

        leaf triple-des-cbc  {
            type  empty;
            description "Use this attribute to set the 3DES-CBC Cipher";
        } // END of triple-des-cbc definition.

        leaf aes128-gcm  {
            type  empty;
            description "Use this attribute to set the AES128-GCM Cipher";
        } // END of aes128-gcm definition.

        leaf aes256-gcm  {
            type  empty;
            description "Use this attribute to set the AES256-GCM Cipher";
        } // END of aes256-gcm definition.

        leaf chacha20-poly1305  {
            type  empty;
            description "Use this attribute to set the ChaCha20-Poly1305 Cipher";
        } // END of chacha20-poly1305 definition.

    } // END of ssh-server-encryption-algorithms-config definition.
    grouping ssh-server-kex-algorithms-config {
        description
            "SSH Server Kex Algorithm Configurations";
        leaf diffie-hellman-group1-sha1  {
            type  empty;
            description "Use this attribute to set the Diffie-Hellman Group1 SHA1 algorithm";
        } // END of diffie-hellman-group1-sha1 definition.

        leaf diffie-hellman-group14-sha1  {
            type  empty;
            description "Use this attribute to set the Diffie-Hellman Group14 SHA1 algorithm";
        } // END of diffie-hellman-group14-sha1 definition.

        leaf diffie-hellman-group14-sha256  {
            type  empty;
            description "Use this attribute to set the Diffie-Hellman Group14 SHA256 algorithm";
        } // END of diffie-hellman-group14-sha256 definition.

        leaf diffie-hellman-group16-sha512  {
            type  empty;
            description "Use this attribute to set the Diffie-Hellman Group16 SHA512 algorithm";
        } // END of diffie-hellman-group16-sha512 definition.

        leaf diffie-hellman-group18-sha512  {
            type  empty;
            description "Use this attribute to set the Diffie-Hellman Group18 SHA512 algorithm";
        } // END of diffie-hellman-group18-sha512 definition.

        leaf diffie-hellman-group-exchange-sha1  {
            type  empty;
            description "Use this attribute to set the Diffie-Hellman Group Exchange SHA1
                        algorithm";
        } // END of diffie-hellman-group-exchange-sha1 definition.

        leaf diffie-hellman-group-exchange-sha256  {
            type  empty;
            description "Use this attribute to set the Diffie-Hellman Group Exchange SHA256
                        algorithm";
        } // END of diffie-hellman-group-exchange-sha256 definition.

        leaf ecdh-sha2-nistp256  {
            type  empty;
            description "Use this attribute to set the ECDH SHA2 NIST P-256 algorithm";
        } // END of ecdh-sha2-nistp256 definition.

        leaf ecdh-sha2-nistp384  {
            type  empty;
            description "Use this attribute to set the ECDH SHA2 NIST P-384 algorithm";
        } // END of ecdh-sha2-nistp384 definition.

        leaf ecdh-sha2-nistp521  {
            type  empty;
            description "Use this attribute to set the ECDH SHA2 NIST P-521 algorithm";
        } // END of ecdh-sha2-nistp521 definition.

        leaf curve25519-sha256  {
            type  empty;
            description "Use this attribute to set the Curve25519 SHA256 algorithm";
        } // END of curve25519-sha256 definition.

        leaf curve25519-sha256-libssh-org  {
            type  empty;
            description "Use this attribute to set the Curve25519 SHA256 @libssh.org algorithm";
        } // END of curve25519-sha256-libssh-org definition.

        leaf sntrup761x25519-sha512  {
            type  empty;
            description "Use this attribute to set the sntrup761x25519 SHA512 algorithm";
        } // END of sntrup761x25519-sha512 definition.

        leaf sntrup761x25519-sha512-openssh  {
            type  empty;
            description "Use this attribute to set the sntrup761x25519 SHA512 @openssh
                        algorithm";
        } // END of sntrup761x25519-sha512-openssh definition.

    } // END of ssh-server-kex-algorithms-config definition.
    grouping ssh-server-mac-algorithms-config {
        description
            "SSH Server Mac Algorithm Configurations";
        leaf hmac-sha1  {
            type  empty;
            description "Use this attribute to set the HMAC-SHA1 MAC";
        } // END of hmac-sha1 definition.

        leaf hmac-sha1-96  {
            type  empty;
            description "Use this attribute to set the HMAC-SHA1-96 MAC";
        } // END of hmac-sha1-96 definition.

        leaf hmac-sha2-256  {
            type  empty;
            description "Use this attribute to set the HMAC-SHA2-256 MAC";
        } // END of hmac-sha2-256 definition.

        leaf hmac-sha2-512  {
            type  empty;
            description "Use this attribute to set the HMAC-SHA2-512 MAC";
        } // END of hmac-sha2-512 definition.

        leaf hmac-md5  {
            type  empty;
            description "Use this attribute to set the HMAC-MD5 MAC";
        } // END of hmac-md5 definition.

        leaf hmac-md5-96  {
            type  empty;
            description "Use this attribute to set the HMAC-MD5-96 MAC";
        } // END of hmac-md5-96 definition.

        leaf umac-64  {
            type  empty;
            description "Use this attribute to set the UMAC-64 @openssh.com MAC";
        } // END of umac-64 definition.

        leaf umac-128  {
            type  empty;
            description "Use this attribute to set the UMAC-128 @openssh.com MAC";
        } // END of umac-128 definition.

        leaf hmac-sha1-etm  {
            type  empty;
            description "Use this attribute to set the HMAC-SHA1-ETM @openssh.com MAC";
        } // END of hmac-sha1-etm definition.

        leaf hmac-sha1-96-etm  {
            type  empty;
            description "Use this attribute to set the HMAC-SHA1-96-ETM @openssh.com MAC";
        } // END of hmac-sha1-96-etm definition.

        leaf hmac-sha2-256-etm  {
            type  empty;
            description "Use this attribute to set the HMAC-SHA2-256-ETM @openssh.com MAC";
        } // END of hmac-sha2-256-etm definition.

        leaf hmac-sha2-512-etm  {
            type  empty;
            description "Use this attribute to set the HMAC-SHA2-512-ETM @openssh.com MAC";
        } // END of hmac-sha2-512-etm definition.

        leaf hmac-md5-etm  {
            type  empty;
            description "Use this attribute to set the HMAC-MD5-ETM @openssh.com MAC";
        } // END of hmac-md5-etm definition.

        leaf hmac-md5-96-etm  {
            type  empty;
            description "Use this attribute to set the HMAC-MD5-96-ETM @openssh.com MAC";
        } // END of hmac-md5-96-etm definition.

        leaf umac-64-etm  {
            type  empty;
            description "Use this attribute to set the UMAC-64-ETM @openssh.com MAC";
        } // END of umac-64-etm definition.

        leaf umac-128-etm  {
            type  empty;
            description "Use this attribute to set the UMAC-128-ETM @openssh.com MAC";
        } // END of umac-128-etm definition.

    } // END of ssh-server-mac-algorithms-config definition.
    grouping ssh-server-default-algorithms-config {
        description
            "SSH Server default Algorithm Configurations";
        leaf default-algorithm  {
            type  empty;
            description "Use this attribute to set the default algorithms";
        } // END of default-algorithm definition.

    } // END of ssh-server-default-algorithms-config definition.
    grouping ssh-server-hostkey-algorithms-config {
        description
            "SSH Server HostKey Algorithm Configurations";
        leaf ssh-ed25519  {
            type  empty;
            description "Use this attribute to set the ssh-ed25519 host key algorithm";
        } // END of ssh-ed25519 definition.

        leaf ssh-rsa  {
            type  empty;
            description "Use this attribute to set the ssh-rsa host key algorithm";
        } // END of ssh-rsa definition.

    } // END of ssh-server-hostkey-algorithms-config definition.
    grouping ssh-server-debug-config {
        description
            "SSH Server debug configurations";
        leaf enable  {
            type  empty;
            description "Use this attribute to enable ssh debugging configurations";
        } // END of enable definition.

    } // END of ssh-server-debug-config definition.
    grouping ssh-server-debug-state {
        description
            "SSH Server terminal debug state information";
        leaf terminal-debug-status  {
            type  cml-data-types:cml_on_off_t;
            description "Use this attribute to display ssh terminal debugging information.";
        } // END of terminal-debug-status definition.

    } // END of ssh-server-debug-state definition.
    grouping ssh-user-keys-config {
        description
            "SSH User Keys configurations";
        leaf-list public-key  {
            type  ipi-ssh-types:ssh_public_key_t {
                length "1..1965";
            }
            description "Use this attribute to set the ssh public-key";
        } // END of public-key definition.

    } // END of ssh-user-keys-config definition.
    grouping ssh-server-top {
        description
            "SSH Server top configurations";
        container vrfs {
            description
                "ssh vrf configurations";

            list vrf {
                key "vrf-name";
                description
                    "ssh vrf instance configurations";
                leaf vrf-name  {
                    type  leafref {
                        path  "../config/vrf-name";
                    }
                    description "VPN routing/forwarding Instance name";
                } // END of vrf-name definition.

                container config {
                    description
                        "config container for ssh vrf instance configurations";
                    uses ssh-server-config;
                    uses ssh-server-default-algorithms-config;
                } // END of config-container definition.
                container state {
                    config false;
                    description
                        "state container for ssh vrf instance configurations";
                    uses ssh-server-config;
                    uses ssh-server-default-algorithms-config;
                } // END of state-container definition.
                container encryption-algorithms {
                    if-feature feature-list:HAVE_SSH_SERVER;
                    description
                        "SSH Server Encryption Algorithm Configurations";
                    container config {
                        description
                            "config container for ssh server encryption algorithm configurations";
                        uses ssh-server-encryption-algorithms-config;
                    } // END of config-container definition.
                    container state {
                        config false;
                        description
                            "state container for ssh server encryption algorithm configurations";
                        uses ssh-server-encryption-algorithms-config;
                    } // END of state-container definition.
                } // END of encryption-algorithms-container definition.
                container kex-algorithms {
                    if-feature feature-list:HAVE_SSH_SERVER;
                    description
                        "SSH Server Key Exchange Algorithm Configurations";
                    container config {
                        description
                            "config container for SSH server key exchange algorithm configurations";
                        uses ssh-server-kex-algorithms-config;
                    } // END of config-container definition.
                    container state {
                        config false;
                        description
                            "state container for SSH server key exchange algorithm configurations";
                        uses ssh-server-kex-algorithms-config;
                    } // END of state-container definition.
                } // END of kex-algorithms-container definition.
                container mac-algorithms {
                    if-feature feature-list:HAVE_SSH_SERVER;
                    description
                        "SSH Server MAC Algorithm Configurations";
                    container config {
                        description
                            "config container for SSH server MAC algorithm configurations";
                        uses ssh-server-mac-algorithms-config;
                    } // END of config-container definition.
                    container state {
                        config false;
                        description
                            "state container for SSH server MAC algorithm configurations";
                        uses ssh-server-mac-algorithms-config;
                    } // END of state-container definition.
                } // END of mac-algorithms-container definition.
                container host-key-algorithms {
                    if-feature feature-list:HAVE_SSH_SERVER;
                    description
                        "SSH Server Host Key Algorithms Configurations";
                    container config {
                        description
                            "config container for SSH server Host Key  algorithms configurations";
                        uses ssh-server-hostkey-algorithms-config;
                    } // END of config-container definition.
                    container state {
                        config false;
                        description
                            "state container for SSH server Host Key algorithm configurations";
                        uses ssh-server-hostkey-algorithms-config;
                    } // END of state-container definition.
                } // END of host-key-algorithms-container definition.
            } // End of vrf-list
        } // END of vrfs-container definition.
    } // END of ssh-server-top definition.
    grouping ssh-disable-default-config {
        description
            "ssh disable default configuration";
        leaf disable-default-instance  {
            if-feature feature-list:HAVE_SSH_SERVER;
            type  empty;
            description "Use this attribute to prevent default ssh config from being enabled at
                        start up";
        } // END of disable-default-instance definition.

    } // END of ssh-disable-default-config definition.
    grouping ssh-disable-default-top {
        description
            "ssh disable default configuration";
        container default-instance {
            if-feature feature-list:HAVE_SSH_SERVER;
            description
                "ssh disable default container configuration";
            container config {
                description
                    "Configuration data for ssh disable global configuration";
                uses ssh-disable-default-config;
            } // END of config-container definition.
            container state {
                config false;
                description
                    "Operational state data for ssh disable global configuration";
                uses ssh-disable-default-config;
            } // END of state-container definition.
        } // END of default-instance-container definition.
    } // END of ssh-disable-default-top definition.
    grouping user-ssh-keypair-attributes {
        description
            "user ssh keypair attributes";
        leaf rsa-key  {
            type  ipi-ssh-types:ssh_public_key_t {
                length "1..1965";
            }
            description "User specific Rivest, Shamir, and Adelman (RSA) public-key
                        cryptography SSH server key";
        } // END of rsa-key definition.

        leaf dsa-key  {
            type  ipi-ssh-types:ssh_public_key_t {
                length "1..1965";
            }
            description "User specific Digital System Algorithm (DSA) SSH key";
        } // END of dsa-key definition.

        leaf fingerprint-rsa  {
            type  ipi-ssh-types:ssh_public_key_t {
                length "1..1965";
            }
            description "MD5 over the binary data within the Base64-encoded RSA public key";
        } // END of fingerprint-rsa definition.

        leaf fingerprint-dsa  {
            type  ipi-ssh-types:ssh_public_key_t {
                length "1..1965";
            }
            description "MD5 over the binary data within the Base64-encoded DSA public key";
        } // END of fingerprint-dsa definition.

    } // END of user-ssh-keypair-attributes definition.

    grouping  ssh-server-grouping {
    description
        "ssh-server configurations";
    container ssh-server {
        if-feature feature-list:HAVE_HOSTPD;
        description
            "ssh-server configurations";
        container debug {
            description
                "SSH debug configurations";
            container config {
                description
                    "Config container for SSH debug configurations";
                uses ssh-server-debug-config;
            } // END of config-container definition.
            container state {
                config false;
                description
                    "State container for SSH debug configurations";
                uses ssh-server-debug-config;
                uses ssh-server-debug-state;
            } // END of state-container definition.
        } // END of debug-container definition.
        uses ssh-server-top;
        uses ssh-disable-default-top;
    } // END of ssh-server-container definition.
    } // END of ssh-server-grouping definition.

    grouping  ssh-keys-grouping {
    description
        "ssh-keys configurations";
    container ssh-keys {
        if-feature feature-list:HAVE_HOSTPD;
        description
            "ssh-keys configurations";
        container config {
            description
                "config container for ssh keys configurations";
            uses ssh-user-keys-config;
        } // END of config-container definition.
        container state {
            config false;
            description
                "state container for ssh keys configurations";
            uses ssh-user-keys-config;
            uses user-ssh-keypair-attributes;
        } // END of state-container definition.
    } // END of ssh-keys-container definition.
    } // END of ssh-keys-grouping definition.

    uses ssh-server-grouping;
    augment /ipi-user-management:user-management/ipi-user-management:users/ipi-user-management:user {
        if-feature feature-list:HAVE_HOSTPD;
        if-feature feature-list:HAVE_USER_MGMT;
        description
            "ssh-keys configurations";
        uses ssh-keys-grouping;
    }


    rpc ssh-terminal-debug-on {
        if-feature feature-list:HAVE_HOSTPD;
        description "Use this RPC to enable debugging for ssh server";
    }

    rpc ssh-terminal-debug-off {
        if-feature feature-list:HAVE_HOSTPD;
        description "Use this RPC to disable debugging for ssh server";
    }

    rpc ssh-clear-hosts {
        if-feature feature-list:HAVE_HOSTPD;
        description "Use this RPC to clear all ssh hosts";
    }

    rpc ssh-generate-server-dsa-key {
        if-feature feature-list:HAVE_SSH_SERVER;
        if-feature feature-list:HAVE_HOSTPD;
        description "Use this attribute to generate ssh host key using DSA Algorithm";
        input  {
            leaf vrf-name  {
                type string;
                default "default";
                description "VPN routing/forwarding Instance name";
            }
            leaf force  {
                type boolean;
                default false;
                description "Use this attribute to overwrite the existing dsa host key";
            }
        }
    }

    rpc ssh-generate-server-rsa-key {
        if-feature feature-list:HAVE_SSH_SERVER;
        if-feature feature-list:HAVE_HOSTPD;
        description "Use this attribute to generate ssh host key using RSA Algorithm";
        input  {
            leaf length  {
                type uint32 {
                    range "1024..4096";
                }
                default "2048";
                description "Use this attribute to set the key-length";
            }
            leaf vrf-name  {
                type string;
                default "default";
                description "VPN routing/forwarding Instance name";
            }
            leaf force  {
                type boolean;
                default false;
                description "Use this attribute to overwrite the existing rsa host key";
            }
        }
    }

    rpc ssh-generate-server-ecdsa-key {
        if-feature feature-list:HAVE_SSH_SERVER;
        if-feature feature-list:HAVE_HOSTPD;
        description "Use this attribute to generate ssh host key using ECDSA Algorithm";
        input  {
            leaf length  {
                type ipi-ssh-types:ssh_ecdsa_key_len_t;
                default "521";
                description "Use this attribute to set the key length";
            }
            leaf vrf-name  {
                type string;
                default "default";
                description "VPN routing/forwarding Instance name";
            }
            leaf force  {
                type boolean;
                default false;
                description "Use this attribute to overwrite the existing ecdsa key";
            }
        }
    }

    rpc ssh-generate-server-ed25519-key {
        if-feature feature-list:HAVE_SSH_SERVER;
        if-feature feature-list:HAVE_HOSTPD;
        description "Use this attribute to generate ssh host key using ED25519 Algorithm";
        input  {
            leaf vrf-name  {
                type string;
                default "default";
                description "VPN routing/forwarding Instance name";
            }
            leaf force  {
                type boolean;
                default false;
                description "Use this attribute to overwrite the existing ed25519 key";
            }
        }
    }

    rpc ssh-clear-server-keys {
        if-feature feature-list:HAVE_SSH_SERVER;
        if-feature feature-list:HAVE_HOSTPD;
        description "Use this attribute to delete ssh host keys";
        input  {
            leaf type  {
                type ipi-ssh-types:ssh_host_key_type_t;
                default "all-keys";
                description "Use this attribute to specify the host-key type";
            }
            leaf vrf-name  {
                type string;
                default "default";
                description "VPN routing/forwarding Instance name";
            }
        }
    }

    rpc ssh-generate-user-rsa-key {
        if-feature feature-list:HAVE_SSH_SERVER;
        if-feature feature-list:HAVE_HOSTPD;
        description "Use this attribute to generate RSA key for a user account";
        input  {
            leaf user-name  {
                type string;
                mandatory true;
                description "Use this attribute to set the username";
            }
            leaf length  {
                type uint32 {
                    range "1024..4096";
                }
                default "4096";
                description "Use this attribute to set the key length";
            }
            leaf force  {
                type boolean;
                default false;
                description "Use this attribute to overwrite the rsa key";
            }
        }
    }

    rpc ssh-generate-user-dsa-key {
        if-feature feature-list:HAVE_SSH_SERVER;
        if-feature feature-list:HAVE_HOSTPD;
        description "Use this attribute to generate DSA key for a user account";
        input  {
            leaf user-name  {
                type string;
                mandatory true;
                description "Use this attribute to set the username";
            }
            leaf force  {
                type boolean;
                default false;
                description "Use this attribute to overwrite the dsa key";
            }
        }
    }

    rpc ssh-clear-user-keys {
        if-feature feature-list:HAVE_SSH_SERVER;
        if-feature feature-list:HAVE_HOSTPD;
        description "Use this attribute to clear a user account's keys";
        input  {
            leaf user-name  {
                type string;
                mandatory true;
                description "Use this attribute to set the username";
            }
        }
    }

}
