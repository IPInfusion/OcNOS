/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-logging-fault-management.yang
*
*/

submodule ipi-logging-fault-management {

    yang-version 1.1;

    belongs-to  ipi-logging { prefix ipi-logging; }

    import feature-list {
        prefix feature-list;
        revision-date 2026-09-15;
    }

    import ipi-logging-types {
        prefix ipi-logging-types;
        revision-date 2025-09-23;
    }

    organization
        "IP Infusion Inc.";

    contact
        "Address: 3965 Freedom Circle, Suite 200, Santa Clara, CA 95054
         Phone: +1 408-400-1900
         E-mail: support@ipinfusion.com
         Web: http://www.ipinfusion.com/";

    description
        "Logging control for fault-management";


    revision "2024-09-23" {
        description "Fixed DB-sync error when deleting severity config at the snmp-syslog container";
        reference " 0.5.1.";
    }

    revision "2024-09-05" {
        description "Added severity attribute to configure SYSLOG over SNMP traps";
        reference " 0.5.0.";
    }

    revision "2022-03-29" {
        description "Added support for shelve and close alarm RPCs";
        reference " 0.4.0.";
    }

    revision "2021-09-03" {
        description "Update descriptions of attribute";
        reference " 0.3.0.";
    }

    revision "2021-03-30" {
        description "Restructured module as per open-config style";
        reference " 0.2.0.";
    }

    revision "2018-06-21" {
        description "Initial Version";
        reference " 0.1.0.";
    }

    grouping logging-fault-management-config {
        description
            "Grouping for fault-management configuration";
        leaf enable-fault-management  {
            type  empty;
            description "Enable Fault Management System";
        } // END of enable-fault-management definition.

    } // END of logging-fault-management-config definition.
    grouping logging-snmp-syslog-config {
        description
            "Grouping for snmp-syslog configuration";
        leaf severity  {
            type  ipi-logging-types:log_severity_t;
            default "3";
            description "Use this attribute to set the severity level for the SYSLOG messages
                        that will be sent over SNMP traps. The Default value to this attribute
                        is 3(error).";
        } // END of severity definition.

    } // END of logging-snmp-syslog-config definition.

    grouping  snmp-syslog-grouping {
    description
        "SYSLOG over SNMP traps configuration";
    container snmp-syslog {
        if-feature feature-list:HAVE_VLOGD;
        description
            "SYSLOG over SNMP traps configuration";
        container config {
            description
                "Configuration data";
            uses logging-snmp-syslog-config;
        } // END of config-container definition.
        container state {
            config false;
            description
                "Operational state data";
            uses logging-snmp-syslog-config;
        } // END of state-container definition.
    } // END of snmp-syslog-container definition.
    } // END of snmp-syslog-grouping definition.

    grouping  fault-management-grouping {
    description
        "Fault management configuration";
    container fault-management {
        if-feature feature-list:HAVE_FMS;
        description
            "Fault management configuration";
        container config {
            description
                "Configuration data";
            uses logging-fault-management-config;
        } // END of config-container definition.
        container state {
            config false;
            description
                "Operational state data";
            uses logging-fault-management-config;
        } // END of state-container definition.
    } // END of fault-management-container definition.
    } // END of fault-management-grouping definition.


}
