/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-user-session.yang
*
*/

submodule ipi-user-session {

    yang-version 1.1;

    belongs-to  ipi-user-session-management { prefix ipi-user-session-management; }

    import feature-list {
        prefix feature-list;
        revision-date 2026-09-15;
    }

    import ipi-user-session-types {
        prefix ipi-user-session-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for operational state data related to
                user-session-management";


    revision "2022-08-09" {
        description "Added skip SMI generation";
        reference " 0.2.2.";
    }

    revision "2022-06-18" {
        description "Added Remote-IP leaf for Netconf clients";
        reference " 0.2.1.";
    }

    revision "2022-06-01" {
        description "Updated the yang file with feature";
        reference " 0.2.0.";
    }

    revision "2022-01-11" {
        description "Initial Version";
        reference " 0.1.0.";
    }

    grouping user-sessions-state {
        description
            "All the runtime attributes for a user session";
        leaf id  {
            type  string {
                length "1..1965";
            }
            description "The user session id.";
        } // END of id definition.

        leaf line  {
            type  string {
                length "1..1965";
            }
            description "The line information which user is logged. For users connected via
                        console, it holds the line console identifier.
                        For users connected via vty, it holds the line vty identifier. For
                        users connected via Netconf, there is no line,
                        it holds NA value.";
        } // END of line definition.

        leaf user-name  {
            type  string {
                length "1..1965";
            }
            description "The user name that is logged in the specific session.";
        } // END of user-name definition.

        leaf client-type  {
            type  ipi-user-session-types:user_session_user_type_t;
            description "The user type, Netconf or CLI.";
        } // END of client-type definition.

        leaf idle-time  {
            type  string {
                length "1..1965";
            }
            description "The user session idle time.";
        } // END of idle-time definition.

        leaf process-identifier  {
            type  uint32;
            description "The user session process id.";
        } // END of process-identifier definition.

        leaf type  {
            type  ipi-user-session-types:user_session_type_t;
            description "The user session type: Local or remote.";
        } // END of type definition.

        leaf user-role  {
            type  ipi-user-session-types:user_session_user_role_type_t;
            description "The user role type.";
        } // END of user-role definition.

        leaf remote-ip  {
            type  string {
                length "1..1965";
                pattern "[^?' =,>|]+";
            }
            description "Remote IP address for netconf clients";
        } // END of remote-ip definition.

    } // END of user-sessions-state definition.
    grouping user-sessions-top {
        description
            "All the runtime user sessions";

        list session {
            key "id";
            config false;
            description
                "List of all runtime user sessions, including line vty, line console
                            and netconf sessions.";
            leaf id  {
                type  leafref {
                    path  "../state/id";
                }
                description "The user session id.";
            } // END of id definition.

            container state {
                config false;
                description
                    "Operational state data for user session";
                uses user-sessions-state;
            } // END of state-container definition.
        } // End of session-list
    } // END of user-sessions-top definition.

    grouping  sessions-grouping {
    description
        "Top level container that holds all user-session runtime attributes";
    container sessions {
        if-feature feature-list:HAVE_IMI;
        config false;
        description
            "Top level container that holds all user-session runtime attributes";
        uses user-sessions-top;
    } // END of sessions-container definition.
    } // END of sessions-grouping definition.


}
