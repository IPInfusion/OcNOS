/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-sys-service-mgmt.yang
*
*/

module ipi-sys-service-mgmt {

    yang-version 1.1;

    namespace   "http://www.ipinfusion.com/yang/ocnos/ipi-sys-service-mgmt";

    prefix "ipi-sys-service-mgmt";

    import ipi-sys-service-mgmt-types {
        prefix ipi-sys-service-mgmt-types;
        revision-date 2025-06-27;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "sys-service-mgmt manages the special services of the device";


    revision "2025-06-27" {
        description "Created CLI for updating system config backup content";
        reference " 1.0.0.";
    }

    grouping system-backup-config {
        description
            "system backup configuration data";
        leaf system-backup-content  {
            type  ipi-sys-service-mgmt-types:system_backup_content_type_t;
            description "system backup content";
        } // END of system-backup-content definition.

    } // END of system-backup-config definition.
    grouping system-backup-top {
        description
            "Top level grouping of system-backup data";
        container system-backup {
            description
                "system-backup Configuration";
            container config {
                description
                    "system-backups Configuration";
                uses system-backup-config;
            } // END of config-container definition.
            container state {
                config false;
                description
                    "system-backups state data";
                uses system-backup-config;
            } // END of state-container definition.
        } // END of system-backup-container definition.
    } // END of system-backup-top definition.

    grouping  system-backups-grouping {
    description
        "system-backups Configuration";
    container system-backups {
        if-feature feature-list:HAVE_HOSTPD;
        description
            "system-backups Configuration";
        uses system-backup-top;
    } // END of system-backups-container definition.
    } // END of system-backups-grouping definition.

    uses system-backups-grouping;

}
