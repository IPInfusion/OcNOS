/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-logging.yang
*
*/

module ipi-logging {

    yang-version 1.1;

    namespace   "http://www.ipinfusion.com/yang/ocnos/ipi-logging";

    prefix "ipi-logging";

    import ipi-logging-types {
        prefix ipi-logging-types;
        revision-date 2025-09-23;
    }

    import cml-data-types {
        prefix cml-data-types;
        revision-date 2026-05-15;
    }

    import feature-list {
        prefix feature-list;
        revision-date 2026-09-15;
    }

    include ipi-logging-remote { revision-date 2025-12-24;}
    include ipi-logging-cli { revision-date 2025-04-18;}
    include ipi-logging-fault-management { revision-date 2024-09-23;}
    organization
        "IP Infusion Inc.";

    contact
        "Address: 3965 Freedom Circle, Suite 200, Santa Clara, CA 95054
         Phone: +1 408-400-1900
         E-mail: support@ipinfusion.com
         Web: http://www.ipinfusion.com/";

    description
        "Syslog Configurations";


    revision "2025-12-24" {
        description "Added dependentObject tag for remote-logging feature";
        reference " 0.12.5.";
    }

    revision "2025-11-03" {
        description "Added new attribute under BDR feature to suppress repeated logs";
        reference " 0.12.4.";
    }

    revision "2025-10-31" {
        description "Corrected the datatype of the file_type attribute in the remove-file object action";
        reference " 0.12.3.";
    }

    revision "2025-10-07" {
        description "Added dependentObj tag for background-debug and config container";
        reference " 0.12.2.";
    }

    revision "2025-09-23" {
        description "Updated BDR buffer-size attribute from objectlist to container";
        reference " 0.12.1.";
    }

    revision "2025-09-09" {
        description "Added Background debug recorder feature changes";
        reference " 0.12.0.";
    }

    revision "2025-05-06" {
        description "Updated when tag to update db when default instance is enabled";
        reference " 0.11.11.";
    }

    revision "2025-04-18" {
        description "Change the attribute of logging cli in submodule ipi-logging-cli";
        reference " 0.11.10.";
    }

    revision "2025-02-11" {
        description "Removed max-session-limit hierarchy in submodule ipi-logging-cli";
        reference " 0.11.9.";
    }

    revision "2025-02-08" {
        description "Revert the range of logging remote server host udp-port number";
        reference " 0.11.8.";
    }

    revision "2025-01-27" {
        description "Removed the log syslog and no log syslog CLI and added log syslog as hidden manual CLI";
        reference " 0.11.7.";
    }

    revision "2024-11-08" {
        description "Updated the range of logging remote server host udp-port number";
        reference " 0.11.6.";
    }

    revision "2024-09-23" {
        description "Fixed DB-sync error when deleting severity config at the snmp-syslog container";
        reference " 0.11.5.";
    }

    revision "2024-09-05" {
        description "Added support for SYSLOG over SNMP traps";
        reference " 0.11.4.";
    }

    revision "2024-08-28" {
        description "Added simultaneous user defined VRF support for remote server";
        reference " 0.11.3.";
    }

    revision "2024-08-22" {
        description "Added flag in when tag to resolve the dependency failure";
        reference " 0.11.2.";
    }

    revision "2024-08-02" {
        description "Remove change lower to upper case validation from hostname. Since hostname are case sensitive";
        reference " 0.11.1.";
    }

    revision "2024-06-25" {
        description "Introduced disable-default attribute to resolve show running-config issue";
        reference " 0.11.0.";
    }

    revision "2024-05-10" {
        description "New attribute for cli timestamp option";
        reference " 0.10.0.";
    }

    revision "2024-03-20" {
        description "Updated maxfilesize attribute to non-mandatory attribute for logging logfile ";
        reference " 0.9.0.";
    }

    revision "2023-12-20" {
        description "Added attr for remote server authpriv facility";
        reference " 0.8.0.";
    }

    revision "2023-08-09" {
        description "Added a Cli to remove the files based on file type";
        reference " 0.10.4.";
    }

    revision "2023-08-08" {
        description "Added when tag to remove logging facility when syslog service is moved between VRF";
        reference " 0.10.3.";
    }

    revision "2023-06-05" {
        description "Added Custom syslog port feature";
        reference " 0.10.2.";
    }

    revision "2023-05-30" {
        description "Added changes to not allow deletion of logging container";
        reference " 0.10.1.";
    }

    revision "2023-05-29" {
        description "Implemented no-debug-all command for Hostpd modules";
        reference " 0.10.0.";
    }

    revision "2023-01-16" {
        description "Implemented no-debug-all command";
        reference " 0.9.2.";
    }

    revision "2022-11-21" {
        description "Added top level container for module-logging object";
        reference " 0.9.1.";
    }

    revision "2022-11-16" {
        description "Updated cli prependstr tag in logging-remote submodule";
        reference " 0.9.0.";
    }

    revision "2022-10-13" {
        description "Corrected logging monitor CLI";
        reference " 0.8.5.";
    }

    revision "2022-10-11" {
        description "Updated logging level of mstp";
        reference " 0.8.4.";
    }

    revision "2022-09-29" {
        description "Updated the name of mrib module in smi-server-modules tag";
        reference " 0.8.3.";
    }

    revision "2022-08-10" {
        description "Updated smi-server-modules tag paramters";
        reference " 0.8.2.";
    }

    revision "2022-07-28" {
        description "Updated smi-server-modules with restructured RIPng module name";
        reference " 0.8.1.";
    }

    revision "2022-07-26" {
        description "Corrected RIP datamodel as per Open Config style";
        reference " 0.8.0.";
    }

    revision "2022-07-13" {
        description "Making debug logging host CLI hidden";
        reference " 0.7.2.";
    }

    revision "2022-06-30" {
        description "Updated the ipi-logging-types with severity level description";
        reference " 0.7.1.";
    }

    revision "2022-06-01" {
        description "Updated the yang file with feature";
        reference " 0.7.0.";
    }

    revision "2022-04-06" {
        description "Add disabling support for logging monitor and logging console";
        reference " 0.5.1.";
    }

    revision "2022-03-29" {
        description "Modified sub module fault-management";
        reference " 0.6.0.";
    }

    revision "2022-01-13" {
        description "Modified sub module";
        reference " 0.5.0.";
    }

    revision "2021-09-03" {
        description "Update descriptions of attribute";
        reference " 0.4.4.";
    }

    revision "2021-07-20" {
        description "Remove auto-populate tag from module-config";
        reference " 0.4.3.";
    }

    revision "2021-06-30" {
        description "Updated data types to use standard yang types wherever applicable";
        reference " 0.4.2.";
    }

    revision "2021-05-08" {
        description "Remove db-triggers for all option in the logging level";
        reference " 0.4.1.";
    }

    revision "2021-03-30" {
        description "Adding fault-management as submodule of ipi-logging";
        reference " 0.4.0.";
    }

    revision "2021-03-06" {
        description "Add a pattern validation for debug-logfile name";
        reference " 0.3.0.";
    }

    revision "2021-01-05" {
        description "Restructured module as per open-config";
        reference " 0.2.0.";
    }

    revision "2018-06-21" {
        description "Initial Version";
        reference " 0.1.0.";
    }

    grouping logging-syslog-config {
        description
            "Grouping for syslog configuration";
        leaf timestamp-granularity  {
            type  ipi-logging-types:timestamp_units_t;
            default "milliseconds";
            description "Use this attribute to set the logging timestamp granularity.";
        } // END of timestamp-granularity definition.

        leaf cli-timestamp  {
            type  empty;
            description "Use this attribute to display execution timestamp in show output";
        } // END of cli-timestamp definition.

    } // END of logging-syslog-config definition.
    grouping logging-syslog-top {
        description
            "Grouping for syslog configuration";
        container syslog {
            if-feature feature-list:HAVE_SYSLOG;
            description
                "Syslog configuration parameters";
            container config {
                description
                    "Configuration data";
                uses logging-syslog-config;
            } // END of config-container definition.
            container state {
                config false;
                description
                    "Operational state data";
                uses logging-syslog-config;
            } // END of state-container definition.
        } // END of syslog-container definition.
    } // END of logging-syslog-top definition.
    grouping logging-debug-logfile-config {
        description
            "Grouping for debug logging log file configuration";
        leaf file-name  {
            type  string {
                length "1..1965";
                pattern "[a-zA-Z0-9_]*";
            }
            mandatory true;
            description "Set name of the debug log file.";
        } // END of file-name definition.

        leaf max-file-size  {
            type  uint32 {
                 range "4096..4194304"  {
                    description "4096..4194304: Supported range 4096 - 4194304";
                 }
            }
            units "bytes";
            mandatory true;
            description "Set size of the debug log file in bytes. The default value is 4194304
                        bytes.";
        } // END of max-file-size definition.

    } // END of logging-debug-logfile-config definition.
    grouping disable-debug-all-config {
        description
            "disable-debug-all-config";
        leaf disable-all-modules-debug  {
            type  empty;
            description "Use this attribute to unset debug globally";
        } // END of disable-all-modules-debug definition.

    } // END of disable-debug-all-config definition.
    grouping debug-global-top {
        description
            "debug-global-top";
    } // END of debug-global-top definition.
    grouping logging-debug-logfile-top {
        description
            "Grouping for debug logging log file configuration";
        container debug-logfile {
            description
                "Log file logging debug configuration parameters";
            container config {
                presence "yes";
                description
                    "Configuration data";
                uses logging-debug-logfile-config;
            } // END of config-container definition.
            container state {
                config false;
                description
                    "Operational state data";
                uses logging-debug-logfile-config;
            } // END of state-container definition.
        } // END of debug-logfile-container definition.
    } // END of logging-debug-logfile-top definition.
    grouping logging-logfile-config {
        description
            "Grouping for logging log file configuration";
        leaf file-name  {
            type  string {
                length "1..1965";
                pattern "[a-zA-Z0-9_]*";
            }
            mandatory true;
            description "Use this attribute to set name of the logging file.";
        } // END of file-name definition.

        leaf severity-level  {
            type  ipi-logging-types:log_severity_t;
            mandatory true;
            description "Use this attribute to set severity level of logging file. Default
                        value is 6-debug-info.";
        } // END of severity-level definition.

        leaf max-file-size  {
            type  uint32 {
                 range "4096..419430400"  {
                    description "4096..419430400: Supported range 4096 - 419430400";
                 }
            }
            units "bytes";
            description "Set size of the log file in bytes. Default value is 419430400 bytes.";
        } // END of max-file-size definition.

    } // END of logging-logfile-config definition.
    grouping logging-logfile-top {
        description
            "Grouping for logging log file configuration";
        container logfile {
            description
                "Log file logging configuration parameters";
            container config {
                presence "yes";
                description
                    "Configuration data";
                uses logging-logfile-config;
            } // END of config-container definition.
            container state {
                config false;
                description
                    "Operational state data";
                uses logging-logfile-config;
            } // END of state-container definition.
        } // END of logfile-container definition.
    } // END of logging-logfile-top definition.
    grouping logging-console-config {
        description
            "Grouping for logging console configuration";
        leaf enable-logging  {
            type  cml-data-types:cml_enable_disable_t;
            mandatory true;
            description "Use this attribute to enable the logging console.";
        } // END of enable-logging definition.

        leaf severity-level  {
            // when " ../enable-logging='enable' ";
            type  ipi-logging-types:log_severity_t;
            default "2";
            description "Use this attribute to set severity level of logging console. Default
                        value is 2-critical.";
        } // END of severity-level definition.

    } // END of logging-console-config definition.
    grouping logging-console-top {
        description
            "Grouping for logging console configuration";
        container console-logging {
            description
                "Console logging configuration parameters";
            container config {
                presence "yes";
                description
                    "Configuration data";
                uses logging-console-config;
            } // END of config-container definition.
            container state {
                config false;
                description
                    "Operational state data";
                uses logging-console-config;
            } // END of state-container definition.
        } // END of console-logging-container definition.
    } // END of logging-console-top definition.
    grouping logging-monitor-config {
        description
            "Grouping for logging monitor configuration";
        leaf enable-logging  {
            type  cml-data-types:cml_enable_disable_t;
            mandatory true;
            description "Use this attribute to enable logging monitor.";
        } // END of enable-logging definition.

        leaf severity-level  {
            // when " ../enable-logging='enable' ";
            type  ipi-logging-types:log_severity_t;
            default "7";
            description "Use this attribute to set severity level of logging monitor. Default
                        value is 7-debug-details.";
        } // END of severity-level definition.

    } // END of logging-monitor-config definition.
    grouping logging-monitor-top {
        description
            "Grouping for logging monitor configuration";
        container monitor-logging {
            description
                "Monitor logging configuration parameters";
            container config {
                presence "yes";
                description
                    "Configuration data";
                uses logging-monitor-config;
            } // END of config-container definition.
            container state {
                config false;
                description
                    "Operational state data";
                uses logging-monitor-config;
            } // END of state-container definition.
        } // END of monitor-logging-container definition.
    } // END of logging-monitor-top definition.
    grouping logging-module-config {
        description
            "Grouping for syslog modules level configuration";
        leaf module-name  {
            type  ipi-logging-types:module_names_t;
            description "Use this attribute to set the module name of proccess to be logged.";
        } // END of module-name definition.

        leaf severity-level  {
            type  ipi-logging-types:log_severity_t;
            mandatory true;
            description "Use this attribute to set the severity level that a message for a
                        specific module must reach before the messages is logged. Default
                        value is 2-critical.";
        } // END of severity-level definition.

    } // END of logging-module-config definition.
    grouping logging-module-top {
        description
            "Grouping for syslog modules level configuration";
        container logging-modules {
            description
                "Top level container for syslog modules";

            list module-logging {
                key "module-name";
                description
                    "Modules";
                leaf module-name  {
                    type  leafref {
                        path  "../config/module-name";
                    }
                    description "Use this attribute to set the module name of proccess to be logged.";
                } // END of module-name definition.

                container config {
                    description
                        "Configuration data";
                    uses logging-module-config;
                } // END of config-container definition.
                container state {
                    config false;
                    description
                        "Operational state data";
                    uses logging-module-config;
                } // END of state-container definition.
            } // End of module-logging-list
        } // END of logging-modules-container definition.
    } // END of logging-module-top definition.
    grouping logging-background-debug-buffer-config {
        description
            "Grouping for BDR log buffer configuration";
        leaf enable  {
            type  empty;
            mandatory true;
            description "Use this attribute to enable a BDR feature";
        } // END of enable definition.

        leaf buffer-size  {
            type  uint8 {
                 range "1..10"  {
                    description "1..10: Supported range 1 - 10";
                 }
            }
            units "MBytes";
            default "1";
            description "Use this attribute to set the BDR module internal buffer size in MB";
        } // END of buffer-size definition.

    } // END of logging-background-debug-buffer-config definition.
    grouping logging-background-debug-module-config {
        description
            "Grouping for BDR modules level configuration";
        leaf module-name  {
            type  ipi-logging-types:bdr_module_names_t;
            description "Use this attribute to set the module name of proccess to be logged.";
        } // END of module-name definition.

        leaf severity-level  {
            type  ipi-logging-types:log_severity_t;
            default "7";
            description "Use this attribute to set the severity level that a message for a
                        specific module must reach before the messages is logged. Default
                        value is 7.";
        } // END of severity-level definition.

        leaf suppress-non-bdr-logs  {
            type  empty;
            description "This feature indicates that the BDR debug is enabled and suppressed
                        other logging";
        } // END of suppress-non-bdr-logs definition.

        leaf disable-suppress-repeated-logs  {
            type  empty;
            description "This attribute indicates repeated logs are suppressed for BDR";
        } // END of disable-suppress-repeated-logs definition.

    } // END of logging-background-debug-module-config definition.
    grouping logging-background-debug-top {
        description
            "Grouping for logging background-debug configuration";
        container background-debug {
            description
                "Background-debug logging configuration parameters";
            container config {
                presence "Enable BDR";
                description
                    "Configuration data for background-debug";
                uses logging-background-debug-buffer-config;
            } // END of config-container definition.
            container state {
                config false;
                description
                    "Operational state data";
                uses logging-background-debug-buffer-config;
            } // END of state-container definition.
            container bdr-module-loggings {
                description
                    "Container for bdr logging attributes";

                list bdr-module-logging {
                when " /ipi-logging:logging/ipi-logging:background-debug/ipi-logging:config ";
                    key "module-name";
                    description
                        "Modules";
                    leaf module-name  {
                        type  leafref {
                            path  "../config/module-name";
                        }
                        description "Use this attribute to set the module name of proccess to be logged.";
                    } // END of module-name definition.

                    container config {
                        description
                            "Configuration data";
                        uses logging-background-debug-module-config;
                    } // END of config-container definition.
                    container state {
                        config false;
                        description
                            "Operational state data";
                        uses logging-background-debug-module-config;
                    } // END of state-container definition.
                } // End of bdr-module-logging-list
            } // END of bdr-module-loggings-container definition.
        } // END of background-debug-container definition.
    } // END of logging-background-debug-top definition.

    grouping  logging-grouping {
    description
        "Logging control";
    container logging {
        description
            "Logging control";
        uses logging-module-top;
        uses logging-monitor-top;
        uses logging-console-top;
        uses logging-logfile-top;
        uses logging-debug-logfile-top;
        uses logging-syslog-top;
        uses debug-global-top;
        uses logging-background-debug-top;
        uses remote-logging-grouping;
        uses global-grouping;
        uses cli-logging-grouping;
        uses snmp-syslog-grouping;
        uses fault-management-grouping;
    } // END of logging-container definition.
    } // END of logging-grouping definition.

    uses logging-grouping;

    rpc logging-fms-flush-db {
        if-feature feature-list:HAVE_FMS;
        description "Flush the FMS database";
    }

    rpc logging-fms-shelve {
        if-feature feature-list:HAVE_FMS;
        description "Use this RPC to shelve alarm based on type";
        input  {
            leaf alarm-type  {
                type string;
                mandatory true;
                description "Shelve Alarm Type";
            }
        }
    }

    rpc logging-fms-close {
        if-feature feature-list:HAVE_FMS;
        description "Use this RPC to close an active alarm";
        input  {
            leaf active-alarm-id  {
                type string;
                mandatory true;
                description "Active Alarm ID";
            }
        }
    }

    rpc terminal-debug-all-off {
        description "Use this command to unconfigure the debug in all modules";
    }

    rpc logging-clear-debug-logfile {
        description "Use logging-clear-debug-logfile to clear the debug logfile content.";
    }

    rpc logging-clear-logging-logfile {
        description "Use logging-clear-logging-logfile to clear the logging logfile
                    content.";
    }

    rpc remove-file {
        description "Use this operation to remove the files based on type";
        input  {
            leaf file_type  {
                type ipi-logging-types:remove_files_t;
                mandatory true;
                description "Use this attribute to get the file type";
            }
            leaf filename  {
                type ipi-logging-types:file_type_t;
                mandatory true;
                description "Use this attribute to get the file name";
            }
        }
    }

}
