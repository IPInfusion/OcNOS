/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-logging-types.yang
*
*/

module ipi-logging-types {

    yang-version 1.1;

    namespace   "http://www.ipinfusion.com/yang/ocnos/ipi-logging-types";

    prefix "ipi-logging-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Logging data types";


    revision "2025-09-23" {
        description "Updated data type for BDR module-name";
        reference " 0.5.1.";
    }

    revision "2025-09-09" {
        description "Added a new data type for BDR module-name";
        reference " 0.5.0.";
    }

    revision "2023-08-08" {
        description "Added a Cli to remove the files based on file type";
        reference " 0.4.2.";
    }

    revision "2022-06-30" {
        description "Updated the yang file with severity enum description";
        reference " 0.4.1.";
    }

    revision "2022-06-01" {
        description "Updated the yang file with feature";
        reference " 0.4.0.";
    }

    revision "2022-01-13" {
        description "Added if-feature for data types";
        reference " 0.3.0.";
    }

    revision "2021-09-03" {
        description "Update descriptions of attribute";
        reference " 0.2.0.";
    }

    revision "2021-01-05" {
        description "Remote-syslog and libsyslog restructuring according to OpenConfig style";
        reference " 0.1.0.";
    }



    typedef  log_facility_t {
        type enumeration {
            enum local0 {
                value 0;
                description "Use local0 facility";
            }
            enum local1 {
                value 1;
                description "Use local1 facility";
            }
            enum local2 {
                value 2;
                description "Use local2 facility";
            }
            enum local3 {
                value 3;
                description "Use local3 facility";
            }
            enum local4 {
                value 4;
                description "Use local4 facility";
            }
            enum local5 {
                value 5;
                description "Use local5 facility";
            }
            enum local6 {
                value 6;
                description "Use local6 facility";
            }
            enum local7 {
                value 7;
                description "Use local7 facility";
            }
            enum user {
                value 8;
                description "Use user facility";
            }
        }
        description "type definition for LOG_FACILITY_T";
    }

    typedef  log_severity_t {
        type enumeration {
            enum 0 {
                value 0;
                description "emerg";
            }
            enum 1 {
                value 1;
                description "alert";
            }
            enum 2 {
                value 2;
                description "critical";
            }
            enum 3 {
                value 3;
                description "error";
            }
            enum 4 {
                value 4;
                description "oper-notify/debug-warn";
            }
            enum 5 {
                value 5;
                description "oper-info/debug-notify";
            }
            enum 6 {
                value 6;
                description "debug-info";
            }
            enum 7 {
                value 7;
                description "debug-details";
            }
        }
        description "type definition for LOG_SEVERITY_T";
    }

    typedef  timestamp_units_t {
        type enumeration {
            enum none {
                value 0;
                description "No timestamp in log messages";
            }
            enum microseconds {
                value 1;
                description "Timestamp in micro-seconds";
            }
            enum milliseconds {
                value 2;
                description "Timestamp in milli-seconds (Default)";
            }
            enum seconds {
                value 3;
                description "Timestamp in seconds";
            }
        }
        description "type definition for TIMESTAMP_UNITS_T";
    }

    typedef  module_names_t {
        type enumeration {
            enum auth {
                value 1;
                if-feature feature-list:HAVE_AUTHD;
                description "Set logging level for auth messages";
            }
            enum bgp {
                value 2;
                description "Set logging level for bgp messages";
            }
            enum cmm {
                value 3;
                if-feature feature-list:HAVE_CMMD;
                description "Set logging level for cmm messages";
            }
            enum dvmrp {
                value 4;
                if-feature feature-list:HAVE_DVMRPD;
                description "Set logging level for dvmrp messages";
            }
            enum hostp {
                value 5;
                if-feature feature-list:HAVE_HOSTPD;
                description "Set logging level for hostp messages";
            }
            enum hsl {
                value 6;
                description "Set logging level for hsl messages";
            }
            enum isis {
                value 7;
                if-feature feature-list:HAVE_ISISD;
                description "Set logging level for isis messages";
            }
            enum ldp {
                value 8;
                if-feature feature-list:HAVE_LDPD;
                description "Set logging level for ldp messages";
            }
            enum lag {
                value 9;
                if-feature feature-list:HAVE_LAGD;
                description "Set logging level for lagd messages";
            }
            enum l2mrib {
                value 10;
                description "Set logging level for l2mrib messages";
            }
            enum mstp {
                value 11;
                description "Set logging level for mstp messages";
            }
            enum mrib {
                value 12;
                description "Set logging level for mrib messages";
            }
            enum nsm {
                value 13;
                description "Set logging level for nsm messages";
            }
            enum onm {
                value 14;
                if-feature feature-list:HAVE_ONMD;
                description "Set logging level for onm messages";
            }
            enum oam {
                value 15;
                description "Set logging level for oam messages";
            }
            enum ospf {
                value 16;
                description "Set logging level for ospf messages";
            }
            enum ospf6 {
                value 17;
                description "Set logging level for ospf6 messages";
            }
            enum ptp {
                value 18;
                if-feature feature-list:HAVE_PTPD;
                description "Set logging level for ptp messages";
            }
            enum rip {
                value 19;
                description "Set logging level for rip messages";
            }
            enum rmon {
                value 20;
                if-feature feature-list:HAVE_RMOND;
                description "Set logging level for rmon messages";
            }
            enum pim {
                value 21;
                description "Set logging level for pim messages";
            }
            enum rib {
                value 22;
                description "Set logging level for rib messages";
            }
            enum vrrp {
                value 23;
                description "Set logging level for vrrp messages";
            }
            enum sflow {
                value 24;
                if-feature feature-list:HAVE_SFLOW;
                description "Set logging level for sflow messages";
            }
            enum trill {
                value 25;
                if-feature feature-list:HAVE_TRILLD;
                description "Set logging level for trill messages";
            }
            enum rsvp {
                value 26;
                if-feature feature-list:HAVE_RSVPD;
                description "Set logging level for rsvp messages";
            }
            enum pserv {
                value 27;
                if-feature feature-list:HAVE_PSERVD;
                description "Set logging level for pservd messages";
            }
            enum cml {
                value 28;
                if-feature feature-list:HAVE_CMLD;
                description "Set logging level for cml messages";
            }
            enum ndd {
                value 29;
                if-feature feature-list:HAVE_NDD;
                description "Set logging level for ndd messages";
            }
            enum ripng {
                value 30;
                description "Set logging level for ripng messages";
            }
            enum vlog {
                value 31;
                description "Set logging level for vlog messages";
            }
            enum all {
                value 32;
                description "Set logging level for all modules";
            }
            enum synce {
                value 33;
                if-feature feature-list:HAVE_SYNCED;
                description "Set logging level for synce messages";
            }
            enum pon {
                value 34;
                if-feature feature-list:HAVE_POND;
                description "Set logging level for pon messages";
            }
            enum pcep {
                value 35;
                if-feature feature-list:HAVE_PCEP;
                description "Set logging level for pcep messages";
            }
            enum udld {
                value 36;
                if-feature feature-list:HAVE_UDLD;
                description "Set logging level for udld messages";
            }
        }
        description "type definition for MODULE_NAMES_T";
    }

    typedef  bdr_module_names_t {
        type enumeration {
            enum auth {
                value 1;
                if-feature feature-list:HAVE_AUTHD;
                description "Set logging level for auth messages";
            }
            enum bgp {
                value 2;
                description "Set logging level for bgp messages";
            }
            enum cmm {
                value 3;
                if-feature feature-list:HAVE_CMMD;
                description "Set logging level for cmm messages";
            }
            enum dvmrp {
                value 4;
                if-feature feature-list:HAVE_DVMRPD;
                description "Set logging level for dvmrp messages";
            }
            enum hostp {
                value 5;
                if-feature feature-list:HAVE_HOSTPD;
                description "Set logging level for hostp messages";
            }
            enum hsl {
                value 6;
                description "Set logging level for hsl messages";
            }
            enum isis {
                value 7;
                if-feature feature-list:HAVE_ISISD;
                description "Set logging level for isis messages";
            }
            enum ldp {
                value 8;
                if-feature feature-list:HAVE_LDPD;
                description "Set logging level for ldp messages";
            }
            enum lag {
                value 9;
                if-feature feature-list:HAVE_LAGD;
                description "Set logging level for lagd messages";
            }
            enum l2mrib {
                value 10;
                description "Set logging level for l2mrib messages";
            }
            enum mstp {
                value 11;
                description "Set logging level for mstp messages";
            }
            enum mrib {
                value 12;
                description "Set logging level for mrib messages";
            }
            enum nsm {
                value 13;
                description "Set logging level for nsm messages";
            }
            enum onm {
                value 14;
                if-feature feature-list:HAVE_ONMD;
                description "Set logging level for onm messages";
            }
            enum oam {
                value 15;
                description "Set logging level for oam messages";
            }
            enum ospf {
                value 16;
                description "Set logging level for ospf messages";
            }
            enum ospf6 {
                value 17;
                description "Set logging level for ospf6 messages";
            }
            enum ptp {
                value 18;
                if-feature feature-list:HAVE_PTPD;
                description "Set logging level for ptp messages";
            }
            enum rip {
                value 19;
                description "Set logging level for rip messages";
            }
            enum rmon {
                value 20;
                if-feature feature-list:HAVE_RMOND;
                description "Set logging level for rmon messages";
            }
            enum pim {
                value 21;
                description "Set logging level for pim messages";
            }
            enum rib {
                value 22;
                description "Set logging level for rib messages";
            }
            enum vrrp {
                value 23;
                description "Set logging level for vrrp messages";
            }
            enum sflow {
                value 24;
                if-feature feature-list:HAVE_SFLOW;
                description "Set logging level for sflow messages";
            }
            enum trill {
                value 25;
                if-feature feature-list:HAVE_TRILLD;
                description "Set logging level for trill messages";
            }
            enum rsvp {
                value 26;
                if-feature feature-list:HAVE_RSVPD;
                description "Set logging level for rsvp messages";
            }
            enum pserv {
                value 27;
                if-feature feature-list:HAVE_PSERVD;
                description "Set logging level for pservd messages";
            }
            enum cml {
                value 28;
                if-feature feature-list:HAVE_CMLD;
                description "Set logging level for cml messages";
            }
            enum ndd {
                value 29;
                if-feature feature-list:HAVE_NDD;
                description "Set logging level for ndd messages";
            }
            enum ripng {
                value 30;
                description "Set logging level for ripng messages";
            }
            enum vlog {
                value 31;
                description "Set logging level for vlog messages";
            }
            enum all {
                value 32;
                description "Set logging level for all modules";
            }
            enum synce {
                value 33;
                if-feature feature-list:HAVE_SYNCED;
                description "Set logging level for synce messages";
            }
            enum pon {
                value 34;
                if-feature feature-list:HAVE_POND;
                description "Set logging level for pon messages";
            }
            enum pcep {
                value 35;
                if-feature feature-list:HAVE_PCEP;
                description "Set logging level for pcep messages";
            }
            enum udld {
                value 36;
                if-feature feature-list:HAVE_UDLD;
                description "Set logging level for udld messages";
            }
        }
        description "type definition for BDR_MODULE_NAMES_T";
    }

    typedef  remove_files_t {
        type enumeration {
            enum techsupport {
                value 0;
                description "Tech Support Option For Protocol(s)";
            }
        }
        description "type definition for REMOVE_FILES_T";
    }

    typedef  all_t {
        type enumeration {
            enum all {
                value 0;
                description "Remove all files";
            }
        }
        description "type definition for ALL_T";
    }

    typedef  cml_filename_t {
        type string {
            pattern "[^?' =,>|]+";
        }
        description "type definition for CML_FILENAME_T";
    }

    typedef  file_type_t {
        type union {
            type all_t {

            }
            type cml_filename_t {

            }
        }
        description "type definition for FILE_TYPE_T";
    }

}
