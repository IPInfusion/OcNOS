/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-snmp-server-extended-types.yang
*
*/

module ipi-snmp-server-extended-types {

    yang-version 1.1;

    namespace   "http://www.ipinfusion.com/yang/ocnos/ipi-snmp-server-extended-types";

    prefix "ipi-snmp-server-extended-types";

    organization
        "IP Infusion Inc.";

    contact
        "Address: 3965 Freedom Circle, Suite 200, Santa Clara, CA 95054
         Phone: +1 408-400-1900
         E-mail: support@ipinfusion.com
         Web: http://www.ipinfusion.com/";

    description
        "ipi-snmp-server-extended datatypes";


    revision "2023-08-28" {
        description "Added a new datatype for String without spaces";
        reference " 0.4.0.";
    }

    revision "2022-06-01" {
        description "Updated the yang file with feature";
        reference " 0.3.0.";
    }

    revision "2022-03-20" {
        description "Added new cli's for SNMP context support";
        reference " 0.2.0.";
    }

    revision "2021-11-16" {
        description "Initial Version";
        reference " 0.1.0.";
    }



    typedef  cml_line_without_pattern_t {
        type string;
        description "type definition for CML_LINE_WITHOUT_PATTERN_T";
    }

    typedef  snmp_server_group_t {
        type enumeration {
            enum network-operator {
                value 1;
                description "System configured group for read-only(default)";
            }
            enum network-admin {
                value 2;
                description "System configured group for read-only";
            }
        }
        description "type definition for SNMP_SERVER_GROUP_T";
    }

    typedef  snmp_server_access_t {
        type enumeration {
            enum ro {
                value 1;
                description "Read-only access with this community string";
            }
        }
        description "type definition for SNMP_SERVER_ACCESS_T";
    }

    typedef  snmp_server_context_t {
        type enumeration {
            enum all {
                value 1;
                description "To allow all context-name";
            }
        }
        description "type definition for SNMP_SERVER_CONTEXT_T";
    }

    typedef  snmp_server_context_name_t {
        type union {
            type snmp_server_context_t {

            }
            type string {

            }
        }
        description "type definition for SNMP_SERVER_CONTEXT_NAME_T";
    }

    typedef  snmp_server_view_version_t {
        type enumeration {
            enum v1 {
                value 1;
                description "Specify v1 for SNMPv1";
            }
            enum v2c {
                value 2;
                description "Specify v2c for SNMPv2c";
            }
        }
        description "type definition for SNMP_SERVER_VIEW_VERSION_T";
    }

    typedef  snmp_server_oid_tree_t {
        type enumeration {
            enum included {
                value 1;
                description "Specify to include";
            }
            enum excluded {
                value 2;
                description "Specify to exclude";
            }
        }
        description "type definition for SNMP_SERVER_OID_TREE_T";
    }

    typedef  snmp_server_user_group_t {
        type string {
            pattern "[^?' =,>|]+";
        }
        description "type definition for SNMP_SERVER_USER_GROUP_T";
    }

    typedef  snmp_server_group_name_t {
        type union {
            type snmp_server_group_t {

            }
            type snmp_server_user_group_t {

            }
        }
        description "type definition for SNMP_SERVER_GROUP_NAME_T";
    }

    typedef  snmp_server_key_type_t {
        type enumeration {
            enum plain {
                value 0;
                description "To specify shared key in clear-text form";
            }
            enum encrypt {
                value 1;
                description "To specify shared key in encrypted form";
            }
        }
        description "type definition for SNMP_SERVER_KEY_TYPE_T";
    }

    typedef  snmp_server_auth_t {
        type enumeration {
            enum md5 {
                value 1;
                description "Specify md5 authentication";
            }
            enum sha {
                value 2;
                description "Specify sha authentication";
            }
        }
        description "type definition for SNMP_SERVER_AUTH_T";
    }

    typedef  snmp_server_priv_t {
        type enumeration {
            enum des {
                value 1;
                description "Specify des privilege";
            }
            enum aes {
                value 2;
                description "Specify aes privilege";
            }
        }
        description "type definition for SNMP_SERVER_PRIV_T";
    }

    typedef  snmp_server_version_t {
        type enumeration {
            enum 1 {
                value 1;
                description "Use SNMPv1";
            }
            enum 2c {
                value 2;
                description "Use SNMPv2c";
            }
            enum 3 {
                value 3;
                description "Use SNMPv3";
            }
        }
        description "type definition for SNMP_SERVER_VERSION_T";
    }

    typedef  snmp_server_version3_auth_type_t {
        type enumeration {
            enum noauth {
                value 1;
                description "Use the SNMPv3 noAuthNoPriv Security Level";
            }
            enum auth {
                value 2;
                description "Use the SNMPv3 authNoPriv Security Level";
            }
            enum priv {
                value 3;
                description "Use the SNMPv3 authPriv Security Level";
            }
        }
        description "type definition for SNMP_SERVER_VERSION3_AUTH_TYPE_T";
    }

    typedef  snmp_v3_server_group_auth_type_t {
        type enumeration {
            enum auth {
                value 1;
                description "Use the SNMPv3 AuthNoPriv Security Level";
            }
            enum priv {
                value 2;
                description "Use the SNMPv3 authPriv Security Level";
            }
            enum noauth {
                value 3;
                description "Use the SNMPv3 NoauthNoPriv Security Level";
            }
        }
        description "type definition for SNMP_V3_SERVER_GROUP_AUTH_TYPE_T";
    }

    typedef  snmp_server_notification_t {
        type enumeration {
            enum traps {
                value 1;
                description "Send Traps messages to this host";
            }
            enum informs {
                value 2;
                description "Send Inform messages to this host";
            }
        }
        description "type definition for SNMP_SERVER_NOTIFICATION_T";
    }

}
