/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-snmp-server.yang
*
*/

module ipi-snmp-server {

    yang-version 1.1;

    namespace   "http://www.ipinfusion.com/yang/ocnos/ipi-snmp-server";

    prefix "ipi-snmp-server";

    import ipi-snmp {
        prefix ipi-snmp;
        revision-date 2025-08-08;
    }

    import cml-data-types {
        prefix cml-data-types;
        revision-date 2026-05-15;
    }

    import ipi-network-instance {
        prefix ipi-network-instance;
        revision-date 2026-08-12;
    }

    import ipi-vrf {
        prefix ipi-vrf;
        revision-date 2026-08-12;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module provides Simple Network Management Protocol configuration";


    revision "2026-08-14" {
        description "added the autopopulate tag to populate vrf";
        reference " 0.10.1.";
    }

    revision "2026-08-12" {
        description "Added the dependent object for vrf";
        reference " 0.10.0.";
    }

    revision "2025-09-17" {
        description "Added dependentObject delete tag to delete the engine-id";
        reference " 0.9.0.";
    }

    revision "2024-10-10" {
        description "unihde snmp ent-ipi-iftable";
        reference " 0.8.2.";
    }

    revision "2024-10-03" {
        description "Renamed command to snmp ent-ipi-iftable";
        reference " 0.8.1.";
    }

    revision "2024-09-03" {
        description "Updated the helpstring of snmp-server contact and location";
        reference " 0.8.0.";
    }

    revision "2024-06-11" {
        description "Added support for user-defined VRF";
        reference " 0.7.0.";
    }

    revision "2024-03-20" {
        description "Added logical and physical interface tables command";
        reference " 0.6.5.";
    }

    revision "2023-08-28" {
        description "Added a new datatype for String without spaces";
        reference " 0.6.4.";
    }

    revision "2023-08-22" {
        description "Updated when tag to skip validations when snmp server is enabled";
        reference " 0.6.3.";
    }

    revision "2023-08-14" {
        description "Added skip yang flag in when tag to resolve compilation failure";
        reference " 0.6.2.";
    }

    revision "2023-08-10" {
        description "Added when tag to resolve DB sync issue";
        reference " 0.6.1.";
    }

    revision "2023-08-08" {
        description "Updated a dependentObject tag related to the smux port config";
        reference " 0.6.0.";
    }

    revision "2022-11-26" {
        description "Updated missing cli command for snmp enable cli";
        reference " 0.5.2.";
    }

    revision "2022-10-13" {
        description "Introduced a trigger to remove snmp_server table when the last view removed";
        reference " 0.5.1.";
    }

    revision "2022-09-28" {
        description "Updated when tag to update db when default instance is enabled";
        reference " 0.5.0.";
    }

    revision "2022-09-23" {
        description "Introduced when tag to update default config for ceragon";
        reference " 0.4.0.";
    }

    revision "2022-09-05" {
        description "Introduced disable-default attribute to resolve show running-config issue";
        reference " 0.3.0.";
    }

    revision "2022-08-29" {
        description "Updated the cli-command with feature";
        reference " 0.2.4.";
    }

    revision "2022-07-21" {
        description "Updated in its sub-module ipi-snmp-server-extended";
        reference " 0.2.3.";
    }

    revision "2022-06-01" {
        description "Updated the yang file with feature";
        reference " 0.2.2.";
    }

    revision "2021-12-15" {
        description "Some if-features included in some dependent objects between this module and ipi-snmp-server-extended";
        reference " 0.2.1.";
    }

    revision "2021-11-16" {
        description "Module restructuring";
        reference " 0.2.0.";
    }

    revision "2018-06-21" {
        description "Initial Version";
        reference " 0.1.0.";
    }

    grouping snmp-server-global-config {
        description
            "SNMP server global configuration";
        leaf system-contact  {
            if-feature feature-list:HAVE_SNMP_AGENT;
            type  cml-data-types:cml_line_t {
                length "1..1965";
            }
            description "Use this attribute to set the system contact information for the
                        device (sysContact object)";
        } // END of system-contact definition.

        leaf system-location  {
            if-feature feature-list:HAVE_SNMP_AGENT;
            type  cml-data-types:cml_line_t {
                length "1..1965";
            }
            description "Use this attribute to set the physical location information of the
                        device (sysLocation object)";
        } // END of system-location definition.

        leaf tcp-session-enabled  {
            if-feature feature-list:HAVE_SNMP_AGENT;
            type  empty;
            description "Use this attribute to start the SNMP agent daemon over TCP";
        } // END of tcp-session-enabled definition.

    } // END of snmp-server-global-config definition.
    grouping snmp-server-default-config {
        description
            "SNMP server disable default configuration";
        leaf disable-default-instance  {
            type  empty;
            description "Use this attribute to prevent default snmp instance from being enabled
                        at start up";
        } // END of disable-default-instance definition.

    } // END of snmp-server-default-config definition.
    grouping snmp-server-default-top {
        description
            "SNMP server disable default configuration";
        container default-instance {
            description
                "SNMP server default container configuration";
            container config {
                description
                    "Configuration data for SNMP server global configuration";
                uses snmp-server-default-config;
            } // END of config-container definition.
            container state {
                config false;
                description
                    "Operational state data for SNMP server global configuration";
                uses snmp-server-default-config;
            } // END of state-container definition.
        } // END of default-instance-container definition.
    } // END of snmp-server-default-top definition.
    grouping snmp-server-global-top {
        description
            "SNMP server global configuration";
        container global {
            description
                "SNMP server global container configuration";
            container config {
                description
                    "Configuration data for SNMP server global configuration";
                uses snmp-server-global-config;
            } // END of config-container definition.
            container state {
                config false;
                description
                    "Operational state data for SNMP server global configuration";
                uses snmp-server-global-config;
            } // END of state-container definition.
        } // END of global-container definition.
    } // END of snmp-server-global-top definition.
    grouping snmp-server-config {
        description
            "SNMP server configuration";
        leaf vrf-name  {
            if-feature feature-list:HAVE_VRF;
            type  leafref {
                path  "/ipi-network-instance:network-instances/ipi-network-instance:network-instance/ipi-vrf:vrf/ipi-vrf:config/ipi-vrf:vrf-name";
            }
            description "VRF name associated with this instance.";
        } // END of vrf-name definition.

        leaf enabled  {
            type  empty;
            description "Use this attribute to enable SNMP server";
        } // END of enabled definition.

    } // END of snmp-server-config definition.
    grouping snmp-server-top {
        description
            "SNMP server top configuration";

        list server {
            key "vrf-name";
            max-elements 1;
            description
                "Server list for SNMP configuration";
            leaf vrf-name  {
                type  leafref {
                    path  "../config/vrf-name";
                }
                description "VRF name associated with this instance.";
            } // END of vrf-name definition.

            container config {
                description
                    "Configuration data for SNMP Server";
                uses snmp-server-config;
            } // END of config-container definition.
            container state {
                config false;
                description
                    "Operational state data for SNMP Server";
                uses snmp-server-config;
            } // END of state-container definition.
            uses snmp-server-global-top;
        } // End of server-list
    } // END of snmp-server-top definition.
    grouping snmp-custom-top {
        description
            "Grouping for SNMP config objects.";
        leaf ent-ipi-iftable  {
            if-feature feature-list:HAVE_SNMP_AGENT;
            type  empty;
            description "Use this attribute to enable separate logical/physical interface
                        tables";
        } // END of ent-ipi-iftable definition.

    } // END of snmp-custom-top definition.

    grouping  servers-grouping {
    description
        "Container for SNMP servers configuration";
    container servers {
        description
            "Container for SNMP servers configuration";
        uses snmp-server-top;
        uses snmp-server-default-top;
    } // END of servers-container definition.
    } // END of servers-grouping definition.

    grouping  custom-grouping {
    description
        "Grouping for custom SNMP settings.";
    container custom {
        description
            "Grouping for custom SNMP settings.";
        container config {
            description
                "This container defines custom snmp configuration.";
            uses snmp-custom-top;
        } // END of config-container definition.
        container state {
            config false;
            description
                "This container defines snmp Operational states.";
            uses snmp-custom-top;
        } // END of state-container definition.
    } // END of custom-container definition.
    } // END of custom-grouping definition.

    augment /ipi-snmp:snmp {
        if-feature feature-list:HAVE_SNMP_AGENT;
        description
            "Container for SNMP servers configuration";
        uses servers-grouping;
    }

    uses custom-grouping;

}
