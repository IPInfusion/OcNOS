/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-network-services-manager-types.yang
*
*/

module ipi-network-services-manager-types {

    yang-version 1.1;

    namespace   "http://www.ipinfusion.com/yang/ocnos/ipi-network-services-manager-types";

    prefix "ipi-network-services-manager-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "network-services-manager datatypes";


    revision "2025-12-23" {
        description "Enhancement of MPLS debug, adding two new filters related to the RSVP";
        reference " 0.3.2.";
    }

    revision "2025-08-25" {
        description " Introduced new NSM debug options 'debug nsm evpn' ";
        reference " 0.3.1.";
    }

    revision "2025-08-12" {
        description "Updated the value for debug nsm mpls";
        reference " 0.3.0.";
    }

    revision "2024-07-24" {
        description "Enhancement of debug nsm mpls command";
        reference " 0.2.0.";
    }

    revision "2022-09-30" {
        description "Implementation of debug lbd CLI";
        reference " 0.5.0.";
    }

    revision "2022-09-05" {
        description "Implementation of debug hsl CLI in exec mode";
        reference " 0.4.0.";
    }

    revision "2022-08-30" {
        description "debug hsl change";
        reference " 0.3.0.";
    }

    revision "2022-08-10" {
        description "Debug hierarchy change";
        reference " 0.2.0.";
    }

    revision "2022-08-05" {
        description "implementation of debug hsl CLI";
        reference " 0.1.1.";
    }

    revision "2022-06-24" {
        description "db-synce issue fix JIRA-58792";
        reference " 0.1.0.";
    }

    revision "2022-06-01" {
        description "Updated the yang file with feature";
        reference "Initial Version";
    }

    revision "2021-09-03" {
        description "Update descriptions of attribute";
        reference "Initial Version";
    }

    revision "2021-07-30" {
        description "Initial Version";
        reference "Initial Version";
    }



    typedef  nsm_debug_t {
        type bits {
            bit addressmonitor {
                position 1;
                if-feature feature-list:NOT_PNE_VERSION_3_7;
                if-feature feature-list:NOT_PNE_VERSION_6_9;
                description "Enable Monitor adddress netlink";
            }
            bit bfd {
                position 2;
                if-feature feature-list:HAVE_BFD;
                description "Bidirectional Forwarding Detection (BFD)";
            }
            bit events {
                position 3;
                description "NSM events";
            }
            bit hal-events {
                position 4;
                if-feature feature-list:HAVE_HAL;
                if-feature feature-list:NOT_PNE_VERSION_6_9;
                if-feature feature-list:NOT_HAVE_SWFWDR;
                description " Hardware Abstraction Layer,NSM events";
            }
            bit hal-ipc {
                position 5;
                if-feature feature-list:HAVE_ASYNC;
                description "Hardware Abstraction Layer,Async Debugging";
            }
            bit linkmonitor {
                position 6;
                description "Enable Monitor link netlink";
            }
            bit packet-recv {
                position 9;
                description "NSM packets,NSM receive packets";
            }
            bit packet-recv-detail {
                position 10;
                description "NSM packets,NSM receive packets,Detailed information display";
            }
            bit packet-send {
                position 11;
                description "NSM packets,NSM receive packets";
            }
            bit packet-send-detail {
                position 12;
                description "NSM packets,NSM receive packets,Detailed information display";
            }
            bit ha {
                position 13;
                if-feature feature-list:HAVE_HA;
                description "NSM High Availability";
            }
            bit ha-all {
                position 14;
                if-feature feature-list:HAVE_HA;
                description "NSM High Availability,All NSM High Availability events";
            }
            bit vxlan {
                position 15;
                if-feature feature-list:HAVE_VXLAN;
                description "VXLAN";
            }
            bit trill {
                position 16;
                if-feature feature-list:HAVE_TRILLD;
                description "TRILL";
            }
            bit ipsec {
                position 17;
                if-feature feature-list:HAVE_IPSEC;
                description "IPSEC";
            }
            bit kernel {
                position 18;
                if-feature feature-list:HAVE_SWFWDR;
                description "NSM kernel";
            }
            bit mpls {
                position 19;
                if-feature feature-list:HAVE_MPLS;
                description "NSM mpls";
            }
            bit mpls-sr-ftn {
                position 21;
                if-feature feature-list:HAVE_MPLS;
                description "NSM mpls,NSM mpls sr,NSM mpls ftn";
            }
            bit mpls-sr-ilm {
                position 22;
                if-feature feature-list:HAVE_MPLS;
                description "NSM mpls,NSM mpls sr,NSM mpls ilm";
            }
            bit mpls-ldp-ftn {
                position 23;
                if-feature feature-list:HAVE_MPLS;
                description "NSM mpls,NSM mpls ldp,NSM mpls ftn";
            }
            bit mpls-ldp-ilm {
                position 24;
                if-feature feature-list:HAVE_MPLS;
                description "NSM mpls,NSM mpls ldp,NSM mpls ilm";
            }
            bit evpn {
                position 25;
                if-feature feature-list:HAVE_BGP_EVPN;
                description "NSM EVPN";
            }
            bit mpls-rsvp-ftn {
                position 26;
                if-feature feature-list:HAVE_MPLS;
                description "NSM mpls,NSM mpls rsvp,NSM mpls ftn";
            }
            bit mpls-rsvp-ilm {
                position 27;
                if-feature feature-list:HAVE_MPLS;
                description "NSM mpls,NSM mpls rsvp,NSM mpls ilm";
            }
        }
        description "type definition for NSM_DEBUG_T";
    }

    typedef  nsm_pkt_mgr_debug_t {
        type bits {
            bit l2-protocol-cfm {
                position 2;
                description "Layer-2,Protocol,Ethernet Connectivity Fault Management Protocol (CFM)";
            }
            bit l2-protocol-eapol {
                position 3;
                description "Layer-2,Protocol,Extensible Authentication Protocol over LAN (EAPoL)";
            }
            bit l2-protocol-efm {
                position 4;
                description "Layer-2,Protocol,Ethernet in the First Mile(EFM) OAM";
            }
            bit l2-protocol-igmp-snoop {
                position 5;
                description "Layer-2,Protocol,Internet Group Management Protocol (IGMP) snooping";
            }
            bit l2-protocol-lacp {
                position 6;
                description "Layer-2,Protocol,Link Aggregation Control Protocol (LACP)";
            }
            bit l2-protocol-lldp {
                position 7;
                description "Layer-2,Protocol,Link Layer Discovery Protocol (LLDP)";
            }
            bit l2-protocol-mldp-snoop {
                position 8;
                description "Layer-2,Protocol,Multicast Listener Discovery (MLD) snooping";
            }
            bit l2-protocol-mstp {
                position 9;
                description "Layer-2,Protocol,Multiple Spanning Tree Protocol (MSTP)";
            }
            bit l2-protocol-ptp {
                position 10;
                description "Layer-2,Protocol,Precision Time Protocol (PTP)";
            }
        }
        description "type definition for NSM_PKT_MGR_DEBUG_T";
    }

    typedef  nsm_exec_debug_t {
        type bits {
            bit addressmonitor {
                position 1;
                if-feature feature-list:NOT_PNE_VERSION_3_7;
                if-feature feature-list:NOT_PNE_VERSION_6_9;
                description "Enable Monitor adddress netlink";
            }
            bit bfd {
                position 2;
                if-feature feature-list:HAVE_BFD;
                description "Bidirectional Forwarding Detection (BFD)";
            }
            bit events {
                position 3;
                description "NSM events";
            }
            bit hal-events {
                position 4;
                if-feature feature-list:HAVE_HAL;
                if-feature feature-list:NOT_PNE_VERSION_6_9;
                if-feature feature-list:NOT_HAVE_SWFWDR;
                description " Hardware Abstraction Layer,NSM events";
            }
            bit hal-ipc {
                position 5;
                if-feature feature-list:HAVE_ASYNC;
                description "Hardware Abstraction Layer,Async Debugging";
            }
            bit linkmonitor {
                position 6;
                description "Enable Monitor link netlink";
            }
            bit packet-recv {
                position 9;
                description "NSM packets,NSM receive packets";
            }
            bit packet-recv-detail {
                position 10;
                description "NSM packets,NSM receive packets,Detailed information display";
            }
            bit packet-send {
                position 11;
                description "NSM packets,NSM receive packets";
            }
            bit packet-send-detail {
                position 12;
                description "NSM packets,NSM receive packets,Detailed information display";
            }
            bit ha {
                position 13;
                if-feature feature-list:HAVE_HA;
                description "NSM High Availability";
            }
            bit ha-all {
                position 14;
                if-feature feature-list:HAVE_HA;
                description "NSM High Availability,All NSM High Availability events";
            }
            bit vxlan {
                position 15;
                if-feature feature-list:HAVE_VXLAN;
                description "VXLAN";
            }
            bit trill {
                position 16;
                if-feature feature-list:HAVE_TRILLD;
                description "TRILL";
            }
            bit ipsec {
                position 17;
                if-feature feature-list:HAVE_IPSEC;
                description "IPSEC";
            }
            bit mpls {
                position 19;
                if-feature feature-list:HAVE_MPLS;
                description "NSM mpls";
            }
            bit mpls-sr-ftn {
                position 21;
                if-feature feature-list:HAVE_MPLS;
                description "NSM mpls,NSM mpls sr,NSM mpls ftn";
            }
            bit mpls-sr-ilm {
                position 22;
                if-feature feature-list:HAVE_MPLS;
                description "NSM mpls,NSM mpls sr,NSM mpls ilm";
            }
            bit mpls-ldp-ftn {
                position 23;
                if-feature feature-list:HAVE_MPLS;
                description "NSM mpls,NSM mpls ldp,NSM mpls ftn";
            }
            bit mpls-ldp-ilm {
                position 24;
                if-feature feature-list:HAVE_MPLS;
                description "NSM mpls,NSM mpls ldp,NSM mpls ilm";
            }
            bit evpn {
                position 25;
                if-feature feature-list:HAVE_BGP_EVPN;
                description "NSM EVPN";
            }
            bit mpls-rsvp-ftn {
                position 26;
                if-feature feature-list:HAVE_MPLS;
                description "NSM mpls,NSM mpls rsvp,NSM mpls ftn";
            }
            bit mpls-rsvp-ilm {
                position 27;
                if-feature feature-list:HAVE_MPLS;
                description "NSM mpls,NSM mpls rsvp,NSM mpls ilm";
            }
        }
        description "type definition for NSM_EXEC_DEBUG_T";
    }

    typedef  hsl_debug_module_t {
        type enumeration {
            enum general {
                value 1;
                description "general logs";
            }
            enum ifmgr {
                value 2;
                description "Interface management logs";
            }
            enum bridge {
                value 3;
                description "Bridge management logs";
            }
            enum msg {
                value 4;
                description "HAL-HSL message logs";
            }
            enum fib {
                value 5;
                description "FIB management";
            }
            enum fdb {
                value 6;
                description "FDB management";
            }
            enum devdrv {
                value 7;
                description "HSL helper Configuration";
            }
            enum pktdrv {
                value 8;
                description "Packet driver logs";
            }
            enum platform {
                value 9;
                description "Platform(Hardware) logs";
            }
            enum pbr {
                value 10;
                description "PBR logs";
            }
            enum bfd {
                value 11;
                if-feature feature-list:HAVE_BFD;
                description "Bidirectional Forwarding Detection";
            }
            enum lacp {
                value 12;
                description "LACP Configuration";
            }
            enum qos {
                value 13;
                if-feature feature-list:HAVE_QOS;
                description "QOS Configuration";
            }
            enum helper {
                value 14;
                description "HSL helper Configuration";
            }
            enum rbridge {
                value 16;
                description "RBridge management logs";
            }
            enum nvo {
                value 17;
                description "NVO (VXLAN/NVGRE trace";
            }
            enum ofl {
                value 18;
                description "OFLD trace";
            }
            enum mlag {
                value 19;
                description "MLAG Configuration";
            }
            enum mpls {
                value 20;
                if-feature feature-list:HAVE_MPLS;
                description "MPLS logs";
            }
            enum srv6 {
                value 21;
                description "SRV6 logs";
            }
            enum ptp {
                value 22;
                description "PTP logs";
            }
            enum extphy {
                value 23;
                description "External phy logs";
            }
        }
        description "type definition for HSL_DEBUG_MODULE_T";
    }

    typedef  hsl_debug_level_t {
        type bits {
            bit info {
                position 0;
                description "General system information profiling";
            }
            bit debug {
                position 1;
                description "Debug trace";
            }
            bit warn {
                position 2;
                description "warnings";
            }
            bit error {
                position 3;
                description "Recovarable error";
            }
            bit fatal {
                position 4;
                description "Fatal failure occured process/system has to terminate/reboot";
            }
            bit admin {
                position 5;
                description "Administrative critical information";
            }
            bit counter {
                position 6;
                description "Counters Debugging";
            }
            bit pkt {
                position 7;
                description "packets Debugging";
            }
        }
        description "type definition for HSL_DEBUG_LEVEL_T";
    }

    typedef  lbd_debug_t {
        type bits {
            bit tx {
                position 1;
                description "LBD transmit packets";
            }
            bit rx {
                position 2;
                description "LBD recieve packets";
            }
            bit event {
                position 3;
                description "LBD event";
            }
            bit info {
                position 4;
                description "LBD info";
            }
        }
        description "type definition for LBD_DEBUG_T";
    }

    typedef  nsm_pktmgr_statistics_type_t {
        type enumeration {
            enum stats {
                value 1;
                description "STATISTICS";
            }
            enum pkt-errors {
                value 2;
                description "PACKET ERROR STATS";
            }
        }
        description "type definition for NSM_PKTMGR_STATISTICS_TYPE_T";
    }

}
