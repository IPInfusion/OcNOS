/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-sys-service-mgmt-types.yang
*
*/

module ipi-sys-service-mgmt-types {

    yang-version 1.1;

    namespace   "http://www.ipinfusion.com/yang/ocnos/ipi-sys-service-mgmt-types";

    prefix "ipi-sys-service-mgmt-types";

    organization
        "IP Infusion Inc.";

    contact
        "Address: 3965 Freedom Circle, Suite 200, Santa Clara, CA 95054
         Phone: +1 408-400-1900
         E-mail: support@ipinfusion.com
         Web: http://www.ipinfusion.com/";

    description
        "sys-service-mgmt manages the special services of the device";


    revision "2025-06-27" {
        description "Created new type for updating system config backup content";
        reference " 1.0.0.";
    }



    typedef  system_backup_content_type_t {
        type enumeration {
            enum config {
                value 1;
                description "Backup config only";
            }
            enum all {
                value 2;
                description "Backup config + installer + local license";
            }
        }
        description "type definition for SYSTEM_BACKUP_CONTENT_TYPE_T";
    }

}
