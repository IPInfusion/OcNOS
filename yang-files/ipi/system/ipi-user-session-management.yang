/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-user-session-management.yang
*
*/

module ipi-user-session-management {

    yang-version 1.1;

    namespace   "http://www.ipinfusion.com/yang/ocnos/ipi-user-session-management";

    prefix "ipi-user-session-management";

    import cml-data-types {
        prefix cml-data-types;
        revision-date 2026-05-15;
    }

    import ipi-user-session-management-types {
        prefix ipi-user-session-management-types;
        revision-date 2022-06-01;
    }

    import feature-list {
        prefix feature-list;
        revision-date 2026-09-15;
    }

    include ipi-user-session { revision-date 2022-08-09;}
    include ipi-max-session-cli { revision-date 2025-07-28;}
    organization
        "IP Infusion Inc.";

    contact
        "Address: 3965 Freedom Circle, Suite 200, Santa Clara, CA 95054
         Phone: +1 408-400-1900
         E-mail: support@ipinfusion.com
         Web: http://www.ipinfusion.com/";

    description
        "This module provides user session management configuration";


    revision "2025-07-28" {
        description " Added when tag for max-session-limit";
        reference " 0.8.0.";
    }

    revision "2025-02-11" {
        description "Created a new module ipi-max-session-cli belonging to ipi-user-session-management";
        reference " 0.7.0.";
    }

    revision "2024-09-11" {
        description "Updated the cli mode prompt command";
        reference " 0.6.0.";
    }

    revision "2024-06-04" {
        description "Updated privilege-level help string";
        reference " 0.5.0.";
    }

    revision "2023-07-07" {
        description "Updated timeout container as presence";
        reference " 0.4.2.";
    }

    revision "2022-12-20" {
        description "Updated description tag";
        reference " 0.4.1.";
    }

    revision "2022-11-16" {
        description "Updated missing cliprependstr tags";
        reference " 0.4.0.";
    }

    revision "2022-08-09" {
        description "Added skip SMI generation for user-session sub-module";
        reference " 0.3.4.";
    }

    revision "2022-06-18" {
        description "Added Remote-IP leaf for Netconf clients /user-sessions hierarchy";
        reference " 0.3.3.";
    }

    revision "2022-06-01" {
        description "Updated the yang file with feature";
        reference " 0.3.2.";
    }

    revision "2022-02-02" {
        description "Grouping names changed for line vty timeout.";
        reference " 0.3.1.";
    }

    revision "2022-01-11" {
        description "New submodule added: ipi-user-session.";
        reference " 0.3.0.";
    }

    revision "2021-11-16" {
        description "Module restructuring";
        reference " 0.2.0.";
    }

    revision "2018-06-21" {
        description "Initial Version";
        reference " 0.1.0.";
    }

    grouping line-common-timeout-config {
        description
            "Common timeout configuration for line";
        leaf minutes  {
            type  uint32 {
                 range "0..35791"  {
                    description "0..35791: Supported range 0 - 35791";
                 }
            }
            units "minutes";
            mandatory true;
            description "Attribute used to set line timeout in minutes. The default is 10
                        minutes.";
        } // END of minutes definition.

        leaf seconds  {
            type  uint32 {
                 range "0..2147483"  {
                    description "0..2147483: Supported range 0 - 2147483";
                 }
            }
            units "seconds";
            description "Attribute used to set line timeout in seconds. The default is 0.";
        } // END of seconds definition.

    } // END of line-common-timeout-config definition.
    grouping line-vty-timeout-top {
        description
            "Line vty timeout top level configuration for line";
        container timeout {
            description
                "Container that holds information about line timeout";
            container config {
                presence "yes";
                description
                    "Configuration data for line timeout";
                uses line-common-timeout-config;
            } // END of config-container definition.
            container state {
                config false;
                description
                    "Operational state data for line timeout";
                uses line-common-timeout-config;
            } // END of state-container definition.
        } // END of timeout-container definition.
    } // END of line-vty-timeout-top definition.
    grouping line-console-timeout-top {
        description
            "Line console timeout top level configuration";
        container timeout {
            description
                "Container that holds information about line timeout";
            container config {
                presence "yes";
                description
                    "Configuration data for line timeout";
                uses line-common-timeout-config;
            } // END of config-container definition.
            container state {
                config false;
                description
                    "Operational state data for line timeout";
                uses line-common-timeout-config;
            } // END of state-container definition.
        } // END of timeout-container definition.
    } // END of line-console-timeout-top definition.
    grouping line-common-config {
        description
            "Common line configuration";
        leaf privilege-level  {
            type  uint8 {
                 range "1..16"  {
                    description "1..16:Not Feature : HAVE_VR  Supported range 1 - 15Feature : HAVE_VR
                            Supported range 1 - 16";
                 }
            }
            description "Attribute used to set line privilege level.";
        } // END of privilege-level definition.

        leaf command-history-max-limit  {
            type  uint32 {
                 range "0..2147483647"  {
                    description "0..2147483647: Supported range 0 - 2147483647";
                 }
            }
            description "Attribute used to set line maximum limit to history commands.";
        } // END of command-history-max-limit definition.

    } // END of line-common-config definition.
    grouping line-vty-config {
        description
            "Line vty configuration";
        leaf vty-id  {
            type  cml-data-types:cml_range_t;
            description "Attribute used to set line vty identification.";
        } // END of vty-id definition.

    } // END of line-vty-config definition.
    grouping line-vty-top {
        description
            "Line vty top level configuration";
        container line-vty {
            description
                "Top container for line-vty configuration";

            list vty {
                key "vty-id";
                description
                    "vty list";
                leaf vty-id  {
                    type  leafref {
                        path  "../config/vty-id";
                    }
                    description "Attribute used to set line vty identifcation.";
                } // END of vty-id definition.

                container config {
                    description
                        "Configuration data for vty line";
                    uses line-vty-config;
                    uses line-common-config;
                } // END of config-container definition.
                container state {
                    config false;
                    description
                        "Operational state data for vty line";
                    uses line-vty-config;
                    uses line-common-config;
                } // END of state-container definition.
                uses line-vty-timeout-top;
            } // End of vty-list
        } // END of line-vty-container definition.
    } // END of line-vty-top definition.
    grouping line-console-config {
        description
            "Line console configuration";
        leaf console-id  {
            type  ipi-user-session-management-types:line_console_id_t;
            default "0";
            description "Attribute used to set line console identifcation.";
        } // END of console-id definition.

    } // END of line-console-config definition.
    grouping line-console-top {
        description
            "Line console top level configuration";
        container line-console {
            description
                "Top container for line-console configuration";

            list console {
                key "console-id";
                max-elements 1;
                description
                    "console list";
                leaf console-id  {
                    type  leafref {
                        path  "../config/console-id";
                    }
                    description "Attribute used to set line console identifcation.";
                } // END of console-id definition.

                container config {
                    description
                        "Configuration data for console line";
                    uses line-console-config;
                    uses line-common-config;
                } // END of config-container definition.
                container state {
                    config false;
                    description
                        "Operational state data for console line";
                    uses line-console-config;
                    uses line-common-config;
                } // END of state-container definition.
                uses line-console-timeout-top;
            } // End of console-list
        } // END of line-console-container definition.
    } // END of line-console-top definition.

    grouping  user-session-grouping {
    description
        "Container for all user-sessions configuration";
    container user-session {
        if-feature feature-list:HAVE_IMI;
        description
            "Container for all user-sessions configuration";
        uses line-console-top;
        uses line-vty-top;
        uses sessions-grouping;
        uses max-session-limit-grouping;
    } // END of user-session-container definition.
    } // END of user-session-grouping definition.

    uses user-session-grouping;

    rpc clear-line {
        if-feature feature-list:HAVE_IMI;
        description "Use this RPC to clear the terminal line";
        input  {
            leaf line-name  {
                type string {
                    length "1..64";
                }
                mandatory true;
                description "line name to be cleared";
            }
        }
    }

}
