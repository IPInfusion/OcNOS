/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-network-services-manager.yang
*
*/

module ipi-network-services-manager {

    yang-version 1.1;

    namespace   "http://www.ipinfusion.com/yang/ocnos/ipi-network-services-manager";

    prefix "ipi-network-services-manager";

    import ipi-network-services-manager-types {
        prefix ipi-network-services-manager-types;
        revision-date 2025-12-23;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module provides user with the possibility of configuring debug
                options for Network Services Manager and Packet Manager";


    revision "2026-01-12" {
        description "Changed module value type from 'int' to 'u_int8_t' form hsl terminal debug on/off";
        reference " 0.12.4.";
    }

    revision "2025-12-23" {
        description "Enhancement of MPLS debug, adding two new filters related to the RSVP";
        reference " 0.12.3.";
    }

    revision "2025-09-19" {
        description "Change srlg helpstring";
        reference " 0.12.2.";
    }

    revision "2025-08-25" {
        description " Introduced new NSM debug options 'debug nsm evpn'";
        reference " 0.12.1.";
    }

    revision "2025-08-12" {
        description "Updated the value for debug nsm mpls";
        reference " 0.12.0.";
    }

    revision "2024-11-28" {
        description "Updated the default value of attribute options";
        reference " 0.11.1.";
    }

    revision "2024-08-27" {
        description "Added no delete api flag in hsl container";
        reference " 0.11.0.";
    }

    revision "2024-07-24" {
        description "Enhancement of debug nsm mpls command";
        reference " 0.2.0.";
    }

    revision "2024-04-08" {
        description "Added clear nsm server ipc-stats command";
        reference " 0.10.0.";
    }

    revision "2023-01-16" {
        description "Added When tag for no-debug-all command";
        reference " 0.9.0.";
    }

    revision "2022-12-07" {
        description "Added the cliprependstr to the prependstr lbd";
        reference " 0.8.0.";
    }

    revision "2022-11-29" {
        description "Addressed make cmlgen warnings";
        reference " 0.7.0.";
    }

    revision "2022-10-17" {
        description "Added if-feature HAVE_HAL for deubug hsl ";
        reference " 0.5.0.";
    }

    revision "2022-09-30" {
        description "Implementation of debug lbd CLI";
        reference " 0.6.0.";
    }

    revision "2022-09-07" {
        description "added if-feature HAVE_USER_HSL for debug hsl data model";
        reference " 0.2.2.";
    }

    revision "2022-09-05" {
        description "Implementation of debug hsl CLI in exec mode";
        reference " 0.4.0.";
    }

    revision "2022-08-30" {
        description "debug hsl change";
        reference " 0.2.1.";
    }

    revision "2022-08-10" {
        description "Debug hierarchy change";
        reference " 0.2.0.";
    }

    revision "2022-08-05" {
        description "implementation of debug hsl CLI";
        reference " 0.1.1.";
    }

    revision "2022-06-24" {
        description "db-synce issue fix JIRA-58792";
        reference " 0.1.0.";
    }

    revision "2022-06-01" {
        description "Updated the yang file with feature";
        reference "Initial Version";
    }

    revision "2021-11-21" {
        description "Moved L2 depenedecies under HAVE_L2";
        reference "Initial Version";
    }

    revision "2021-09-03" {
        description "Update descriptions of attribute";
        reference "Initial Version";
    }

    revision "2021-07-30" {
        description "Initial Version";
        reference "Initial Version";
    }

    grouping net-serv-mgr-debug-term-pktmgr-state {
        description
            "net-serv-mgr-debug-term-pktmgr-state";
        leaf terminal-debug-status  {
            if-feature feature-list:HAVE_L2;
            type  ipi-network-services-manager-types:nsm_pkt_mgr_debug_t;
            description "Terminal debug for pkt-mgr debug";
        } // END of terminal-debug-status definition.

    } // END of net-serv-mgr-debug-term-pktmgr-state definition.
    grouping net-serv-mgr-debug-term-nsm-state {
        description
            "net-serv-mgr-debug-term-nsm-state";
        leaf terminal-debug-status  {
            type  ipi-network-services-manager-types:nsm_debug_t;
            description "Terminal debug for nsm debug";
        } // END of terminal-debug-status definition.

    } // END of net-serv-mgr-debug-term-nsm-state definition.
    grouping net-serv-mgr-debug-term-lbd-state {
        description
            "net-serv-mgr-debug-term-lbd-state";
        leaf debug-options-lbd  {
            if-feature feature-list:HAVE_LBD;
            type  ipi-network-services-manager-types:lbd_debug_t;
            description "Terminal debug for LBD debug";
        } // END of debug-options-lbd definition.

    } // END of net-serv-mgr-debug-term-lbd-state definition.
    grouping net-serv-mgr-terminal-debug-top {
        description
            "net-serv-mgr-terminal-debug-top";
        container terminal {
            config false;
            description
                "Container for terminal debug";
            container nsm {
                config false;
                description
                    "Container for nsm terminal debug";
                container state {
                    config false;
                    description
                        "Operational state data";
                    uses net-serv-mgr-debug-term-nsm-state;
                } // END of state-container definition.
            } // END of nsm-container definition.
            container pkt-mgr {
                config false;
                description
                    "Container for pkt-mgr terminal debug";
                container state {
                    config false;
                    description
                        "Operational state data";
                    uses net-serv-mgr-debug-term-pktmgr-state;
                } // END of state-container definition.
            } // END of pkt-mgr-container definition.
            container lbd {
                if-feature feature-list:HAVE_LBD;
                config false;
                description
                    "Container for LBD terminal debug";
                container state {
                    config false;
                    description
                        "Operational state data";
                    uses net-serv-mgr-debug-term-lbd-state;
                } // END of state-container definition.
            } // END of lbd-container definition.
        } // END of terminal-container definition.
    } // END of net-serv-mgr-terminal-debug-top definition.
    grouping net-serv-mgr-debug-lbd-config {
        description
            "net-serv-mgr-debug-lbd-config";
        leaf debug-options  {
            if-feature feature-list:HAVE_LBD;
            type  ipi-network-services-manager-types:lbd_debug_t;
            description "Use this attribute to debug LBD packet";
        } // END of debug-options definition.

    } // END of net-serv-mgr-debug-lbd-config definition.
    grouping net-serv-mgr-debug-lbd-top {
        description
            "net-serv-mgr-debug-lbd-top";
        container lbd {
            if-feature feature-list:HAVE_LBD;
            description
                "Container that holds LBD debug data";
            container config {
                description
                    "Configuration data for LBD debug data";
                uses net-serv-mgr-debug-lbd-config;
            } // END of config-container definition.
            container state {
                config false;
                description
                    "Operational state data for LBD debug data";
                uses net-serv-mgr-debug-lbd-config;
            } // END of state-container definition.
        } // END of lbd-container definition.
    } // END of net-serv-mgr-debug-lbd-top definition.
    grouping net-serv-mgr-debug-pktmgr-config {
        description
            "net-serv-mgr-debug-pktmgr-config";
        leaf options  {
            if-feature feature-list:HAVE_L2;
            type  ipi-network-services-manager-types:nsm_pkt_mgr_debug_t;
            description "Use this attribute to debug vlan packet";
        } // END of options definition.

    } // END of net-serv-mgr-debug-pktmgr-config definition.
    grouping net-serv-mgr-debug-pktmgr-top {
        description
            "net-serv-mgr-debug-pktmgr-top";
        container pkt-mgr {
            description
                "Container that holds pkt-mgr debug data";
            container config {
                description
                    "Configuration data for pkt-mgr debug data";
                uses net-serv-mgr-debug-pktmgr-config;
            } // END of config-container definition.
            container state {
                config false;
                description
                    "Operational state data for pkt-mgr debug data";
                uses net-serv-mgr-debug-pktmgr-config;
            } // END of state-container definition.
        } // END of pkt-mgr-container definition.
    } // END of net-serv-mgr-debug-pktmgr-top definition.
    grouping net-serv-mgr-debug-nsm-config {
        description
            "net-serv-mgr-debug-nsm-config";
        leaf options  {
            type  ipi-network-services-manager-types:nsm_debug_t;
            description "Use this attribute to debug nsm";
        } // END of options definition.

    } // END of net-serv-mgr-debug-nsm-config definition.
    grouping net-serv-mgr-debug-nsm-top {
        description
            "net-serv-mgr-debug-nsm-top";
        container nsm {
            description
                "Container that holds nsm debug data";
            container config {
                description
                    "Configuration data for nsm debug data";
                uses net-serv-mgr-debug-nsm-config;
            } // END of config-container definition.
            container state {
                config false;
                description
                    "Operational state data for nsm debug data";
                uses net-serv-mgr-debug-nsm-config;
            } // END of state-container definition.
        } // END of nsm-container definition.
    } // END of net-serv-mgr-debug-nsm-top definition.
    grouping net-serv-mgr-debug-hsl-config {
        description
            "Grouping for debug HSL config objects";
        leaf module-name  {
            type  ipi-network-services-manager-types:hsl_debug_module_t;
            description "Use this Attribute to set debug HSL module";
        } // END of module-name definition.

        leaf level  {
            type  ipi-network-services-manager-types:hsl_debug_level_t;
            mandatory true;
            description "Use this Attribute to set debug level for HSL module";
        } // END of level definition.

    } // END of net-serv-mgr-debug-hsl-config definition.
    grouping net-serv-mgr-debug-hsl-top {
        description
            "Top-level container for debug HSL module";
        container hsl {
            if-feature feature-list:HAVE_USER_HSL;
            description
                "Container that holds HSL debug data";

            list hsl-module {
                key "module-name";
                description
                    "objectlist that holds HSL debug data";
                leaf module-name  {
                    type  leafref {
                        path  "../config/module-name";
                    }
                    description "Use this attribute to set debug HSL module";
                } // END of module-name definition.

                container config {
                    description
                        "Configuration data for HSL debug data";
                    uses net-serv-mgr-debug-hsl-config;
                } // END of config-container definition.
                container state {
                    config false;
                    description
                        "Operational state data for HSL debug data";
                    uses net-serv-mgr-debug-hsl-config;
                } // END of state-container definition.
            } // End of hsl-module-list
        } // END of hsl-container definition.
    } // END of net-serv-mgr-debug-hsl-top definition.
    grouping net-serv-mgr-debug-top {
        description
            "net-serv-mgr-debug-top";
        container debug {
            description
                "Container that stores all debug data for network services manager";
            uses net-serv-mgr-debug-nsm-top;
            uses net-serv-mgr-debug-pktmgr-top;
            uses net-serv-mgr-debug-hsl-top;
            uses net-serv-mgr-debug-lbd-top;
            uses net-serv-mgr-terminal-debug-top;
        } // END of debug-container definition.
    } // END of net-serv-mgr-debug-top definition.

    grouping  network-services-manager-grouping {
    description
        "Container for all data related to network services manager";
    container network-services-manager {
        description
            "Container for all data related to network services manager";
        uses net-serv-mgr-debug-top;
    } // END of network-services-manager-container definition.
    } // END of network-services-manager-grouping definition.

    uses network-services-manager-grouping;

    rpc nsm-terminal-debug-on {
        description "Enable nsm terminal debug categories";
        input  {
            leaf terminal-debug-options  {
                type ipi-network-services-manager-types:nsm_exec_debug_t;
                mandatory true;
                description "Bitmap representing nsm debug categories";
            }
        }
    }

    rpc nsm-terminal-debug-off {
        description "Disable nsm terminal debug categories";
        input  {
            leaf terminal-debug-options  {
                type ipi-network-services-manager-types:nsm_exec_debug_t;
                mandatory true;
                description "Bitmap representing nsm debug categories";
            }
        }
    }

    rpc hsl-terminal-debug-on {
        if-feature feature-list:NOT_HAVE_SWFWDR;
        if-feature feature-list:HAVE_HAL;
        description "Enable HSL terminal debug categories";
        input  {
            leaf module-name  {
                type ipi-network-services-manager-types:hsl_debug_module_t;
                mandatory true;
                description "Use this Attribute to enable terminal debug for a HSL module";
            }
            leaf level  {
                type ipi-network-services-manager-types:hsl_debug_level_t;
                mandatory true;
                description "Use this Attribute to enable terminal  debug level for HSL module";
            }
        }
    }

    rpc hsl-terminal-debug-off {
        if-feature feature-list:NOT_HAVE_SWFWDR;
        if-feature feature-list:HAVE_HAL;
        description "Disable HSL terminal debug categories";
        input  {
            leaf module-name  {
                type ipi-network-services-manager-types:hsl_debug_module_t;
                mandatory true;
                description "Use this Attribute to disable terminal debug for a  HSL module";
            }
            leaf level  {
                type ipi-network-services-manager-types:hsl_debug_level_t;
                mandatory true;
                description "Use this Attribute to disable terminal  debug level for HSL module";
            }
        }
    }

    rpc pktmgr-terminal-debug-on {
        if-feature feature-list:HAVE_L2;
        description "Enable pktmgr terminal debug categories";
        input  {
            leaf terminal-debug-options  {
                type ipi-network-services-manager-types:nsm_pkt_mgr_debug_t;
                mandatory true;
                description "Bitmap representing pktmgr debug categories";
            }
        }
    }

    rpc pktmgr-terminal-debug-off {
        if-feature feature-list:HAVE_L2;
        description "Disable pktmgr terminal debug categories";
    }

    rpc lbd-terminal-debug-on {
        if-feature feature-list:HAVE_LBD;
        description "Enable LBD terminal debug categories";
        input  {
            leaf debug-options  {
                type ipi-network-services-manager-types:lbd_debug_t;
                mandatory true;
                description "Bitmap representing LBD debug categories";
            }
        }
    }

    rpc lbd-terminal-debug-off {
        if-feature feature-list:HAVE_LBD;
        description "Disable LBD terminal debug categories";
        input  {
            leaf debug-options  {
                type ipi-network-services-manager-types:lbd_debug_t;
                mandatory true;
                description "Bitmap representing LBD debug categories";
            }
        }
    }

    rpc pktmgr-debug-statistics-enable {
        description "Used to enable pktmgr debug statistics";
    }

    rpc pktmgr-debug-statistics-disable {
        description "Used to disable pktmgr debug statistics";
    }

    rpc pktmgr-debug-statistics-get {
        description "Get pktmgr statistics from HW and put on log";
    }

    rpc pktmgr-debug-error-statistics-get {
        description "Get pktmgr debug error statistics and put on log";
        input  {
            leaf debug-error-statistics  {
                type ipi-network-services-manager-types:nsm_pktmgr_statistics_type_t;
                mandatory true;
                description "set exec mode debug commands error stats";
            }
        }
    }

    rpc clear-nsm-ipc-statistics {
        if-feature feature-list:HAVE_ASYNC;
        description "Use this RPC to clear statistics from nsm ipc";
    }

    rpc clear-nsm-server-ipc-statistics {
        description "Use this RPC to clear statistics for nsm messages";
    }

    rpc nsm-snmp-restart {
        if-feature feature-list:HAVE_SNMP;
        description "Use this RPC to restart SNMP for nsm";
    }

}
