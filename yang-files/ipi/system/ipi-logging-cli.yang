/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-logging-cli.yang
*
*/

submodule ipi-logging-cli {

    yang-version 1.1;

    belongs-to  ipi-logging { prefix ipi-logging; }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "IMI global logging configurations";


    revision "2025-04-18" {
        description "Change the attribute of logging cli";
        reference " 0.5.1.";
    }

    revision "2025-02-11" {
        description "Removed max-session-limit from cli-logging container";
        reference " 0.5.0.";
    }

    revision "2022-06-01" {
        description "Updated the yang file with feature";
        reference " 0.4.0.";
    }

    revision "2021-09-03" {
        description "Update descriptions of attribute";
        reference "Initial Version";
    }

    revision "2021-01-05" {
        description "Restructured module as per open-config";
        reference " 0.2.0.";
    }

    revision "2018-06-21" {
        description "Initial Version";
        reference " 0.1.0.";
    }

    grouping logging-cli-imi-config {
        description
            "Grouping for logging cli configuration";
        leaf enable-logging  {
            type  boolean;
            description "Use this attribute to enable/disable CLI history logs. By default CLI
                        history is enabled.";
        } // END of enable-logging definition.

    } // END of logging-cli-imi-config definition.

    grouping  cli-logging-grouping {
    description
        "Logging cli configurations";
    container cli-logging {
        if-feature feature-list:HAVE_IMI;
        if-feature feature-list:HAVE_SYSLOG;
        description
            "Logging cli configurations";
        container config {
            description
                "Configuration data";
            uses logging-cli-imi-config;
        } // END of config-container definition.
        container state {
            config false;
            description
                "Operational state data";
            uses logging-cli-imi-config;
        } // END of state-container definition.
    } // END of cli-logging-container definition.
    } // END of cli-logging-grouping definition.


}
