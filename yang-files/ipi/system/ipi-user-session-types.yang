/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-user-session-types.yang
*
*/

module ipi-user-session-types {

    yang-version 1.1;

    namespace   "http://www.ipinfusion.com/yang/ocnos/ipi-user-session-types";

    prefix "ipi-user-session-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "User sessions data types";


    revision "2022-06-01" {
        description "Updated the yang file with feature";
        reference " 0.2.0.";
    }

    revision "2022-01-11" {
        description "Initial Version";
        reference " 0.1.0.";
    }



    typedef  user_session_user_type_t {
        type enumeration {
            enum CLI {
                value 1;
                description "User type CLI";
            }
            enum NETCONF {
                value 2;
                description "User type Netconf";
            }
        }
        description "type definition for USER_SESSION_USER_TYPE_T";
    }

    typedef  user_session_type_t {
        type enumeration {
            enum Local {
                value 1;
                description "Session type local";
            }
            enum Remote {
                value 2;
                description "Session type remote";
            }
        }
        description "type definition for USER_SESSION_TYPE_T";
    }

    typedef  user_session_user_role_type_t {
        type enumeration {
            enum network-admin {
                value 1;
                description "User role network-admin";
            }
            enum network-engineer {
                value 2;
                description "User role network-engineer";
            }
            enum network-operator {
                value 3;
                description "User role network-operator";
            }
            enum network-user {
                value 4;
                description "User role network-user";
            }
            enum linux-admin {
                value 5;
                description "User role linux-admin";
            }
            enum rbac-customized-role {
                value 6;
                if-feature feature-list:HAVE_RBAC;
                description "User role rbac-customized-role";
            }
            enum unknown-role {
                value 7;
                description "User role unknown-role";
            }
        }
        description "type definition for USER_SESSION_USER_ROLE_TYPE_T";
    }

}
