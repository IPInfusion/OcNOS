/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgnos-update-notifications.yang
*
*/

module ipi-bgnos-update-notifications {

    yang-version 1.1;

    namespace   "http://www.ipinfusion.com/yang/ocnos/ipi-bgnos-update-notifications";

    prefix "ipi-bgnos-update-notifications";

    import cml-data-types {
        prefix cml-data-types;
        revision-date 2025-06-11;
    }

    import feature-list {
        prefix feature-list;
        revision-date 2025-07-01;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for BelugaNOS update notifications";


    revision "2023-11-28" {
        description "Cache priority added to notification";
        reference " 0.1.1.";
    }

    revision "2023-11-09" {
        description "Initial version";
        reference " 0.1.0.";
    }



    notification bgnos-image-upgrade-done {
        if-feature feature-list:HAVE_BGNOS_CUSTOM;

        description "This belugaNOS update event is generated when the OS boots with sucess after a system upgrade operation..";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

}
