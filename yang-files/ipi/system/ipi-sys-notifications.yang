/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-sys-notifications.yang
*
*/

module ipi-sys-notifications {

    yang-version 1.1;

    namespace   "http://www.ipinfusion.com/yang/ocnos/ipi-sys-notifications";

    prefix "ipi-sys-notifications";

    import cml-data-types {
        prefix cml-data-types;
        revision-date 2026-05-15;
    }

    organization
        "IP Infusion Inc.";

    contact
        "Address: 3965 Freedom Circle, Suite 200, Santa Clara, CA 95054
         Phone: +1 408-400-1900
         E-mail: support@ipinfusion.com
         Web: http://www.ipinfusion.com/";

    description
        "sys-notification has internal notifications for config lock, unlock,
                config-change, netconf get operation warnings";


    revision "2025-03-10" {
        description "Added nacm-config-save notification for NACM feature";
        reference " 0.4.2.";
    }

    revision "2024-07-03" {
        description "Added notification for NETCONF get operation warnings";
        reference " 0.4.1.";
    }

    revision "2022-09-30" {
        description "Import cml-data-types used by notifications";
        reference " 0.4.0.";
    }

    revision "2022-06-01" {
        description "Updated the yang file with feature";
        reference " 0.3.0.";
    }

    revision "2021-09-20" {
        description "Renamed force-unlock notification";
        reference " 0.2.0.";
    }

    revision "2021-07-30" {
        description "Initial version";
        reference " 0.1.0.";
    }



    notification lock-forcibly-released {

        description "Send notification when force unlock is done..";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

    notification config-sync-completion-status {

        description "Send notification when config sync is complete..";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

    notification config-change {

        description "Send notification when configuration is changed..";

        leaf message {
            type string;
            description " config change message notification";
            }
        }

        notification system-shutdown-or-reload {

            description "Send notification when system is shutdown or reloaded..";

            leaf severity {
                type cml-data-types:cml_notif_severity_t;
                description "Notification severity level (value: CRITICAL)";
            }

            leaf eventClass {
                type cml-data-types:cml_notif_class_t;
                description "Notification event class (value: MESSAGE)";
            }

            leaf message {
                type string;
                description " alarm message notification";
            }
        }

        notification get-warning-notification {

            description "Notification for netconf get operation warning information..";

            leaf severity {
                type cml-data-types:cml_notif_severity_t;
                description "Notification severity level (value: INFO)";
            }

            leaf eventClass {
                type cml-data-types:cml_notif_class_t;
                description "Notification event class (value: MESSAGE)";
            }

            leaf message {
                type string;
                description " alarm message notification";
            }
        }

}
