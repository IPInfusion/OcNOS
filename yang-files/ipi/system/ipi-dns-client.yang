/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dns-client.yang
*
*/

module ipi-dns-client {

    yang-version 1.1;

    namespace   "http://www.ipinfusion.com/yang/ocnos/ipi-dns-client";

    prefix "ipi-dns-client";

    import ietf-inet-types {
        prefix inet;
        revision-date 2013-07-15;
    }

    import cml-data-types {
        prefix cml-data-types;
        revision-date 2026-05-15;
    }

    import ipi-network-instance {
        prefix ipi-network-instance;
        revision-date 2026-08-12;
    }

    import ipi-vrf {
        prefix ipi-vrf;
        revision-date 2026-08-12;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module provides user with the possibility to configure the device
                DNS client parameters";


    revision "2025-07-31" {
        description "Updated when tag to handle vrf name removal when host/nameserver configs deleted.";
        reference " 0.6.2.";
    }

    revision "2025-07-25" {
        description "Updated when tag to include lookup enabled config.";
        reference " 0.6.1.";
    }

    revision "2025-06-09" {
        description "Added when tag to remove vrfs when none of its child exist";
        reference " 0.6.0.";
    }

    revision "2025-06-05" {
        description "Added custom error code for lookup-enabled attribute.";
        reference " 0.5.6.";
    }

    revision "2025-05-09" {
        description "Added disable-default attribute to resolve show running-config issue";
        reference " 0.5.5.";
    }

    revision "2024-09-12" {
        description "Updated the helpstring of domain-name";
        reference " 0.5.4.";
    }

    revision "2024-07-23" {
        description "Allow using DNS client on user defined VRFs instead of only default and management VRFs";
        reference " 0.5.2.";
    }

    revision "2024-03-07" {
        description "Added utils function to update ip name-server ipv6 address";
        reference " 0.5.1.";
    }

    revision "2023-05-29" {
        description "Added When tag for no-debug-all command";
        reference " 0.5.0.";
    }

    revision "2023-04-06" {
        description "Added implicit delete tag";
        reference " 0.4.0.";
    }

    revision "2023-01-02" {
        description "Added utils function to update hostname ipv6 address";
        reference " 0.3.2.";
    }

    revision "2022-12-05" {
        description "cli-sequence if-feature addition";
        reference " 0.3.1.";
    }

    revision "2022-08-10" {
        description "Debug hierarchy change";
        reference " 0.3.0.";
    }

    revision "2022-06-24" {
        description "Added implicit delete for servers and search-domains containers";
        reference " 0.2.2.";
    }

    revision "2022-06-01" {
        description "Updated the yang file with feature";
        reference " 0.2.1.";
    }

    revision "2021-12-15" {
        description "Some if-feature removed from datamodel";
        reference " 0.2.0.";
    }

    revision "2021-11-16" {
        description "Added some if-feature to fix customer SKU compilation";
        reference " 0.1.3.";
    }

    revision "2021-08-23" {
        description "Type changed for attribute domain-lookup";
        reference " 0.1.2.";
    }

    revision "2021-08-18" {
        description "Some checks fixed for domain-list and nameservers";
        reference " 0.1.1.";
    }

    revision "2021-07-30" {
        description "Initial Version";
        reference " 0.1.0.";
    }

    grouping dns-vrf-host-entry-config {
        description
            "dns-vrf-host-entry-config";
        leaf hostname  {
            type  cml-data-types:cml_host_string_t {
                length "1..63";
            }
            description "Configure a static hostname-to-address mappings in DNS.";
        } // END of hostname definition.

        leaf ipv4-address  {
            type  inet:ipv4-address;
            description "Configure a static hostname-to-address IPv4 mapping in DNS.";
        } // END of ipv4-address definition.

        leaf ipv6-address  {
            if-feature feature-list:HAVE_IPV6;
            type  inet:ipv6-address;
            description "Configure a static hostname-to-address IPv6 mapping in DNS.";
        } // END of ipv6-address definition.

    } // END of dns-vrf-host-entry-config definition.
    grouping dns-vrf-host-entries-top {
        description
            "dns-vrf-host-entries-top";
        container host-entries {
            description
                "Static hosts data";

            list host-entry {
                key "hostname";
                description
                    "Static host data";
                leaf hostname  {
                    type  leafref {
                        path  "../config/hostname";
                    }
                    description "Configure a static hostname-to-address mappings in DNS.";
                } // END of hostname definition.

                container config {
                    description
                        "Static host configuration data";
                    uses dns-vrf-host-entry-config;
                } // END of config-container definition.
                container state {
                    config false;
                    description
                        "Static host operational state data";
                    uses dns-vrf-host-entry-config;
                } // END of state-container definition.
            } // End of host-entry-list
        } // END of host-entries-container definition.
    } // END of dns-vrf-host-entries-top definition.
    grouping dns-vrf-search-domain-config {
        description
            "dns-vrf-search-domain-config";
        leaf domain-name  {
            type  inet:domain-name {
                pattern "[a-zA-Z0-9]([a-zA-Z0-9-]*[a-zA-Z0-9])?(\\.[a-zA-Z0-9]([a-zA-Z0-9-]*[a-zA-Z0-9])?)*";
                }
                description "Configure a list of default domain names used to complete unqualified
                            host names. Each domain in the list is to be tried in turn.The ip
                            domain-list command is similar to the ip domain-name command, except
                            that with the ip domain-list command you can define a list of domains,
                            each to be tried in turn.If there is no domain list, the default
                            domain name specified with the ip domain-name command is used. If
                            there is a domain list, the default domain name is not used.";
            } // END of domain-name definition.

    } // END of dns-vrf-search-domain-config definition.
    grouping dns-vrf-search-domains-top {
        description
            "dns-vrf-search-domains-top";
        container search-domains {
            description
                "Search domains data";

            list search-domain {
                key "domain-name";
                description
                    "Search domain data";
                leaf domain-name  {
                    type  leafref {
                        path  "../config/domain-name";
                    }
                    description "Use this attribute to define a list of default domain names used to
                                complete unqualified host names. Each domain in the list is to be
                                tried in turn. The ip domain-list command is similar to the ip
                                domain-name command, except that with the ip domain-list command you
                                can define a list of domains, each to be tried in turn.If there is no
                                domain list, the default domain name specified with the ip domain-name
                                command is used. If there is a domain list, the default domain name is
                                not used.";
                } // END of domain-name definition.

                container config {
                    description
                        "Search domain configuration data";
                    uses dns-vrf-search-domain-config;
                } // END of config-container definition.
                container state {
                    config false;
                    description
                        "Search domain operational state data";
                    uses dns-vrf-search-domain-config;
                } // END of state-container definition.
            } // End of search-domain-list
        } // END of search-domains-container definition.
    } // END of dns-vrf-search-domains-top definition.
    grouping dns-vrf-servers-config {
        description
            "dns-vrf-servers-config";
        leaf address  {
            type  inet:ip-address;
            description "Name server address used for name resolution.";
        } // END of address definition.

    } // END of dns-vrf-servers-config definition.
    grouping dns-vrf-servers-top {
        description
            "dns-vrf-servers-top";
        container servers {
            description
                "Name servers data";

            list server {
                key "address";
                description
                    "Name server data";
                leaf address  {
                    type  leafref {
                        path  "../config/address";
                    }
                    description "Name server address used for name resolution.";
                } // END of address definition.

                container config {
                    description
                        "Name server configuration data";
                    uses dns-vrf-servers-config;
                } // END of config-container definition.
                container state {
                    config false;
                    description
                        "Server operational state data";
                    uses dns-vrf-servers-config;
                } // END of state-container definition.
            } // End of server-list
        } // END of servers-container definition.
    } // END of dns-vrf-servers-top definition.
    grouping dns-vrf-config {
        description
            "dns-vrf-config";
        leaf vrf-name  {
            if-feature feature-list:HAVE_VRF;
            type  leafref {
                path  "/ipi-network-instance:network-instances/ipi-network-instance:network-instance/ipi-vrf:vrf/ipi-vrf:config/ipi-vrf:vrf-name";
            }
            description "VRF name associated with this instance.";
        } // END of vrf-name definition.

        leaf lookup-enabled  {
            type  empty;
            description "Enable DNS translation.";
        } // END of lookup-enabled definition.

        leaf default-domain-name  {
            type  inet:domain-name {
                pattern "[a-zA-Z0-9]([a-zA-Z0-9-]*[a-zA-Z0-9])?(\\.[a-zA-Z0-9]([a-zA-Z0-9-]*[a-zA-Z0-9])?)*";
                }
                description "Default domain name used to complete unqualified host names (names
                            without a dotted-decimal domain name).";
            } // END of default-domain-name definition.

    } // END of dns-vrf-config definition.
    grouping dns-vrfs-top {
        description
            "dns-vrfs-top";
        container vrfs {
            description
                "VRF list for DNS configuration";

            list vrf {
                key "vrf-name";
                description
                    "VRF list for DNS configuration";
                leaf vrf-name  {
                    type  leafref {
                        path  "../config/vrf-name";
                    }
                    description "VRF name associated with this instance.";
                } // END of vrf-name definition.

                container config {
                    description
                        "DNS configuration";
                    uses dns-vrf-config;
                } // END of config-container definition.
                container state {
                    config false;
                    description
                        "DNS operational state data";
                    uses dns-vrf-config;
                } // END of state-container definition.
                uses dns-vrf-servers-top;
                uses dns-vrf-search-domains-top;
                uses dns-vrf-host-entries-top;
            } // End of vrf-list
        } // END of vrfs-container definition.
    } // END of dns-vrfs-top definition.
    grouping dns-debug-config {
        description
            "dns-debug-config";
        leaf enable  {
            type  empty;
            description "DNS client debug.";
        } // END of enable definition.

    } // END of dns-debug-config definition.
    grouping dns-debug-terminal-state {
        description
            "dns-debug-terminal-state";
        leaf terminal-debug-status  {
            type  cml-data-types:cml_on_off_t;
            description "DNS client debug.";
        } // END of terminal-debug-status definition.

    } // END of dns-debug-terminal-state definition.
    grouping dns-debug-top {
        description
            "dns-debug-top";
        container debug {
            description
                "DNS client debug data";
            container config {
                description
                    "DNS client debugging configuration";
                uses dns-debug-config;
            } // END of config-container definition.
            container state {
                config false;
                description
                    "DNS client debugging information";
                uses dns-debug-config;
                uses dns-debug-terminal-state;
            } // END of state-container definition.
        } // END of debug-container definition.
    } // END of dns-debug-top definition.
    grouping dns-default-config {
        description
            "ip domain-lookup disable default configuration";
        leaf disable-default-instance  {
            type  empty;
            description "Use this attribute to prevent default DNS config from being enabled at
                        start up";
        } // END of disable-default-instance definition.

    } // END of dns-default-config definition.
    grouping dns-default-top {
        description
            "ip domain-lookup disable default configuration";
        container default-instance {
            description
                "dns client default container configuration";
            container config {
                description
                    "Configuration data for dns client configuration";
                uses dns-default-config;
            } // END of config-container definition.
            container state {
                config false;
                description
                    "Operational state data for DNS configuration";
                uses dns-default-config;
            } // END of state-container definition.
        } // END of default-instance-container definition.
    } // END of dns-default-top definition.

    grouping  dns-grouping {
    description
        "Container for DNS";
    container dns {
        if-feature feature-list:HAVE_DNS_CLIENT;
        description
            "Container for DNS";
        uses dns-vrfs-top;
        uses dns-debug-top;
        uses dns-default-top;
    } // END of dns-container definition.
    } // END of dns-grouping definition.

    uses dns-grouping;

    rpc dns-client-terminal-debug-on {
        if-feature feature-list:HAVE_DNS_CLIENT;
        description "Enable DNS client debug";
    }

    rpc dns-client-terminal-debug-off {
        if-feature feature-list:HAVE_DNS_CLIENT;
        description "Disable DNS client debug";
    }

}
