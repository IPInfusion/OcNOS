/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-lb.yang
*
*/

module ipi-lb {

    yang-version 1.1;

    namespace   "http://www.ipinfusion.com/yang/ocnos/ipi-lb";

    prefix "ipi-lb";

    import ipi-lb-types {
        prefix ipi-lb-types;
        revision-date 2021-07-10;
    }

    import ietf-yang-types {
        prefix yang;
        revision-date 2013-07-15;
    }

    import feature-list {
        prefix feature-list;
        revision-date 2026-09-15;
    }

    include ipi-lb-group { revision-date 2022-06-01;}
    include ipi-lb-modem { revision-date 2025-02-27;}
    organization
        "IP Infusion Inc.";

    contact
        "Address: 3965 Freedom Circle, Suite 200, Santa Clara, CA 95054
         Phone: +1 408-400-1900
         E-mail: support@ipinfusion.com
         Web: http://www.ipinfusion.com/";

    description
        "Link Bonding Configurations";


    revision "2025-02-27" {
        description "Updated the flag for modem-port-vlan attr";
        reference " 0.4.2.";
    }

    revision "2023-03-19" {
        description "Added utils_func tag for segment-ether-type modem-ethert-type and control-ethertype";
        reference " 0.4.1.";
    }

    revision "2023-02-06" {
        description "Enforced the hexadecimal format for ethertype";
        reference " 0.4.0.";
    }

    revision "2022-07-05" {
        description "Added tx-holdoff-timer attribute";
        reference " 0.3.0.";
    }

    revision "2022-06-01" {
        description "Updated the yang file with feature";
        reference " 0.2.0.";
    }

    revision "2021-07-10" {
        description "Initial Version";
        reference "Initial Version";
    }

    grouping link-bonding-global-config {
        description
            "Grouping for link-bonding-global-config configuration data";
        leaf control-traffic  {
            type  empty;
            description "Use this attribute to enable/disable link bonding control traffic";
        } // END of control-traffic definition.

        leaf segment-ether-type  {
            type  string {
                length "1..1965";
                pattern "0x[0-9a-fA-F]+";
            }
            description "Use this attribute to set the segment ethertype";
        } // END of segment-ether-type definition.

        leaf modem-ether-type  {
            type  string {
                length "1..1965";
                pattern "0x[0-9a-fA-F]+";
            }
            description "Use this attribute to set the modem ethertype";
        } // END of modem-ether-type definition.

        leaf control-ether-type  {
            type  string {
                length "1..1965";
                pattern "0x[0-9a-fA-F]+";
            }
            description "Use this attribute to set the control ethertype";
        } // END of control-ether-type definition.

        leaf crc-enabled  {
            type  empty;
            description "Use this attribute enable crc calculation";
        } // END of crc-enabled definition.

        leaf segment-size  {
            type  ipi-lb-types:lb_segment_size_t;
            description "Use this attribute to set the segment size";
        } // END of segment-size definition.

        leaf total-shared-buffers  {
            type  uint16 {
                 range "0..16383"  {
                    description "0..16383: Supported range 0 - 16383";
                 }
            }
            description "Use this attribute to configure the number of total shared buffers";
        } // END of total-shared-buffers definition.

        leaf max-buffers  {
            type  uint16 {
                 range "0..16383"  {
                    description "0..16383: Supported range 0 - 16383";
                 }
            }
            description "Use this attribute to configure the maximum size of buffers";
        } // END of max-buffers definition.

        leaf guaranteed-buffers  {
            type  uint16 {
                 range "0..16383"  {
                    description "0..16383: Supported range 0 - 16383";
                 }
            }
            description "Use this attribute to configure the number of guaranteed buffers per
                        LBG";
        } // END of guaranteed-buffers definition.

        leaf timeout-threshold  {
            type  uint16 {
                 range "0..65535"  {
                    description "0..65535: Supported range 0 - 65535";
                 }
            }
            description "Use this attribute to set the timeout threshold per LBG";
        } // END of timeout-threshold definition.

        leaf tx-holdoff-timer  {
            type  uint16 {
                 range "0..5000"  {
                    description "0..5000: Supported range 0 - 5000";
                 }
            }
            description "Use this attribute to set the transmit holdoff timer";
        } // END of tx-holdoff-timer definition.

        leaf max-out-of-order  {
            type  uint16 {
                 range "0..8191"  {
                    description "0..8191: Supported range 0 - 8191";
                 }
            }
            description "Use this attribute to set the maximum difference allowed between the
                        expected sequence number and heads of modem FIFOs of the LBG";
        } // END of max-out-of-order definition.

        leaf expected-seq-number  {
            type  uint16 {
                 range "0..16383"  {
                    description "0..16383: Supported range 0 - 16383";
                 }
            }
            description "Use this attribute to set the expected sequence number";
        } // END of expected-seq-number definition.

    } // END of link-bonding-global-config definition.
    grouping link-bonding-global-top {
        description
            "Grouping for Link Bonding global";
        container global {
            description
                "Container for global Link Bonding configuration";
            container config {
                description
                    "Configuration data for global Link Bonding";
                uses link-bonding-global-config;
            } // END of config-container definition.
            container state {
                config false;
                description
                    "Operational state data for";
                uses link-bonding-global-config;
                uses link-bonding-global-counters-state;
            } // END of state-container definition.
        } // END of global-container definition.
    } // END of link-bonding-global-top definition.
    grouping link-bonding-global-counters-state {
        description
            "Operational data representing LB global counters";
        leaf in-segments-drop  {
            type  yang:counter64;
            description "Global counter for LBG RX segment Drops";
        } // END of in-segments-drop definition.

        leaf in-packets  {
            type  yang:counter64;
            description "Global counter for LBG RX Packets";
        } // END of in-packets definition.

        leaf in-bypass-packets  {
            type  yang:counter64;
            description "Global counter for LBG RX which are not LBG packets";
        } // END of in-bypass-packets definition.

        leaf out-error-packets  {
            type  yang:counter64;
            description "Global counter for LBG TX error packets";
        } // END of out-error-packets definition.

        leaf out-control-packets  {
            type  yang:counter64;
            description "Global counter for TX Control packets";
        } // END of out-control-packets definition.

        leaf out-control-bytes  {
            type  yang:counter64;
            description "Global counter for TX Control Bytes";
        } // END of out-control-bytes definition.

    } // END of link-bonding-global-counters-state definition.

    grouping  link-bonding-grouping {
    description
        "Link Bonding";
    container link-bonding {
        if-feature feature-list:HAVE_LINK_BONDING;
        description
            "Link Bonding";
        uses link-bonding-global-top;
        uses modem-grouping;
        uses link-bonding-group-grouping;
    } // END of link-bonding-container definition.
    } // END of link-bonding-grouping definition.

    uses link-bonding-grouping;

}
