/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-lb-group.yang
*
*/

submodule ipi-lb-group {

    yang-version 1.1;

    belongs-to  ipi-lb { prefix ipi-lb; }

    import feature-list {
        prefix feature-list;
        revision-date 2026-09-15;
    }

    import ipi-interface {
        prefix ipi-interface;
        revision-date 2026-03-10;
    }

    organization
        "IP Infusion Inc.";

    contact
        "Address: 3965 Freedom Circle, Suite 200, Santa Clara, CA 95054
         Phone: +1 408-400-1900
         E-mail: support@ipinfusion.com
         Web: http://www.ipinfusion.com/";

    description
        "Link Bonding Group Configurations";


    revision "2022-06-01" {
        description "Updated the yang file with feature";
        reference " 0.2.0.";
    }

    revision "2021-07-10" {
        description "Initial Version";
        reference " 0.1.0.";
    }

    grouping lb-interface-lbg-config {
        description
            "Grouping for link bonding configuration data";
        leaf name  {
            type  leafref {
                path  "/ipi-interface:interfaces/ipi-interface:interface/ipi-interface:name";
            }
            description "The Link Bonding Group interface name";
        } // END of name definition.

    } // END of lb-interface-lbg-config definition.

    grouping  link-bonding-group-grouping {
    description
        "Container for interface lbg";
    container link-bonding-group {
        if-feature feature-list:HAVE_LINK_BONDING;
        description
            "Container for interface lbg";
        container interfaces {
            description
                "Configuration data for interface lbg";

            list interface {
                key "name";
                description
                    "Configuration data for interface lbg";
                leaf name  {
                    type  leafref {
                        path  "../config/name";
                    }
                    description "Interface name for Link Bonding Group";
                } // END of name definition.

                container config {
                    description
                        "Configuration data for interface";
                    uses lb-interface-lbg-config;
                } // END of config-container definition.
                container state {
                    config false;
                    description
                        "Operational state data for link-bonding-group";
                    uses lb-interface-lbg-config;
                } // END of state-container definition.
            } // End of interface-list
        } // END of interfaces-container definition.
    } // END of link-bonding-group-container definition.
    } // END of link-bonding-group-grouping definition.


}
