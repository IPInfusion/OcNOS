/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-lb-modem.yang
*
*/

submodule ipi-lb-modem {

    yang-version 1.1;

    belongs-to  ipi-lb { prefix ipi-lb; }

    import feature-list {
        prefix feature-list;
        revision-date 2026-09-15;
    }

    import ipi-interface {
        prefix ipi-interface;
        revision-date 2026-03-10;
    }

    import ietf-yang-types {
        prefix yang;
        revision-date 2013-07-15;
    }

    import ipi-lb-types {
        prefix ipi-lb-types;
        revision-date 2021-07-10;
    }

    organization
        "IP Infusion Inc.";

    contact
        "Address: 3965 Freedom Circle, Suite 200, Santa Clara, CA 95054
         Phone: +1 408-400-1900
         E-mail: support@ipinfusion.com
         Web: http://www.ipinfusion.com/";

    description
        "Link Bonding Configurations";


    revision "2025-02-27" {
        description "Updated the flag for modem-port-vlan attr";
        reference " 0.2.1.";
    }

    revision "2022-06-01" {
        description "Updated the yang file with feature";
        reference " 0.2.0.";
    }

    revision "2021-07-10" {
        description "Initial Version";
        reference "Initial Version";
    }

    grouping modem-shape-control-traffic-config {
        description
            "Grouping for modem control-traffic shape configuration";
        leaf rate  {
            // when " ipi-lb-modem:modem/interfaces/interface/modem/shape/config/rate-unit ";
            type  uint64 {
                 range "1..1000000000"  {
                    description "1..1000000000: Supported range 1 - 1000000000";
                 }
            }
            mandatory true;
            description "Use this attribute to configure shaping on control port to impose a
                        maximum rate on it";
        } // END of rate definition.

        leaf rate-unit  {
            // when " ipi-lb-modem:modem/interfaces/interface/modem/shape/config/rate ";
            type  ipi-lb-types:lb_control_shape_rate_unit_t;
            mandatory true;
            description "Use this attribute to set the shape rate unit";
        } // END of rate-unit definition.

    } // END of modem-shape-control-traffic-config definition.
    grouping modem-shape-top {
        description
            "Grouping for modem control-traffic shape";
        container shape {
            description
                "Configuration data for modem control-traffic shape";
            container config {
                presence "modem-shape";
                description
                    "Configuration data for QoS traffic shape";
                uses modem-shape-control-traffic-config;
            } // END of config-container definition.
            container state {
                config false;
                description
                    "Configuration data for QoS traffic shape";
                uses modem-shape-control-traffic-config;
            } // END of state-container definition.
        } // END of shape-container definition.
    } // END of modem-shape-top definition.
    grouping modem-port-vlan-config {
        description
            "Grouping for modem interface port-vlan configuration";
        leaf port  {
            type  leafref {
                path  "/ipi-interface:interfaces/ipi-interface:interface/ipi-interface:name";
            }
            description "Use this attribute attached the modem to a port";
        } // END of port definition.

        leaf vlan  {
            // when " ipi-lb-modem:modem/interfaces/interface/modem/port-vlan/config/port ";
            type  uint16 {
                 range "1..4094"  {
                    description "1..4094: Supported range 1 - 4094";
                 }
            }
            description "Use this attribute to configure the vlan for the modem interface";
        } // END of vlan definition.

    } // END of modem-port-vlan-config definition.
    grouping modem-port-vlan-top {
        description
            "Grouping for modem port vlan";
        container port-vlan {
            description
                "Configuration data for modem port vlan";
            container config {
                description
                    "Configuration data for port-vlan";
                uses modem-port-vlan-config;
            } // END of config-container definition.
            container state {
                config false;
                description
                    "Configuration data for port-vlan";
                uses modem-port-vlan-config;
            } // END of state-container definition.
        } // END of port-vlan-container definition.
    } // END of modem-port-vlan-top definition.
    grouping interface-modem-config {
        description
            "Grouping for modem interface modem configuration";
        leaf source-mac  {
            type  yang:mac-address {
                pattern "[0-9a-fA-F]{2}(:[0-9a-fA-F]{2}){5}";
                }
                description "Use this attribute to configure the source-mac of the modem interface";
            } // END of source-mac definition.

            leaf destination-mac  {
                type  yang:mac-address {
                    pattern "[0-9a-fA-F]{2}(:[0-9a-fA-F]{2}){5}";
                    }
                    description "Use this attribute to configure the destination-mac used on the modem
                                interface";
                } // END of destination-mac definition.

                leaf compensation  {
                    type  int8 {
                         range "-63..63"  {
                            description "-63..63: Supported range -63 - 63";
                         }
                    }
                    description "Use this attribute to configure the componsation for the modem
                                interface";
                } // END of compensation definition.

                leaf link-bonding-group  {
                    type  uint8 {
                         range "1..255"  {
                            description "1..255: Supported range 1 - 255";
                         }
                    }
                    description "Use this attribute to configure the link-bonding-group for the modem
                                interface";
                } // END of link-bonding-group definition.

    } // END of interface-modem-config definition.
    grouping interface-modem-top {
        description
            "Grouping for modem interface modem mode";
        container modem {
            description
                "Configuration data for modem interface";
            container config {
                description
                    "Configuration data for modem interface";
                uses interface-modem-config;
            } // END of config-container definition.
            container state {
                config false;
                description
                    "Operational state data for modem";
                uses interface-modem-config;
            } // END of state-container definition.
            uses modem-port-vlan-top;
            uses modem-shape-top;
        } // END of modem-container definition.
    } // END of interface-modem-top definition.
    grouping interface-config {
        description
            "Grouping for modem interface configuration";
        leaf name  {
            type  leafref {
                path  "/ipi-interface:interfaces/ipi-interface:interface/ipi-interface:name";
            }
            description "The interface name to configure the modem parameters.";
        } // END of name definition.

    } // END of interface-config definition.

    grouping  modem-grouping {
    description
        "Container for interface modem";
    container modem {
        if-feature feature-list:HAVE_LINK_BONDING;
        description
            "Container for interface modem";
        container interfaces {
            description
                "Top level container for Link-Bonding modem interfaces";

            list interface {
                key "name";
                description
                    "List for Link-Bonding modem interfaces";
                leaf name  {
                    type  leafref {
                        path  "../config/name";
                    }
                    description "Interface name for which modem is being configured";
                } // END of name definition.

                container config {
                    description
                        "Configuration data for interface";
                    uses interface-config;
                } // END of config-container definition.
                container state {
                    config false;
                    description
                        "Operational state data for modem";
                    uses interface-config;
                } // END of state-container definition.
                uses interface-modem-top;
            } // End of interface-list
        } // END of interfaces-container definition.
    } // END of modem-container definition.
    } // END of modem-grouping definition.


}
