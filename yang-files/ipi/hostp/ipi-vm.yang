/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-vm.yang
*
*/

module ipi-vm {

    yang-version 1.1;

    namespace   "http://www.ipinfusion.com/yang/ocnos/ipi-vm";

    prefix "ipi-vm";

    import ipi-vm-types {
        prefix ipi-vm-types;
        revision-date 2022-05-16;
    }

    import ipi-vrf {
        prefix ipi-vrf;
        revision-date 2026-08-12;
    }

    import ipi-network-instance {
        prefix ipi-network-instance;
        revision-date 2026-08-12;
    }

    import ietf-inet-types {
        prefix inet;
        revision-date 2013-07-15;
    }

    import cml-data-types {
        prefix cml-data-types;
        revision-date 2026-05-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Data Model for Virtual Machine";


    revision "2026-01-09" {
        description "Making control-channel get deleted when vm-bridge is deleted";
        reference " 0.4.0.";
    }

    revision "2024-04-01" {
        description "Added a when tag for  nat and snat and added utils_func tag for tpid attribute";
        reference " 0.3.3.";
    }

    revision "2023-02-15" {
        description "change in CLI design for nat dnat CLI";
        reference " 0.3.2.";
    }

    revision "2023-02-12" {
        description "Making the vrf VRF_NAME as optional for snat and dnat CLI";
        reference " 0.3.1.";
    }

    revision "2023-02-08" {
        description "Added a proper helpstring for nat dnat CLI and install condition for feature guest vm enable CLI";
        reference " 0.3.0.";
    }

    revision "2023-01-05" {
        description "Leafref correction for config container";
        reference " 0.2.2.";
    }

    revision "2022-09-06" {
        description "Generate vm-bridge-create with mode change";
        reference " 0.2.1.";
    }

    revision "2022-07-31" {
        description "Stop using inet:ipv4-prefix and inet:ipv6-prefix due to Cisco NSO iterop";
        reference " 0.2.0.";
    }

    revision "2022-05-16" {
        description "Initial Version";
        reference " 0.1.0.";
    }

    grouping vm-bridge-config {
        description
            "Grouping for VM-Bridge config objects.";
        leaf bridge-name  {
            type  string {
                length "1..16";
                pattern "[^?' =,>|]+";
            }
            description "Name of the VM bridge";
        } // END of bridge-name definition.

    } // END of vm-bridge-config definition.
    grouping vm-control-channel-config {
        description
            "Grouping for VM-Bridge Control channel config objects.";
        leaf vlan  {
            type  uint16 {
                 range "1..4095"  {
                    description "1..4095: Supported range 1 - 4095";
                 }
            }
            mandatory true;
            description "Set control channel vlan id";
        } // END of vlan definition.

        leaf tpid  {
            type  string {
                length "1..1965";
                pattern "0x[0-9a-fA-F]+";
            }
            mandatory true;
            description "Set control channel tpid";
        } // END of tpid definition.

    } // END of vm-control-channel-config definition.
    grouping guest-vm {
        description
            "grouping of guestvm object";
        leaf enable-feature  {
            type  boolean;
            mandatory true;
            description "Global command to enable Guest-VM feature";
        } // END of enable-feature definition.

    } // END of guest-vm definition.
    grouping vm-dnat-config {
        description
            "Grouping for VM-dnat config objects.";
        leaf from-match-type  {
            type  ipi-vm-types:cml_nat_from_match_t;
            description "match-ip or source-interface";
        } // END of from-match-type definition.

        leaf from-match-value  {
            type  ipi-vm-types:cml_nat_from_value_t;
            description "IP Address or Interface name";
        } // END of from-match-value definition.

        leaf to-ip-addr  {
            type  inet:ipv4-address;
            description "To IP address";
        } // END of to-ip-addr definition.

        leaf protocol  {
            type  ipi-vm-types:cml_proto_t;
            description "Use TCP or UDP for NAT";
        } // END of protocol definition.

        leaf from-port-num  {
            type  int32 {
                 range "-1..65535"  {
                    description "-1..65535: Supported range -1 - 65535";
                 }
            }
            default "-1";
            description "Source port number. Since '0' is valid port number, used '-1' for
                        optional manipulation";
        } // END of from-port-num definition.

        leaf to-port-num  {
            type  int32 {
                 range "-1..65535"  {
                    description "-1..65535: Supported range -1 - 65535";
                 }
            }
            default "-1";
            description "Destination port number. Since '0' is valid port number, used '-1' for
                        optional manipulation";
        } // END of to-port-num definition.

        leaf vrf-name  {
            type  leafref {
                path  "/ipi-network-instance:network-instances/ipi-network-instance:network-instance/ipi-vrf:vrf/ipi-vrf:config/ipi-vrf:vrf-name";
            }
            description "VRF Name";
        } // END of vrf-name definition.

    } // END of vm-dnat-config definition.
    grouping vm-snat-config {
        description
            "Grouping for VM-snat config objects.";
        leaf from-ip-addr  {
            type  cml-data-types:cml_ipv4_prefix_t;
            description "From IP address and subnet mask";
        } // END of from-ip-addr definition.

        leaf to-ip-addr  {
            type  ipi-vm-types:cml_nat_from_value_t;
            description "To IP address";
        } // END of to-ip-addr definition.

        leaf vrf-name  {
            type  leafref {
                path  "/ipi-network-instance:network-instances/ipi-network-instance:network-instance/ipi-vrf:vrf/ipi-vrf:config/ipi-vrf:vrf-name";
            }
            description "VRF Name";
        } // END of vrf-name definition.

    } // END of vm-snat-config definition.

    grouping  vm-grouping {
    description
        "Container for VM";
    container vm {
        if-feature feature-list:HAVE_HOSTPD;
        if-feature feature-list:HAVE_GUEST_VM;
        description
            "Container for VM";
        container vm-bridges {
            description
                "Configuration data for vm-bridges";

            list vm-bridge {
                key "bridge-name";
                description
                    "Configuration data for vm-bridge";
                leaf bridge-name  {
                    type  leafref {
                        path  "../config/bridge-name";
                    }
                    description "Name of the VM bridge";
                } // END of bridge-name definition.

                container config {
                    description
                        "Configuration data for vm-bridge";
                    uses vm-bridge-config;
                } // END of config-container definition.
                container state {
                    config false;
                    description
                        "Operational state data for vm-bridge";
                    uses vm-bridge-config;
                } // END of state-container definition.
            } // End of vm-bridge-list
        } // END of vm-bridges-container definition.
        container control-channel {
            description
                "Container for control-channel,including configuration and state data";
            container config {
                when " /ipi-vm:vm/ipi-vm:vm-bridges/ipi-vm:vm-bridge/ipi-vm:config/ipi-vm:bridge-name ";
                presence "vm-control-channel-config";
                description
                    "This container defines control-channel configuration.";
                uses vm-control-channel-config;
            } // END of config-container definition.
            container state {
                config false;
                description
                    "Operational state data for control-channel";
                uses vm-control-channel-config;
            } // END of state-container definition.
        } // END of control-channel-container definition.
    } // END of vm-container definition.
    } // END of vm-grouping definition.

    grouping  nat-grouping {
    description
        "Container for nat";
    container nat {
        if-feature feature-list:HAVE_HOSTPD;
        if-feature feature-list:HAVE_GUEST_VM;
        description
            "Container for nat";
        container dnat {
            description
                "Container for dnat";

            list dnat-vrf {
                key "from-match-type from-match-value to-ip-addr protocol from-port-num to-port-num vrf-name";
                description
                    "VM-dnat vrf list";
                leaf from-match-type  {
                    type  leafref {
                        path  "../config/from-match-type";
                    }
                    description "match-ip or source-interface";
                } // END of from-match-type definition.

                leaf from-match-value  {
                    type  leafref {
                        path  "../config/from-match-value";
                    }
                    description "IP address or Interface name";
                } // END of from-match-value definition.

                leaf to-ip-addr  {
                    type  leafref {
                        path  "../config/to-ip-addr";
                    }
                    description "To IP address";
                } // END of to-ip-addr definition.

                leaf protocol  {
                    type  leafref {
                        path  "../config/protocol";
                    }
                    description "Use TCP or UDP for NAT";
                } // END of protocol definition.

                leaf from-port-num  {
                    type  leafref {
                        path  "../config/from-port-num";
                    }
                    description "Source port number. Since '0' is valid port number, used '-1' for
                                optional manipulation";
                } // END of from-port-num definition.

                leaf to-port-num  {
                    type  leafref {
                        path  "../config/to-port-num";
                    }
                    description "Destination port number. Since '0' is valid port number, used '-1' for
                                optional manipulation";
                } // END of to-port-num definition.

                leaf vrf-name  {
                    type  leafref {
                        path  "../config/vrf-name";
                    }
                    description "VRF Name";
                } // END of vrf-name definition.

                container config {
                    presence "nat-dnat-dnat-vrf-config";
                    description
                        "This container defines dnat configuration.";
                    uses vm-dnat-config;
                } // END of config-container definition.
                container state {
                    config false;
                    description
                        "Operational state data for dnat";
                    uses vm-dnat-config;
                } // END of state-container definition.
            } // End of dnat-vrf-list
        } // END of dnat-container definition.
        container snat {
            description
                "Container for snat";

            list snat-vrf {
                key "from-ip-addr to-ip-addr vrf-name";
                description
                    "VM-snat vrf list";
                leaf from-ip-addr  {
                    type  leafref {
                        path  "../config/from-ip-addr";
                    }
                    description "From IP address and subnet mask";
                } // END of from-ip-addr definition.

                leaf to-ip-addr  {
                    type  leafref {
                        path  "../config/to-ip-addr";
                    }
                    description "To IP address";
                } // END of to-ip-addr definition.

                leaf vrf-name  {
                    type  leafref {
                        path  "../config/vrf-name";
                    }
                    description "VRF Name";
                } // END of vrf-name definition.

                container config {
                    presence "nat-snat-snat-vrf-config";
                    description
                        "This container defines snat configuration.";
                    uses vm-snat-config;
                } // END of config-container definition.
                container state {
                    config false;
                    description
                        "Operational state data for snat";
                    uses vm-snat-config;
                } // END of state-container definition.
            } // End of snat-vrf-list
        } // END of snat-container definition.
    } // END of nat-container definition.
    } // END of nat-grouping definition.

    grouping  guestVm-grouping {
    description
        "Description about guest vm feature enable";
    container guestVm {
        if-feature feature-list:HAVE_HOSTPD;
        if-feature feature-list:HAVE_GUEST_VM;
        description
            "Description about guest vm feature enable";
        container config {
            presence "guestVm-config";
            description
                "This container defines gestVm configuration.";
            uses guest-vm;
        } // END of config-container definition.
        container state {
            config false;
            description
                "This container defines gestVm configuration.";
            uses guest-vm;
        } // END of state-container definition.
    } // END of guestVm-container definition.
    } // END of guestVm-grouping definition.

    uses vm-grouping;
    uses nat-grouping;
    uses guestVm-grouping;

}
