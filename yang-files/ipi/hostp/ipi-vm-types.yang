/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-vm-types.yang
*
*/

module ipi-vm-types {

    yang-version 1.1;

    namespace   "http://www.ipinfusion.com/yang/ocnos/ipi-vm-types";

    prefix "ipi-vm-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "VM data types";


    revision "2022-05-16" {
        description "Initial Version";
        reference " 0.1.0.";
    }



    typedef  cml_proto_t {
        type enumeration {
            enum tcp {
                value 1;
                description "Give TCP";
            }
            enum udp {
                value 2;
                description "Give UDP";
            }
        }
        description "type definition for CML_PROTO_T";
    }

    typedef  cml_nat_from_match_t {
        type enumeration {
            enum match-ip {
                value 1;
                description "Match IPv4 address";
            }
            enum source-interface {
                value 2;
                description "Source interface";
            }
        }
        description "type definition for CML_NAT_FROM_MATCH_T";
    }

    typedef  cml_nat_from_value_t {
        type union {
            type inet:ipv4-address {

            }
            type string {

            }
        }
        description "type definition for CML_NAT_FROM_VALUE_T";
    }

}
