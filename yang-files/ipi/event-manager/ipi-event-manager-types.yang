/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-event-manager-types.yang
*
*/

module ipi-event-manager-types {

    yang-version 1.1;

    namespace   "http://www.ipinfusion.com/yang/ocnos/ipi-event-manager-types";

    prefix "ipi-event-manager-types";

    organization
        "IP Infusion Inc.";

    contact
        "Address: 3965 Freedom Circle, Suite 200, Santa Clara, CA 95054
         Phone: +1 408-400-1900
         E-mail: support@ipinfusion.com
         Web: http://www.ipinfusion.com/";

    description
        "Event Manager related data types";


    revision "2022-10-26" {
        description "Changing EVENT_MANAGER_SEVERITY_LEVEL_T element '6' to 'all'";
        reference " 0.1.1.";
    }

    revision "2022-09-29" {
        description "Initial Version";
        reference " 0.1.0.";
    }



    typedef  event_manager_execution_status_t {
        type enumeration {
            enum Success {
                value 0;
                description "Success";
            }
            enum Fail {
                value 1;
                description "Fail";
            }
            enum Not-Run {
                value 2;
                description "Not Run";
            }
        }
        description "type definition for EVENT_MANAGER_EXECUTION_STATUS_T";
    }

    typedef  event_manager_status_t {
        type enumeration {
            enum Inactive {
                value 0;
                description "Inactive";
            }
            enum Active {
                value 1;
                description "Active";
            }
        }
        description "type definition for EVENT_MANAGER_STATUS_T";
    }

    typedef  event_manager_action_type_t {
        type enumeration {
            enum script {
                value 0;
                description "Configure script as action";
            }
        }
        description "type definition for EVENT_MANAGER_ACTION_TYPE_T";
    }

    typedef  event_manager_event_type_t {
        type enumeration {
            enum syslog {
                value 0;
                description "Syslog Event";
            }
        }
        description "type definition for EVENT_MANAGER_EVENT_TYPE_T";
    }

    typedef  event_manager_severity_level_t {
        type enumeration {
            enum 0 {
                value 0;
                description "Emergency - Priority 0";
            }
            enum 1 {
                value 1;
                description "Alert - Priority 1";
            }
            enum 2 {
                value 2;
                description "Critical - Priority 2";
            }
            enum 3 {
                value 3;
                description "Error - Priority 3";
            }
            enum 4 {
                value 4;
                description "Notify - Priority 4";
            }
            enum 5 {
                value 5;
                description "Info - Priority 5";
            }
            enum all {
                value 6;
                description "All (Default)";
            }
        }
        description "type definition for EVENT_MANAGER_SEVERITY_LEVEL_T";
    }

}
