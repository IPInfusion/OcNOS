/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-event-manager.yang
*
*/

module ipi-event-manager {

    yang-version 1.1;

    namespace   "http://www.ipinfusion.com/yang/ocnos/ipi-event-manager";

    prefix "ipi-event-manager";

    import ietf-yang-types {
        prefix yang;
        revision-date 2013-07-15;
    }

    import ipi-event-manager-types {
        prefix ipi-event-manager-types;
        revision-date 2022-10-26;
    }

    import cml-data-types {
        prefix cml-data-types;
        revision-date 2026-05-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Event Manager";


    revision "2022-10-26" {
        description "Changing EVENT_MANAGER_SEVERITY_LEVEL_T element '6' to 'all'";
        reference " 0.1.4.";
    }

    revision "2022-10-18" {
        description "Adding ROLE_NETWORK_ADMIN to event-manager objectlists";
        reference " 0.1.3.";
    }

    revision "2022-10-06" {
        description "Adding ipi-event-manager_get_api to protocol-api-header-file";
        reference " 0.1.2.";
    }

    revision "2022-10-04" {
        description "Set custom error codes on key attributes";
        reference " 0.1.1.";
    }

    revision "2022-09-29" {
        description "Initial Version of Event Manager Feature";
        reference " 0.1.0.";
    }

    grouping event-manager-config {
        description
            "Grouping for event-manager configuration data";
        leaf feature  {
            type  cml-data-types:cml_enable_disable_t;
            description "Enable Event Manager";
        } // END of feature definition.

    } // END of event-manager-config definition.
    grouping event-manager-event-config {
        description
            "Grouping for event configuration data";
        leaf event-name  {
            type  string {
                length "2..32";
                pattern "[^?' =,>|]+";
            }
            description "Name of event";
        } // END of event-name definition.

        leaf event-type  {
            type  ipi-event-manager-types:event_manager_event_type_t;
            mandatory true;
            description "Event Type";
        } // END of event-type definition.

        leaf event-id  {
            // when " ../event-type='syslog' ";
            type  string {
                length "4..128";
                pattern "[^?' =,>|]+";
            }
            mandatory true;
            description "Event ID Name";
        } // END of event-id definition.

        leaf event-pattern  {
            // when " ../event-type='syslog' ";
            type  cml-data-types:cml_line_t {
                length "1..1965";
            }
            description "Pattern to match";
        } // END of event-pattern definition.

        leaf severity  {
            // when " ../event-type='syslog' ";
            type  ipi-event-manager-types:event_manager_severity_level_t;
            default "all";
            description "Severity level";
        } // END of severity definition.

    } // END of event-manager-event-config definition.
    grouping event-manager-event-state {
        description
            "Grouping for event operation state data";
        leaf trigger-count  {
            type  yang:counter64;
            description "Counter for number of times trigger is invoked";
        } // END of trigger-count definition.

        leaf policy-count  {
            type  yang:counter64;
            description "Counter for number of associated policies";
        } // END of policy-count definition.

        leaf status  {
            type  ipi-event-manager-types:event_manager_status_t;
            description "Status of event";
        } // END of status definition.

        leaf policy-map  {
            type  leafref {
                path  "/event-manager/policies/policy/config/policy-name";
            }
            description "Event-Policy mapping";
        } // END of policy-map definition.

    } // END of event-manager-event-state definition.
    grouping event-manager-action-config {
        description
            "Grouping for action configuration data";
        leaf action-name  {
            type  string {
                length "2..32";
                pattern "[^?' =,>|]+";
            }
            description "Name of action";
        } // END of action-name definition.

        leaf action-type  {
            type  ipi-event-manager-types:event_manager_action_type_t;
            mandatory true;
            description "Type of action";
        } // END of action-type definition.

        leaf action-script  {
            // when " ../action-type='script' ";
            type  string {
                length "4..64";
                pattern "[a-zA-Z][a-zA-Z0-9_]*.py";
            }
            mandatory true;
            description "Name of script";
        } // END of action-script definition.

    } // END of event-manager-action-config definition.
    grouping event-manager-action-state {
        description
            "Grouping for action operational state data";
        leaf trigger-count  {
            type  yang:counter64;
            description "Counter for number of times trigger is invoked";
        } // END of trigger-count definition.

        leaf policy-count  {
            type  yang:counter64;
            description "Counter for number of associated policies";
        } // END of policy-count definition.

        leaf status  {
            type  ipi-event-manager-types:event_manager_status_t;
            description "Status of action";
        } // END of status definition.

        leaf-list policy-map  {
            type  leafref {
                path  "/event-manager/policies/policy/config/policy-name";
            }
            description "Action-Policy Mapping";
        } // END of policy-map definition.

    } // END of event-manager-action-state definition.
    grouping event-manager-policy-config {
        description
            "Grouping for policy configuration data";
        leaf policy-name  {
            type  string {
                length "2..32";
                pattern "[^?' =,>|]+";
            }
            description "Name of policy";
        } // END of policy-name definition.

        leaf event-name  {
            type  leafref {
                path  "/event-manager/event-entries/event-entry/event-name";
            }
            mandatory true;
            description "Name of event";
        } // END of event-name definition.

        leaf action-name  {
            type  leafref {
                path  "/event-manager/action-entries/action-entry/action-name";
            }
            mandatory true;
            description "Name of action";
        } // END of action-name definition.

    } // END of event-manager-policy-config definition.
    grouping event-manager-policy-state {
        description
            "Grouping for policy operational state data";
        leaf trigger-count  {
            type  yang:counter64;
            description "Counter for number of times trigger is invoked";
        } // END of trigger-count definition.

        leaf status  {
            type  ipi-event-manager-types:event_manager_status_t;
            description "Policy status";
        } // END of status definition.

        leaf last-execution-status  {
            type  ipi-event-manager-types:event_manager_execution_status_t;
            default "Not-Run";
            description "Last execution status of policy";
        } // END of last-execution-status definition.

        leaf last-execution-time  {
            type  string {
                length "1..1965";
            }
            description "Last execution time of policy";
        } // END of last-execution-time definition.

    } // END of event-manager-policy-state definition.
    grouping event-manager-events-top {
        description
            "Grouping for Event List Configurations";
        container event-entries {
            when " /ipi-event-manager:event-manager/ipi-event-manager:config/ipi-event-manager:feature ";
            description
                "Event Manager Event Configurations";

            list event-entry {
                key "event-name";
                max-elements 50;
                description
                    "List of event entries";
                leaf event-name  {
                    type  leafref {
                        path  "../config/event-name";
                    }
                    description "Name of event";
                } // END of event-name definition.

                container config {
                    description
                        "Configuration Data for event entry";
                    uses event-manager-event-config;
                } // END of config-container definition.
                container state {
                    config false;
                    description
                        "Operational state data for event entry";
                    uses event-manager-event-config;
                    uses event-manager-event-state;
                } // END of state-container definition.
            } // End of event-entry-list
        } // END of event-entries-container definition.
    } // END of event-manager-events-top definition.
    grouping event-manager-actions-top {
        description
            "Grouping for Action List Configurations";
        container action-entries {
            when " /ipi-event-manager:event-manager/ipi-event-manager:config/ipi-event-manager:feature ";
            description
                "Event Manager Action Configurations";

            list action-entry {
                key "action-name";
                max-elements 50;
                description
                    "List of action entries";
                leaf action-name  {
                    type  leafref {
                        path  "../config/action-name";
                    }
                    description "Name of action";
                } // END of action-name definition.

                container config {
                    description
                        "Configuration Data for Action Entry";
                    uses event-manager-action-config;
                } // END of config-container definition.
                container state {
                    config false;
                    description
                        "Operational state data for Action Entry";
                    uses event-manager-action-config;
                    uses event-manager-action-state;
                } // END of state-container definition.
            } // End of action-entry-list
        } // END of action-entries-container definition.
    } // END of event-manager-actions-top definition.
    grouping event-manager-policies-top {
        description
            "Grouping for Policy Configurations";
        container policies {
            when " /ipi-event-manager:event-manager/ipi-event-manager:config/ipi-event-manager:feature ";
            description
                "Event Manager Policy configurations";

            list policy {
                key "policy-name";
                max-elements 50;
                description
                    "List of policy entries";
                leaf policy-name  {
                    type  leafref {
                        path  "../config/policy-name";
                    }
                    description "Name of policy";
                } // END of policy-name definition.

                container config {
                    description
                        "Configuration Data for policy entry";
                    uses event-manager-policy-config;
                } // END of config-container definition.
                container state {
                    config false;
                    description
                        "Operational state data for policy entry";
                    uses event-manager-policy-config;
                    uses event-manager-policy-state;
                } // END of state-container definition.
            } // End of policy-list
        } // END of policies-container definition.
    } // END of event-manager-policies-top definition.

    grouping  event-manager-grouping {
    description
        "Event Manager configuration";
    container event-manager {
        if-feature feature-list:HAVE_VLOGD;
        if-feature feature-list:HAVE_EVENT_MANAGER;
        description
            "Event Manager configuration";
        container config {
            description
                "Configuration data for Event Manager";
            uses event-manager-config;
        } // END of config-container definition.
        container state {
            config false;
            description
                "Operational state data for Event Manager";
            uses event-manager-config;
        } // END of state-container definition.
        uses event-manager-events-top;
        uses event-manager-actions-top;
        uses event-manager-policies-top;
    } // END of event-manager-container definition.
    } // END of event-manager-grouping definition.

    uses event-manager-grouping;

    rpc event-manager-clear-statistics-all {
        if-feature feature-list:HAVE_VLOGD;
        if-feature feature-list:HAVE_EVENT_MANAGER;
        description "Use this RPC to clear event-manager statistics for all policies";
    }

    rpc event-manager-clear-statistics-on-policy {
        if-feature feature-list:HAVE_VLOGD;
        if-feature feature-list:HAVE_EVENT_MANAGER;
        description "Use this RPC to clear event-manager statistics for a policy";
        input  {
            leaf policy-name  {
                type string;
                mandatory true;
                description "Policy Name";
            }
        }
    }

}
