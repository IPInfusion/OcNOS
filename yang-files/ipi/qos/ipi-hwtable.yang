/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-hwtable.yang
*
*/

module ipi-hwtable {

    yang-version 1.1;

    namespace   "http://www.ipinfusion.com/yang/ocnos/ipi-hwtable";

    prefix "ipi-hwtable";

    import cml-data-types {
        prefix cml-data-types;
        revision-date 2026-05-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Hardware Table monitoring";


    revision "2023-04-04" {
        description "Initial release";
        reference " 0.1.0.";
    }



    notification hwtable-monitor-full-notification {
        if-feature feature-list:HAVE_SNMP;
        if-feature feature-list:NOT_HAVE_SWFWDR;

        description "Hardware table usage is full.";

        leaf severity {
            type cml-data-types:cml_notif_severity_t;
            description "Notification severity level (value: MAJOR)";
        }

        leaf eventClass {
            type cml-data-types:cml_notif_class_t;
            description "Notification event class (value: MESSAGE)";
        }

        leaf message {
            type string;
            description " alarm message notification";
        }
    }

    notification hwtable-monitor-full-clear-notification {
        if-feature feature-list:HAVE_SNMP;
        if-feature feature-list:NOT_HAVE_SWFWDR;

        description "Hardware table usage is no longer full.";

        leaf severity {
            type cml-data-types:cml_notif_severity_t;
            description "Notification severity level (value: WARNING)";
        }

        leaf eventClass {
            type cml-data-types:cml_notif_class_t;
            description "Notification event class (value: MESSAGE)";
        }

        leaf message {
            type string;
            description " alarm message notification";
        }
    }

}
