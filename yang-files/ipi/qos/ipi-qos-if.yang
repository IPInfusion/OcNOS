/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-qos-if.yang
*
*/

module ipi-qos-if {

    yang-version 1.1;

    namespace   "http://www.ipinfusion.com/yang/ocnos/ipi-qos-if";

    prefix "ipi-qos-if";

    import cml-data-types {
        prefix cml-data-types;
        revision-date 2026-05-15;
    }

    import ietf-yang-types {
        prefix yang;
        revision-date 2013-07-15;
    }

    import ipi-qos {
        prefix ipi-qos;
        revision-date 2026-09-09;
    }

    import ipi-qos-types {
        prefix ipi-qos-types;
        revision-date 2026-09-09;
    }

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Quality of Service (QoS) interface information";


    revision "2026-09-09" {
        description "Changed the helpstring for QOS_THRESHOLD_T";
        reference " 0.5.17.";
    }

    revision "2026-01-29" {
        description "Removed ingress-pg-map profile deletion on switchport operations";
        reference " 0.5.16.";
    }

    revision "2026-01-20" {
        description "service policy to be cleared from DB on configuring mlag to sa";
        reference " 0.5.15.";
    }

    revision "2026-01-16" {
        description "Added dependentObject tag for match queue";
        reference " 0.5.14.";
    }

    revision "2025-12-02" {
        description "shape rate configs to be removed on configuring the channel-group and unconfiguring the channel-group";
        reference " 0.5.13.";
    }

    revision "2025-11-28" {
        description "Handled QoS profiles deletion when aggregator is added to interface";
        reference " 0.5.12.";
    }

    revision "2025-11-25" {
        description "Updated shape rate help string for q2c";
        reference " 0.5.11.";
    }

    revision "2025-11-10" {
        description "Corrected missing feature validateion for inner-cos command";
        reference " 0.5.10.";
    }

    revision "2025-11-07" {
        description "Added missing dependentObject tag for interface dependency";
        reference " 0.5.9.";
    }

    revision "2025-10-14" {
        description "Added a new attribute inner-cos";
        reference " 0.5.8.";
    }

    revision "2025-10-11" {
        description "Handled QoS profiles deletion when MLAG is added to interface";
        reference " 0.5.7.";
    }

    revision "2025-10-10" {
        description "Handled Ingress PG profile deletion when MLAG is added to interface";
        reference " 0.5.6.";
    }

    revision "2025-09-26" {
        description "Added a new attribute lag-shaper";
        reference " 0.5.5.";
    }

    revision "2025-09-15" {
        description "Added when tag to rate attribute";
        reference " 0.5.4.";
    }

    revision "2025-09-10" {
        description "Egress Dynamic ECN profile support for Tomahawk 5";
        reference " 0.5.3.";
    }

    revision "2025-09-04" {
        description "Removed EVPN_IRB_IF_MODE while configuring IRB interface";
        reference " 0.5.2.";
    }

    revision "2025-08-25" {
        description "pg-map profile support for DC boards";
        reference " 0.5.1.";
    }

    revision "2025-08-20" {
        description "Add queue-size state data per queue to the interfaces";
        reference " 0.5.0.";
    }

    revision "2025-07-03" {
        description "added dependent obj to remove service-policy when member aggreagtion configured";
        reference " 0.4.23.";
    }

    revision "2025-06-20" {
        description "Fixed dbsync issues while reconfiguring shape";
        reference " 0.4.22.";
    }

    revision "2025-06-15" {
        description "Remove aggregator related triggers in qos interfaces, and keep qos interface name config when aggregating";
        reference " 0.4.21.";
    }

    revision "2025-06-05" {
        description "Added when tag to delete the service-policy configs when we attach po or sa to member";
        reference " 0.4.20.";
    }

    revision "2025-04-30" {
        description "wred limits max-threshold updated for DC boards";
        reference " 0.4.19.";
    }

    revision "2025-04-08" {
        description "Add dependencies between copp service-policy and other objects and access-list";
        reference " 0.4.18.";
    }

    revision "2025-03-07" {
        description "Fixed new dbsync issues caused by the BCOM-124 fix";
        reference " 0.4.17.";
    }

    revision "2025-03-03" {
        description "Changed the class-map and policy-map name length from 32 to 64";
        reference " 0.4.16.";
    }

    revision "2025-02-06" {
        description "Block CLI for DSCP-ENCAP for Q2";
        reference " 0.4.14.";
    }

    revision "2025-01-31" {
        description "Create/delete QoS interfaces as needed in order to show statistics in default queuing policy maps";
        reference " 0.4.15.";
    }

    revision "2025-01-14" {
        description "New type CoPP for clear qos statistics command";
        reference " 0.4.13.";
    }

    revision "2025-01-13" {
        description "Exceed action datatype for CoPP removed";
        reference " 0.4.12.";
    }

    revision "2025-01-06" {
        description "Changed the data type of rate kbps attribute";
        reference " 0.4.11.";
    }

    revision "2025-01-03" {
        description "Revert Block CLI for DSCP-ENCAP for Q2";
        reference " 0.4.10.";
    }

    revision "2024-12-30" {
        description "Block CLI for DSCP-ENCAP for Q2";
        reference " 0.4.9.";
    }

    revision "2024-12-20" {
        description "Converting qos CLI from string to enum and modifying the display strings";
        reference " 6.0.14.";
    }

    revision "2024-11-27" {
        description "Added new policy-map, class-map of type copp";
        reference " 0.4.8.";
    }

    revision "2024-09-25" {
        description "Block qos untagged-priority command for Q2";
        reference " 0.4.7.";
    }

    revision "2024-07-18" {
        description "Added support for lag memeber shaper config";
        reference " 0.4.6.";
    }

    revision "2024-06-19" {
        description "set color option added for Q2 platform";
        reference " 0.4.5.";
    }

    revision "2024-06-12" {
        description "Inclusion of streaming telemetry yaml file";
        reference " 0.4.4.";
    }

    revision "2024-06-06" {
        description "Masked policy-map bandwidth command for Marvell platform";
        reference " 0.2.2.";
    }

    revision "2024-05-14" {
        description "Added When flag for qos-service-policy to delete the attribute when encapsulation is deleted";
        reference " 0.4.3.";
    }

    revision "2024-04-12" {
        description "Cleanup shape config properly from aggregated members";
        reference " 0.4.2.";
    }

    revision "2024-02-06" {
        description "Masked a redundant option for QOS_TRAFFIC_TYPE_T datatype for Marvell platform";
        reference " 0.2.1.";
    }

    revision "2024-01-09" {
        description "Added HAVE_CUSTOM2_QOS flag in conditional check of aggregator member";
        reference " 0.4.1.";
    }

    revision "2023-11-27" {
        description "Changed WRED CLI using HAVE_CUSTOM1_QOS option for Marvell";
        reference " 0.3.9.";
    }

    revision "2023-11-09" {
        description "Added HAVE_CUSTOM4_QOS flag for QOS_TRAFFIC_TYPE_T datatype";
        reference " 0.3.8.";
    }

    revision "2023-10-16" {
        description "Added leafref for exp-encapsulation";
        reference " 0.3.7.";
    }

    revision "2023-08-21" {
        description "Added HAVE_CUSTOM4_QOS flag for label-switching";
        reference " 0.3.6.";
    }

    revision "2023-06-29" {
        description "Added HAVE_CUSTOM4_QOS flag for Marvell AC5X";
        reference " 0.3.5.";
    }

    revision "2023-04-17" {
        description "updated when tag for /interfaces/interface/map-profile";
        reference " 0.3.4.";
    }

    revision "2022-12-30" {
        description "Fixed the trigger to remove traffic-shaper after switchport removal";
        reference " 0.3.3.";
    }

    revision "2022-12-07" {
        description "Removed the prependstr profile-map and used the vlaue map-profile in cliprependstr";
        reference " 0.3.2.";
    }

    revision "2022-12-05" {
        description "Updated when expressions";
        reference " 0.3.1.";
    }

    revision "2022-12-04" {
        description "Reverting fix of JIRA-62451 since its breaking QoS CLIs";
        reference " 0.4.0.";
    }

    revision "2022-11-29" {
        description "Addressed make cmlgen warnings";
        reference " 0.3.0.";
    }

    revision "2022-11-04" {
        description "Fixed the trigger to remove egress service-policy after switchport removal";
        reference " 0.2.0.";
    }

    revision "2022-09-30" {
        description "Import cml-data-types used by notifications";
        reference " 0.1.7.";
    }

    revision "2022-09-27" {
        description "Added trigger to delete service-policy when port mode changes";
        reference " 0.1.6.";
    }

    revision "2022-08-26" {
        description "changed mapping profile helpstring from queue to traffic-class";
        reference " 0.1.5.";
    }

    revision "2022-07-30" {
        description "Updated when expressions in yang";
        reference " 0.2.0.";
    }

    revision "2022-07-28" {
        description "Added dependentObject for policy-map configs in interface";
        reference " 0.1.4.";
    }

    revision "2022-07-19" {
        description "Removed autoPopulate from interfaces container";
        reference " 0.1.3.";
    }

    revision "2022-07-16" {
        description "Global yang model name is changed as Global TE yang model";
        reference " 0.1.2.";
    }

    revision "2022-07-01" {
        description "Added pattern check for bandwidth related commands in MPLS yang model";
        reference " 0.1.1.";
    }

    revision "2022-06-21" {
        description "Changes in the MPLS yang model w.r.t to admin-groups";
        reference " 0.1.0.";
    }

    revision "2022-06-15" {
        description "Changed the interface name key to be a leafref to the attribute name on config container";
        reference "Initial Version";
    }

    revision "2022-06-01" {
        description "Updated the yang file with feature";
        reference "Initial Version";
    }

    revision "2022-04-28" {
        description "Renamed EVPN IRB related attributes";
        reference "Initial Version";
    }

    revision "2021-09-01" {
        description "Changed base interface module's switchport attribute name and the datatype from bool to empty";
        reference "Initial Version";
    }

    revision "2021-07-06" {
        description "Add support to IP precedence(TOS) related profile.";
        reference "Initial Version";
    }

    revision "2021-06-09" {
        description "Merged 'type-qos' and 'type-queuing' with 'policy-map-name'.";
        reference "Initial Version";
    }

    revision "2021-06-05" {
        description "Added dscp-encap and exp-to-queue profiles.";
        reference "Initial Version";
    }

    revision "2021-06-04" {
        description "Changed notification type to ALARM";
        reference "Initial Version";
    }

    revision "2021-05-06" {
        description "Added type attr in service-policy";
        reference "Initial Version";
    }

    revision "2021-05-05" {
        description "Added length in policies names";
        reference "Initial Version";
    }

    revision "2021-03-23" {
        description "Removed mutation-map related objects";
        reference "Initial Version";
    }

    revision "2020-12-04" {
        description "Restructured module as per open-config style";
        reference "Initial Version";
    }

    revision "2018-06-21" {
        description "Initial Version";
        reference "Initial Version";
    }

    grouping qos-interface-config {
        description
            "Grouping for interface QoS configuration";
        leaf name  {
            type  leafref {
                path  "/ipi-interface:interfaces/ipi-interface:interface/ipi-interface:name";
            }
            description "Interface name for which QoS is being configured";
        } // END of name definition.

        leaf untagged-priority  {
            when " /ipi-interface:interfaces/ipi-interface:interface/ipi-interface:config/ipi-interface:enable-switchport ";
            type  uint8 {
                 range "0..7"  {
                    description "0..7: Supported range 0 - 7";
                 }
            }
            description "Use this attribute to set internal priority for untagged traffic on L2
                        interface";
        } // END of untagged-priority definition.

        leaf trust-dscp  {
            when " /ipi-interface:interfaces/ipi-interface:interface/ipi-interface:config/ipi-interface:enable-switchport ";
            type  empty;
            description "Use this command to classify the ingress traffic based on DSCP map on
                        L2 interface";
        } // END of trust-dscp definition.

        leaf lag-shaper  {
            if-feature feature-list:HAVE_DNX;
            type  ipi-qos-types:qos_lag_shaper_t;
            description "Use this command to enable/disable lag shaper";
        } // END of lag-shaper definition.

        leaf lag-shaper-unit  {
            // when " ../lag-shaper ";
            if-feature feature-list:HAVE_DNX;
            type  uint8 {
                 range "0..1"  {
                    description "0..1: Supported range 0 - 1";
                 }
            }
            description "Use this command to enable/disable lag shaper";
        } // END of lag-shaper-unit definition.

    } // END of qos-interface-config definition.
    grouping qos-traffic-shape-config {
        description
            "Grouping for QoS traffic shape configuration";
        leaf rate  {
            // when " ../rate-unit + !contain(ipi-interface:interfaces/interface/name, 'bvi') ";
            type  uint64 {
                 range "1..1000000000"  {
                    description "1..1000000000:Not Feature : HAVE_CUSTOM2_QOS  Supported range 1 -
                            1000000000Feature : HAVE_CUSTOM2_QOS Supported range 1 - 1000000000";
                 }
            }
            mandatory true;
            description "Use this attribute to configure shaping on an egress queue to impose a
                        maximum rate on it";
        } // END of rate definition.

        leaf rate-unit  {
            // when " ../rate ";
            type  ipi-qos-types:qos_shape_rate_unit_t;
            mandatory true;
            description "Use this attribute to set the shape rate unit";
        } // END of rate-unit definition.

        leaf burst-rate  {
            // when " ../rate ";
            if-feature feature-list:NOT_HAVE_CUSTOM2_QOS;
            type  uint64 {
                 range "1..1000000"  {
                    description "1..1000000: Supported range 1 - 1000000";
                 }
            }
            mandatory true;
            description "Use this attribute to set a shape rate burst";
        } // END of burst-rate definition.

    } // END of qos-traffic-shape-config definition.
    grouping qos-traffic-shape-top {
        description
            "Grouping for QoS traffic shape";
        container traffic-shape {
            description
                "Configuration data for QoS traffic shape";
            container config {
                // when " ../config/rate + ../config/rate-unit ";
                presence "true";
                description
                    "Configuration data for QoS traffic shape";
                uses qos-traffic-shape-config;
            } // END of config-container definition.
            container state {
                config false;
                description
                    "Operational state data for QoS traffic shape";
                uses qos-traffic-shape-config;
            } // END of state-container definition.
        } // END of traffic-shape-container definition.
    } // END of qos-traffic-shape-top definition.
    grouping qos-interface-remark-top {
        description
            "Grouping for QoS remark";
        container remark {
            when " /ipi-qos:qos/ipi-qos:global/ipi-qos:config/ipi-qos:enable-qos = 'enable' ";
            description
                "Configuration data for QoS remark";
            container config {
                description
                    "Configuration data for QoS remark";
                uses qos-interface-remark-config;
            } // END of config-container definition.
            container state {
                config false;
                description
                    "Operational state data for QoS remark";
                uses qos-interface-remark-config;
            } // END of state-container definition.
        } // END of remark-container definition.
    } // END of qos-interface-remark-top definition.
    grouping qos-interface-remark-config {
        description
            "Grouping for QoS remark configuration";
        leaf cos  {
            when " /ipi-interface:interfaces/ipi-interface:interface/ipi-interface:config/ipi-interface:enable-switchport ";
            type  ipi-qos-types:cml_remark_state_t;
            description "Use this command to enable/disable remarking of CoS set by the egress
                        map";
        } // END of cos definition.

        leaf inner-cos  {
            when " /ipi-interface:interfaces/ipi-interface:interface/ipi-interface:config/ipi-interface:enable-switchport ";
            if-feature feature-list:HAVE_CUSTOM2_QOS;
            if-feature feature-list:HAVE_SUBINTERFACE;
            type  empty;
            description "Remarking of CoS for inner-vlan(applies for inner-vlan updated by
                        rewrite)";
        } // END of inner-cos definition.

        leaf dei  {
            when " /ipi-interface:interfaces/ipi-interface:interface/ipi-interface:config/ipi-interface:enable-switchport ";
            if-feature feature-list:NOT_HAVE_CUSTOM2_QOS;
            type  ipi-qos-types:cml_remark_state_t;
            description "Use this command to enable/disable remarking of DEI set by the egress
                        map";
        } // END of dei definition.

        leaf dscp  {
            type  ipi-qos-types:cml_remark_state_t;
            description "Use this command to enable/disable remarking of DSCP set by the egress
                        map";
        } // END of dscp definition.

    } // END of qos-interface-remark-config definition.
    grouping qos-map-profile-ref-config {
        description
            "Grouping for QoS map profile reference configuration";
        leaf cos-to-queue  {
            when " /ipi-interface:interfaces/ipi-interface:interface/ipi-interface:config/ipi-interface:enable-switchport ";
            type  string {
                length "1..1965";
                pattern "[^?' =,>|]+";
            }
            description "Use this attibute to attach a CoS to Traffic-Class profile to the
                        interface";
        } // END of cos-to-queue definition.

        leaf dscp-to-dscp  {
            // when " not(/ipi-interface:interfaces/ipi-interface:interface/ipi-interface:config/ipi-interface:enable-switchport) ";
            if-feature feature-list:HAVE_CUSTOM2_QOS_OR_HAVE_CUSTOM4_QOS;
            type  string {
                length "1..1965";
                pattern "[^?' =,>|]+";
            }
            description "Use this attibute to attach a DSCP to DSCP profile to the interface";
        } // END of dscp-to-dscp definition.

        leaf precedence-to-precedence  {
            // when " not(/ipi-interface:interfaces/ipi-interface:interface/ipi-interface:config/ipi-interface:enable-switchport) ";
            if-feature feature-list:HAVE_CUSTOM2_QOS_OR_HAVE_CUSTOM4_QOS;
            type  string {
                length "1..1965";
                pattern "[^?' =,>|]+";
            }
            description "Use this attibute to attach a Precedence to Precedencde profile to the
                        interface";
        } // END of precedence-to-precedence definition.

        leaf dscp-to-queue  {
            type  string {
                length "1..1965";
                pattern "[^?' =,>|]+";
            }
            description "Use this attibute to attach a DSCP to Traffic-Class profile to the
                        interface";
        } // END of dscp-to-queue definition.

        leaf precedence-to-queue  {
            type  string {
                length "1..1965";
                pattern "[^?' =,>|]+";
            }
            description "Use this attibute to attach a Precedence to Traffic-Class profile to
                        the interface";
        } // END of precedence-to-queue definition.

        leaf exp-encapsulation  {
            // when " not(/ipi-interface:interfaces/ipi-interface:interface/ipi-interface:config/ipi-interface:enable-switchport) ";
            if-feature feature-list:HAVE_DIFFSERV;
            if-feature feature-list:HAVE_CUSTOM2_QOS;
            if-feature feature-list:NOT_HAVE_CUSTOM3_QOS;
            type  leafref {
                path  "/ipi-qos:qos/ipi-qos:global/ipi-qos:map-profile/ipi-qos:exp-encapsulation-profiles/ipi-qos:exp-encapsulation-profile/ipi-qos:name";
            }
            description "Use this attibute to attach a MPLS experimental encapsulation profile
                        to the interface";
        } // END of exp-encapsulation definition.

        leaf dscp-encapsulation  {
            // when " not(/ipi-interface:interfaces/ipi-interface:interface/ipi-interface:config/ipi-interface:enable-switchport) ";
            if-feature feature-list:HAVE_CUSTOM2_QOS;
            if-feature feature-list:NOT_HAVE_CUSTOM3_QOS;
            type  string {
                length "1..1965";
                pattern "[^?' =,>|]+";
            }
            description "Use this attibute to attach a MPLS dscp encapsulation profile to the
                        interface";
        } // END of dscp-encapsulation definition.

        leaf queue-color-to-cos  {
            when " /ipi-interface:interfaces/ipi-interface:interface/ipi-interface:config/ipi-interface:enable-switchport ";
            type  string {
                length "1..1965";
                pattern "[^?' =,>|]+";
            }
            description "Use this attibute to attach a Traffic-Class color to CoS profile to
                        the interface";
        } // END of queue-color-to-cos definition.

        leaf queue-color-to-dscp  {
            if-feature feature-list:HAVE_CUSTOM1_QOS_OR_HAVE_CUSTOM4_QOS;
            type  string {
                length "1..1965";
                pattern "[^?' =,>|]+";
            }
            description "Use this attibute to attach a Traffic-Class color to DSCP profile to
                        the interface";
        } // END of queue-color-to-dscp definition.

        leaf queue-to-precedence  {
            if-feature feature-list:HAVE_CUSTOM1_QOS_OR_HAVE_CUSTOM4_QOS;
            type  string {
                length "1..1965";
                pattern "[^?' =,>|]+";
            }
            description "Use this attibute to attach a queue color to Precedence profile to the
                        interface";
        } // END of queue-to-precedence definition.

        leaf queue-to-exp  {
            // when " not(/ipi-interface:interfaces/ipi-interface:interface/ipi-interface:config/ipi-interface:enable-switchport) ";
            if-feature feature-list:HAVE_DIFFSERV;
            if-feature feature-list:HAVE_CUSTOM1_QOS_OR_HAVE_CUSTOM3_QOS_OR_HAVE_CUSTOM4_QOS;
            type  string {
                length "1..1965";
                pattern "[^?' =,>|]+";
            }
            description "Use this attibute to attach a Traffic-Class to exp profile to the
                        interface";
        } // END of queue-to-exp definition.

        leaf ingress-pg-map  {
            if-feature feature-list:HAVE_BUFFER_TUNING;
            if-feature feature-list:HAVE_CUSTOM1_QOS;
            type  string {
                length "1..1965";
                pattern "[^?' =,>|]+";
            }
            description "Use this attibute to attach a ingress PG map profile to the interface";
        } // END of ingress-pg-map definition.

        leaf egress-dynamic-ecn  {
            type  string {
                length "1..31";
                pattern "[^?' =,>|]+";
            }
            description "Use this attibute to attach an egress dynamic ECN profile to the
                        interface";
        } // END of egress-dynamic-ecn definition.

    } // END of qos-map-profile-ref-config definition.
    grouping qos-map-profile-ref-top {
        description
            "Grouping for QoS map profile reference";
        container map-profile {
            if-feature feature-list:HAVE_QOS_MAPPING_PROFILE;
            description
                "Configuration data for QoS map profile reference";
            container config {
                description
                    "Configuration data for QoS map profile reference";
                uses qos-map-profile-ref-config;
            } // END of config-container definition.
            container state {
                config false;
                description
                    "Operational state data for QoS map profile reference";
                uses qos-map-profile-ref-config;
            } // END of state-container definition.
        } // END of map-profile-container definition.
    } // END of qos-map-profile-ref-top definition.
    grouping qos-qos-statistics-state {
        description
            "Grouping for QoS qos statistics state";
        leaf matched-packets  {
            type  yang:counter64;
            description "The number of packets that matched the rules of class-map attached to
                        the interface";
        } // END of matched-packets definition.

        leaf matched-octets  {
            type  yang:counter64;
            description "The number of bytes that matched the rules of class-map attached to
                        the interface";
        } // END of matched-octets definition.

        leaf transmitted-packets  {
            type  yang:counter64;
            description "The number of packets that were transmitted that matched the rules of
                        class-map attached to the interface";
        } // END of transmitted-packets definition.

        leaf transmitted-octets  {
            type  yang:counter64;
            description "The number of bytes that were transmitted that matched the rules of
                        class-map attached to the interface";
        } // END of transmitted-octets definition.

        leaf dropped-packets  {
            type  yang:counter64;
            description "The number of packets that were dropped due to policer action on the
                        class-map attached to the interface";
        } // END of dropped-packets definition.

        leaf dropped-octets  {
            type  yang:counter64;
            description "The number of bytes that were dropped due to policer action on the
                        class-map attached to the interface";
        } // END of dropped-octets definition.

    } // END of qos-qos-statistics-state definition.
    grouping qos-queue-mode-queue-size-state {
        description
            "Grouping for QoS queue size state";
        leaf max-threshold  {
            type  yang:counter64;
            description "This attribute stores the queue-size limits on egress queue";
        } // END of max-threshold definition.

        leaf max-threshold-type  {
            type  ipi-qos-types:qos_threshold_t;
            description "This attribute stores the queue-size unit";
        } // END of max-threshold-type definition.

    } // END of qos-queue-mode-queue-size-state definition.
    grouping qos-queue-mode-queue-size-top {
        description
            "Grouping for QoS queue size";
        container queue-size {
            config false;
            description
                "State data for QoS queue size";
            container state {
                config false;
                description
                    "Operational state data for QoS queue size";
                uses qos-queue-mode-queue-size-state;
            } // END of state-container definition.
        } // END of queue-size-container definition.
    } // END of qos-queue-mode-queue-size-top definition.
    grouping qos-queue-statistics-state {
        description
            "Grouping for QoS queue statistics state";

        list queue {
            key "id";
            config false;
            description
                "Operational state data list for QoS queue statistics";
            leaf id  {
                type  uint8;
                description "An unique number associated with the queue";
            } // END of id definition.

            container counters {
                config false;
                description
                    "Operational state data for QoS queue statistics counters";
                leaf total-transmitted-packets  {
                    type  yang:counter64;
                    description "Total number of packets transmitted out of the queue";
                } // END of total-transmitted-packets definition.

                leaf total-transmitted-octets  {
                    type  yang:counter64;
                    description "Total number of octets transmitted out of the queue";
                } // END of total-transmitted-octets definition.

                leaf total-dropped-packets  {
                    type  yang:counter64;
                    description "Total number of packets dropped in the queue";
                } // END of total-dropped-packets definition.

                leaf total-dropped-octets  {
                    type  yang:counter64;
                    description "Total number of octets dropped in the queue";
                } // END of total-dropped-octets definition.

                leaf green-transmitted-packets  {
                    type  yang:counter64;
                    description "Number of green packets transmitted out of the queue";
                } // END of green-transmitted-packets definition.

                leaf non-green-transmitted-packets  {
                    type  yang:counter64;
                    description "Number of yellow and red (when applicable) packets transmitted out of
                                the queue";
                } // END of non-green-transmitted-packets definition.

                leaf green-dropped-packets  {
                    type  yang:counter64;
                    description "Number of green packets dropped in the queue";
                } // END of green-dropped-packets definition.

                leaf yellow-dropped-packets  {
                    type  yang:counter64;
                    description "Number of yellow packets dropped in the queue";
                } // END of yellow-dropped-packets definition.

                leaf red-dropped-packets  {
                    type  yang:counter64;
                    description "Number of red packets dropped in the queue";
                } // END of red-dropped-packets definition.

                leaf rate-kbps  {
                    type  decimal64 {
                         fraction-digits 3;                    }
                    description "Queue rate in Kbps";
                } // END of rate-kbps definition.

                leaf rate-mbps  {
                    type  decimal64 {
                         fraction-digits 6;                    }
                    description "Queue rate in Mbps";
                } // END of rate-mbps definition.

                leaf rate-gbps  {
                    type  decimal64 {
                         fraction-digits 6;                    }
                    description "Queue rate in Gbps";
                } // END of rate-gbps definition.

            } // END of counters-container definition.
            uses qos-queue-mode-queue-size-top;
        } // End of queue-list
    } // END of qos-queue-statistics-state definition.
    grouping qos-service-policy-ingress-state {
        description
            "Grouping for QoS input service policy state";
        container class-maps-level-1 {
            config false;
            description
                "Operational state data for QoS input service policy";

            list class-map-level-1 {
                key "class-map-name-level-1";
                config false;
                description
                    "Operational state data list for QoS input service policy";
                leaf class-map-name-level-1  {
                    type  leafref {
                        path  "../state/class-map-name-level-1";
                    }
                    description "Name of the class-map attached to the interface";
                } // END of class-map-name-level-1 definition.

                container state {
                    config false;
                    description
                        "Operational state data for QoS statistics level 1";
                    leaf class-map-name-level-1  {
                        type  string {
                            length "1..1965";
                            pattern "[^?' =,>|]+";
                        }
                        description "Name of the class-map attached to the interface";
                    } // END of class-map-name-level-1 definition.

                    container counters {
                        config false;
                        description
                            "Operational state data for QoS statistics counters";
                        uses qos-qos-statistics-state;
                    } // END of counters-container definition.
                } // END of state-container definition.
                container class-maps-level-2 {
                    config false;
                    description
                        "Operational state data for QoS input service policy";

                    list class-map-level-2 {
                        key "class-map-name-level-2";
                        config false;
                        description
                            "Operational state data list for QoS input service policy";
                        leaf class-map-name-level-2  {
                            type  leafref {
                                path  "../state/class-map-name-level-2";
                            }
                            description "Name of the class-map attached to the interface";
                        } // END of class-map-name-level-2 definition.

                        container state {
                            config false;
                            description
                                "Operational state data for QoS statistics level 2";
                            leaf class-map-name-level-2  {
                                type  string {
                                    length "1..1965";
                                    pattern "[^?' =,>|]+";
                                }
                                description "Name of the class-map attached to the interface";
                            } // END of class-map-name-level-2 definition.

                            container counters {
                                config false;
                                description
                                    "Operational state data for QoS statistics counters";
                                uses qos-qos-statistics-state;
                            } // END of counters-container definition.
                        } // END of state-container definition.
                        container class-maps-level-3 {
                            config false;
                            description
                                "Operational state data for QoS input service policy";

                            list class-map-level-3 {
                                key "class-map-name-level-3";
                                config false;
                                description
                                    "Operational state data list for QoS input service policy";
                                leaf class-map-name-level-3  {
                                    type  leafref {
                                        path  "../state/class-map-name-level-3";
                                    }
                                    description "Name of the class-map attached to the interface";
                                } // END of class-map-name-level-3 definition.

                                container state {
                                    config false;
                                    description
                                        "Operational state data for QoS statistics level 3";
                                    leaf class-map-name-level-3  {
                                        type  string {
                                            length "1..1965";
                                            pattern "[^?' =,>|]+";
                                        }
                                        description "Name of the class-map attached to the interface";
                                    } // END of class-map-name-level-3 definition.

                                    container counters {
                                        config false;
                                        description
                                            "Operational state data for QoS statistics counters";
                                        uses qos-qos-statistics-state;
                                    } // END of counters-container definition.
                                } // END of state-container definition.
                            } // End of class-map-level-3-list
                        } // END of class-maps-level-3-container definition.
                    } // End of class-map-level-2-list
                } // END of class-maps-level-2-container definition.
            } // End of class-map-level-1-list
        } // END of class-maps-level-1-container definition.
    } // END of qos-service-policy-ingress-state definition.
    grouping qos-service-policy-egress-state {
        description
            "Grouping for QoS output service policy state";
        container class-maps-level-1 {
            config false;
            description
                "Operational state data for QoS output service policy";

            list class-map-level-1 {
                key "class-map-name-level-1";
                config false;
                description
                    "Operational state data list for QoS output service policy";
                leaf class-map-name-level-1  {
                    type  leafref {
                        path  "../state/class-map-name-level-1";
                    }
                    description "Name of the class-map attached to the interface";
                } // END of class-map-name-level-1 definition.

                container state {
                    config false;
                    description
                        "Operational state data for QoS statistics level one";
                    leaf class-map-name-level-1  {
                        type  string {
                            length "1..1965";
                            pattern "[^?' =,>|]+";
                        }
                        description "Name of the class-map attached to the interface";
                    } // END of class-map-name-level-1 definition.

                    container queues {
                        config false;
                        description
                            "Operational state data for QoS queue statistics";
                        uses qos-queue-statistics-state;
                    } // END of queues-container definition.
                } // END of state-container definition.
                container class-maps-level-2 {
                    config false;
                    description
                        "Operational state data for QoS input service policy";

                    list class-map-level-2 {
                        key "class-map-name-level-2";
                        config false;
                        description
                            "Operational state data list for QoS input service policy";
                        leaf class-map-name-level-2  {
                            type  leafref {
                                path  "../state/class-map-name-level-2";
                            }
                            description "Name of the class-map attached to the interface";
                        } // END of class-map-name-level-2 definition.

                        container state {
                            config false;
                            description
                                "Operational state data for QoS statistics level two";
                            leaf class-map-name-level-2  {
                                type  string {
                                    length "1..1965";
                                    pattern "[^?' =,>|]+";
                                }
                                description "Name of the class-map attached to the interface";
                            } // END of class-map-name-level-2 definition.

                            container queues {
                                config false;
                                description
                                    "Operational state data for QoS queue statistics";
                                uses qos-queue-statistics-state;
                            } // END of queues-container definition.
                        } // END of state-container definition.
                        container class-maps-level-3 {
                            config false;
                            description
                                "Operational state data for QoS input service policy";

                            list class-map-level-3 {
                                key "class-map-name-level-3";
                                config false;
                                description
                                    "Operational state data list for QoS input service policy";
                                leaf class-map-name-level-3  {
                                    type  leafref {
                                        path  "../state/class-map-name-level-3";
                                    }
                                    description "Name of the class-map attached to the interface";
                                } // END of class-map-name-level-3 definition.

                                container state {
                                    config false;
                                    description
                                        "Operational state data for QoS statistics level three";
                                    leaf class-map-name-level-3  {
                                        type  string {
                                            length "1..1965";
                                            pattern "[^?' =,>|]+";
                                        }
                                        description "Name of the class-map attached to the interface";
                                    } // END of class-map-name-level-3 definition.

                                    container queues {
                                        config false;
                                        description
                                            "Operational state data for QoS queue statistics";
                                        uses qos-queue-statistics-state;
                                    } // END of queues-container definition.
                                } // END of state-container definition.
                            } // End of class-map-level-3-list
                        } // END of class-maps-level-3-container definition.
                    } // End of class-map-level-2-list
                } // END of class-maps-level-2-container definition.
            } // End of class-map-level-1-list
        } // END of class-maps-level-1-container definition.
    } // END of qos-service-policy-egress-state definition.
    grouping qos-service-policy-config {
        description
            "Grouping for QoS service policy configuration";
        leaf type-qos-policy-map-name  {
            type  string {
                length "1..64";
                pattern "[^?' =,>|]+";
            }
            description "Use this attribute to attach a service-policy of type qos to the
                        interface";
        } // END of type-qos-policy-map-name definition.

    } // END of qos-service-policy-config definition.
    grouping qos-service-policy-egress-config {
        description
            "Grouping for QoS service policy egress configuration";
        leaf type-qos-policy-map-name  {
            if-feature feature-list:HAVE_CUSTOM1_QOS_OR_HAVE_CUSTOM3_QOS_OR_HAVE_CUSTOM4_QOS;
            type  string {
                length "1..64";
                pattern "[^?' =,>|]+";
            }
            description "Use this attribute to attach a service-policy of type qos to the
                        interface";
        } // END of type-qos-policy-map-name definition.

        leaf type-queuing-policy-map-name  {
            type  string {
                length "1..64";
                pattern "[^?' =,>|]+";
            }
            description "Use this attribute to attach a service-policy of type queue to the
                        interface";
        } // END of type-queuing-policy-map-name definition.

    } // END of qos-service-policy-egress-config definition.
    grouping qos-service-policy-ingress-top {
        description
            "Grouping for QoS input service policy";
        container ingress {
            description
                "Configuration data for QoS input service policy";
            container config {
                description
                    "Configuration data for QoS input service policy";
                uses qos-service-policy-config;
            } // END of config-container definition.
            container state {
                config false;
                description
                    "Operational state data for QoS input service policy";
                uses qos-service-policy-config;
            } // END of state-container definition.
            uses qos-service-policy-ingress-state;
        } // END of ingress-container definition.
    } // END of qos-service-policy-ingress-top definition.
    grouping qos-service-policy-egress-top {
        description
            "Grouping for QoS output service policy";
        container egress {
            description
                "Configuration data for QoS output service policy";
            container config {
                description
                    "Configuration data for QoS output service policy";
                uses qos-service-policy-egress-config;
            } // END of config-container definition.
            container state {
                config false;
                description
                    "Operational state data for QoS output service policy";
                uses qos-service-policy-egress-config;
            } // END of state-container definition.
            uses qos-service-policy-egress-state;
        } // END of egress-container definition.
    } // END of qos-service-policy-egress-top definition.
    grouping qos-service-policy-top {
        description
            "Grouping for QoS service policy";
        container service-policy {
            description
                "Configuration data for QoS service policy";
            uses qos-service-policy-ingress-top;
            uses qos-service-policy-egress-top;
        } // END of service-policy-container definition.
    } // END of qos-service-policy-top definition.

    grouping  interfaces-grouping {
    description
        "Configuration data for interface QoS";
    container interfaces {
        if-feature feature-list:HAVE_QOS;
        description
            "Configuration data for interface QoS";

        list interface {
        when " /ipi-qos:qos/ipi-qos:global/ipi-qos:config/ipi-qos:enable-qos = 'enable' ";
            key "name";
            description
                "Configuration data list for interface QoS";
            leaf name  {
                type  leafref {
                    path  "../config/name";
                }
                description "Interface name for which QoS is being configured";
            } // END of name definition.

            container config {
                description
                    "Configuration data for interface QoS";
                uses qos-interface-config;
            } // END of config-container definition.
            container state {
                config false;
                description
                    "Operational state data for interface QoS";
                uses qos-interface-config;
            } // END of state-container definition.
            uses qos-interface-remark-top;
            uses qos-traffic-shape-top;
            uses qos-map-profile-ref-top;
            uses qos-service-policy-top;
        } // End of interface-list
    } // END of interfaces-container definition.
    } // END of interfaces-grouping definition.

    augment /ipi-qos:qos {
        if-feature feature-list:HAVE_QOS;
        description
            "Configuration data for interface QoS";
        uses interfaces-grouping;
    }


    notification qos-subinterface-default-policy-add-notification {
        if-feature feature-list:HAVE_QOS;

        description "Add default policy on subif in DB.";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

    notification qos-subinterface-default-policy-delete-notification {
        if-feature feature-list:HAVE_QOS;

        description "Delete default policy on subif in DB.";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

    notification qos-subinterface-traffic-shape-add-notification {
        if-feature feature-list:HAVE_QOS;

        description "Add port shaper from subif in DB.";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

    notification qos-subinterface-traffic-shape-delete-notification {
        if-feature feature-list:HAVE_QOS;

        description "Delete port shaper from subif in DB.";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

}
