/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospf-redistribute.yang
*
*/

submodule ipi-ospf-redistribute {

    yang-version 1.1;

    belongs-to  ipi-ospf { prefix ipi-ospf; }

    import ipi-ospf-types {
        prefix ipi-ospf-types;
        revision-date 2024-09-05;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF redistribute";


    revision "2022-06-01" {
        description "Updated the yang file with feature";
        reference " 0.5.0.";
    }

    revision "2021-09-03" {
        description "Update descriptions of attribute";
        reference "Initial Version";
    }

    revision "2021-05-05" {
        description "Fix issue to configure redistribute for isis and ospf protocols";
        reference "Initial Version";
    }

    revision "2021-04-06" {
        description "Restructured module in accordance with OpenConfig style";
        reference "Initial Version";
    }

    grouping ospfv2-redistribute-common-config {
        description
            "Grouping for OSPF redistribute common configuration data";
        leaf metric  {
            type  uint32 {
                 range "0..16777214"  {
                    description "0..16777214: Supported range 0 - 16777214";
                 }
            }
            description "Use this attribute to set metric value.";
        } // END of metric definition.

        leaf metric-type  {
            type  ipi-ospf-types:ospf_metric_type_t;
            description "Use this attribute to set metric type.";
        } // END of metric-type definition.

        leaf route-map  {
            type  string {
                length "1..1965";
                pattern "[^?' =,>|]+";
            }
            description "Use this attribute to set route-map instance.";
        } // END of route-map definition.

        leaf tag  {
            type  uint32 {
                 range "0..4294967295"  {
                    description "0..4294967295: Supported range 0 - 4294967295";
                 }
            }
            description "Use this attribute to set the tag value to use as a match value for
                        controlling redistribution via route maps.";
        } // END of tag definition.

    } // END of ospfv2-redistribute-common-config definition.
    grouping ospfv2-redistribute-routing-protocol-config {
        description
            "Grouping for OSPF redistribute routing protocol configuration data";
        leaf protocol  {
            type  ipi-ospf-types:ospf_route_source_type_t;
            description "This attribute redistributes routes from a routing protocol, static
                        route, and kernel route into an OSPF routing table.";
        } // END of protocol definition.

    } // END of ospfv2-redistribute-routing-protocol-config definition.
    grouping ospfv2-redistribute-routing-protocol-top {
        description
            "Grouping for OSPF redistribute routing protocol";
        container routing-protocols {
            description
                "OSPF redistribute routing protocols";

            list routing-protocol {
                key "protocol";
                description
                    "List of OSPF redistribute routing protocols";
                leaf protocol  {
                    type  leafref {
                        path  "../config/protocol";
                    }
                    description "This attribute redistributes routes from a routing protocol, static
                                route, or kernel route into an OSPF routing table.";
                } // END of protocol definition.

                container config {
                    description
                        "Configuration data for OSPF redistribute routing protocol";
                    uses ospfv2-redistribute-routing-protocol-config;
                    uses ospfv2-redistribute-common-config;
                } // END of config-container definition.
                container state {
                    config false;
                    description
                        "Operational state data for OSPF redistribute routing protocol";
                    uses ospfv2-redistribute-routing-protocol-config;
                    uses ospfv2-redistribute-common-config;
                } // END of state-container definition.
            } // End of routing-protocol-list
        } // END of routing-protocols-container definition.
    } // END of ospfv2-redistribute-routing-protocol-top definition.
    grouping ospfv2-redistribute-isis-process-config {
        description
            "Grouping for OSPF redistribute IS-IS process configuration data";
        leaf isis-process-id  {
            type  string {
                length "1..1965";
                pattern "[^?' =,>|]+";
            }
            description "This attribute redistributes routes from an instance of IS-IS into an
                        OSPF routing table.";
        } // END of isis-process-id definition.

    } // END of ospfv2-redistribute-isis-process-config definition.
    grouping ospfv2-redistribute-isis-process-top {
        description
            "Grouping for OSPF redistribute IS-IS process";
        container isis-processes {
            description
                "OSPF redistribute IS-IS processes";

            list isis-process {
                key "isis-process-id";
                description
                    "List of OSPF redistribute IS-IS processes";
                leaf isis-process-id  {
                    type  leafref {
                        path  "../config/isis-process-id";
                    }
                    description "This attribute redistributes routes from an instance of IS-IS into an
                                OSPF routing table.";
                } // END of isis-process-id definition.

                container config {
                    description
                        "Configuration data for OSPF redistribute IS-IS process";
                    uses ospfv2-redistribute-isis-process-config;
                    uses ospfv2-redistribute-common-config;
                } // END of config-container definition.
                container state {
                    config false;
                    description
                        "Operational state data for OSPF redistribute IS-IS process";
                    uses ospfv2-redistribute-isis-process-config;
                    uses ospfv2-redistribute-common-config;
                } // END of state-container definition.
            } // End of isis-process-list
        } // END of isis-processes-container definition.
    } // END of ospfv2-redistribute-isis-process-top definition.
    grouping ospfv2-redistribute-ospf-process-config {
        description
            "Grouping for OSPF redistribute OSPF process configuration data";
        leaf ospf-process-id  {
            type  uint16 {
                 range "0..65535"  {
                    description "0..65535: Supported range 0 - 65535";
                 }
            }
            description "This attribute redistributes routes from an instance of OSPF into
                        another OSPF routing table.";
        } // END of ospf-process-id definition.

    } // END of ospfv2-redistribute-ospf-process-config definition.
    grouping ospfv2-redistribute-ospf-process-top {
        description
            "Grouping for OSPF redistribute OSPF process";
        container ospf-processes {
            description
                "OSPF redistribute OSPF processes";

            list ospf-process {
                key "ospf-process-id";
                description
                    "List of OSPF redistribute OSPF processes";
                leaf ospf-process-id  {
                    type  leafref {
                        path  "../config/ospf-process-id";
                    }
                    description "This attribute redistributes routes from an instance of OSPF into
                                another OSPF routing table.";
                } // END of ospf-process-id definition.

                container config {
                    description
                        "Configuration data for OSPF redistribute OSPF process";
                    uses ospfv2-redistribute-ospf-process-config;
                    uses ospfv2-redistribute-common-config;
                } // END of config-container definition.
                container state {
                    config false;
                    description
                        "Operational state data for OSPF redistribute OSPF process";
                    uses ospfv2-redistribute-ospf-process-config;
                    uses ospfv2-redistribute-common-config;
                } // END of state-container definition.
            } // End of ospf-process-list
        } // END of ospf-processes-container definition.
    } // END of ospfv2-redistribute-ospf-process-top definition.
    grouping ospfv2-redistribute-config {
        description
            "Grouping for OSPF redistribute configuration data";
        leaf default-metric  {
            type  uint32 {
                 range "1..16777214"  {
                    description "1..16777214: Supported range 1 - 16777214";
                 }
            }
            default "2";
            description "Use this attribute to set a default metric for OSPF. A default metric
                        facilitates redistributing routes with incompatible metrics. If the
                        metrics do not convert, the default metric provides an alternative.
                        Use this attribute to use the same metric value for all redistributed
                        routes. Use this attribute in conjunction with the redistribute
                        command.";
        } // END of default-metric definition.

    } // END of ospfv2-redistribute-config definition.
    grouping ospfv2-redistribute-top {
        description
            "Grouping for OSPF redistribute";
        container redistribute {
            description
                "OSPF redistribute";
            container config {
                description
                    "Configuration data for OSPF redistribute";
                uses ospfv2-redistribute-config;
            } // END of config-container definition.
            container state {
                config false;
                description
                    "Operational state data for OSPF redistribute";
                uses ospfv2-redistribute-config;
            } // END of state-container definition.
            uses ospfv2-redistribute-routing-protocol-top;
            uses ospfv2-redistribute-ospf-process-top;
            uses ospfv2-redistribute-isis-process-top;
        } // END of redistribute-container definition.
    } // END of ospfv2-redistribute-top definition.


}
