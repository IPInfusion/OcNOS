/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospf-global.yang
*
*/

submodule ipi-ospf-global {

    yang-version 1.1;

    belongs-to  ipi-ospf { prefix ipi-ospf; }

    import feature-list {
        prefix feature-list;
        revision-date 2026-09-15;
    }

    import ietf-inet-types {
        prefix inet;
        revision-date 2013-07-15;
    }

    import ipi-ospf-types {
        prefix ipi-ospf-types;
        revision-date 2024-09-05;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF global";


    revision "2022-06-01" {
        description "Updated the yang file with feature";
        reference " 0.4.0.";
    }

    revision "2021-09-03" {
        description "Update descriptions of attribute";
        reference "Initial Version";
    }

    revision "2021-08-05" {
        description "Graceful restart disable-all-neighbors triggers deletion of disable-all-neighbor when set";
        reference "Initial Version";
    }

    revision "2021-04-06" {
        description "Restructured module in accordance with OpenConfig style";
        reference "Initial Version";
    }

    grouping ospfv2-cspf-config {
        description
            "Grouping for OSPF Constrained Shortest Path First (CSPF) configuration
                        data";
        leaf tie-break-method  {
            type  ipi-ospf-types:ospf_cspf_tie_break_t;
            description "Use this attribute to set the CSPF (Constrained Shortest Path First)
                        tie-break method.";
        } // END of tie-break-method definition.

        leaf default-retry-interval  {
            type  uint16 {
                 range "1..3600"  {
                    description "1..3600: Supported range 1 - 3600";
                 }
            }
            units "seconds";
            description "Use this attribute to set the CSPF (Constrained Shortest Path First)
                        default computation retry-interval.";
        } // END of default-retry-interval definition.

        leaf enable-better-protection  {
            if-feature feature-list:HAVE_GMPLS;
            type  empty;
            description "Use this attribute to enable the CSPF (Constrained Shortest Path
                        First) protection type.";
        } // END of enable-better-protection definition.

        leaf enable-resource-constraint-crankback  {
            if-feature feature-list:HAVE_LSP_PROTECTION;
            type  empty;
            description "Use this attribute to enable the CSPF (Constrained Shortest Path
                        First) resource constraint for crankback.";
        } // END of enable-resource-constraint-crankback definition.

    } // END of ospfv2-cspf-config definition.
    grouping ospfv2-cspf-top {
        description
            "Grouping for OSPF Constrained Shortest Path First (CSPF)";
        container cspf {
            if-feature feature-list:HAVE_OSPF_CSPF;
            description
                "OSPF Constrained Shortest Path First (CSPF)";
            container config {
                description
                    "Configuration data for OSPF CSPF";
                uses ospfv2-cspf-config;
            } // END of config-container definition.
            container state {
                config false;
                description
                    "Operational state data for OSPF CSPF";
                uses ospfv2-cspf-config;
            } // END of state-container definition.
        } // END of cspf-container definition.
    } // END of ospfv2-cspf-top definition.
    grouping ospfv2-graceful-restart-helper-config {
        description
            "Grouping for OSPF global graceful restart helper configuration data";
        leaf max-grace-period  {
            // when " !ipi-ospf:ospfv2/global/graceful-restart/helper/config/disable-all-neighbors ";
            type  uint16 {
                 range "2..1800"  {
                    description "2..1800: Supported range 2 - 1800";
                 }
            }
            units "seconds";
            description "Use this attribute to set the maximum grace period. Act as helper only
                        if received grace-period is less than this value.";
        } // END of max-grace-period definition.

        leaf disable-all-neighbors  {
            // when " !ipi-ospf:ospfv2/global/graceful-restart/helper/config/max-grace-period ";
            type  empty;
            description "Use this attribute to prevent the router OSPF from acting as helper
                        for any neighbor.";
        } // END of disable-all-neighbors definition.

        leaf-list disable-neighbor  {
            // when " !ipi-ospf:ospfv2/global/graceful-restart/helper/config/disable-all-neighbors ";
            type  inet:ipv4-address;
            description "Use this attribute to set the neighbor router-id for which never act
                        as helper.";
        } // END of disable-neighbor definition.

    } // END of ospfv2-graceful-restart-helper-config definition.
    grouping ospfv2-graceful-restart-helper-top {
        description
            "Grouping for OSPF global graceful restart helper";
        container helper {
            description
                "OSPF global graceful restart helper";
            container config {
                description
                    "Configuration data for OSPF global graceful restart helper";
                uses ospfv2-graceful-restart-helper-config;
            } // END of config-container definition.
            container state {
                config false;
                description
                    "Operational state data for OSPF global graceful restart helper";
                uses ospfv2-graceful-restart-helper-config;
            } // END of state-container definition.
        } // END of helper-container definition.
    } // END of ospfv2-graceful-restart-helper-top definition.
    grouping ospfv2-graceful-restart-config {
        description
            "Grouping for OSPF global graceful restart configuration data";
        leaf grace-period  {
            type  uint16 {
                 range "2..1800"  {
                    description "2..1800: Supported range 2 - 1800";
                 }
            }
            units "seconds";
            description "Use this attribute to set the grace period for restarting the router
                        OSPF.";
        } // END of grace-period definition.

    } // END of ospfv2-graceful-restart-config definition.
    grouping ospfv2-graceful-restart-top {
        description
            "Grouping for OSPF global graceful restart";
        container graceful-restart {
            if-feature feature-list:HAVE_RESTART;
            description
                "OSPF global graceful restart";
            container config {
                description
                    "Configuration data for OSPF global graceful restart";
                uses ospfv2-graceful-restart-config;
            } // END of config-container definition.
            container state {
                config false;
                description
                    "Operational state data for OSPF global graceful restart";
                uses ospfv2-graceful-restart-config;
            } // END of state-container definition.
            uses ospfv2-graceful-restart-helper-top;
        } // END of graceful-restart-container definition.
    } // END of ospfv2-graceful-restart-top definition.
    grouping ospfv2-global-config {
        description
            "Grouping for OSPF global configuration data";
        leaf area-interface-config-mode  {
            type  empty;
            description "Use this attribute to set the OSPF area interface mode operation.
                        Enabling this makes OSPF compatible with OpenConfig datamodel.";
        } // END of area-interface-config-mode definition.

        leaf enable-multi-instance-capability  {
            if-feature feature-list:HAVE_OSPF_MULTI_INST;
            type  empty;
            description "Use this attribute to enable OSPF multiple instances capability.";
        } // END of enable-multi-instance-capability definition.

    } // END of ospfv2-global-config definition.
    grouping ospfv2-global-top {
        description
            "Grouping for OSPF global configuration";
        container global {
            description
                "OSPF global configuration";
            container config {
                description
                    "Configuration data for OSPF global";
                uses ospfv2-global-config;
            } // END of config-container definition.
            container state {
                config false;
                description
                    "Operational state data for OSPF global";
                uses ospfv2-global-config;
            } // END of state-container definition.
            uses ospfv2-graceful-restart-top;
            uses ospfv2-cspf-top;
        } // END of global-container definition.
    } // END of ospfv2-global-top definition.


}
