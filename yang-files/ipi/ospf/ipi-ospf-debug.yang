/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospf-debug.yang
*
*/

submodule ipi-ospf-debug {

    yang-version 1.1;

    belongs-to  ipi-ospf { prefix ipi-ospf; }

    import feature-list {
        prefix feature-list;
        revision-date 2026-09-15;
    }

    import ipi-ospf-types {
        prefix ipi-ospf-types;
        revision-date 2024-09-05;
    }

    import cml-data-types {
        prefix cml-data-types;
        revision-date 2026-05-15;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF debug";


    revision "2023-05-25" {
        description "Added new cli 'debug ip ospf all' and 'debug cspf all'";
        reference " 0.6.0.";
    }

    revision "2023-02-02" {
        description "Updated missing Description";
        reference " 0.5.0.";
    }

    revision "2022-09-20" {
        description "Changed the validate functions of no-debug-ospf-all from UPDATE to DELETE";
        reference " 0.4.2.";
    }

    revision "2022-09-09" {
        description "Fixed db-sync debug ospf all bug";
        reference " 0.4.1.";
    }

    revision "2022-08-10" {
        description "Debug hierarchy change";
        reference " 0.4.0.";
    }

    revision "2022-06-01" {
        description "Updated the yang file with feature";
        reference " 0.3.0.";
    }

    revision "2022-02-09" {
        description "Added When tag constraints for 'debug' container";
        reference " 0.5.1.";
    }

    revision "2021-10-25" {
        description "Added debug packet options type";
        reference " 0.2.2.";
    }

    revision "2021-09-10" {
        description "Added debug terminal state tree";
        reference " 0.2.1.";
    }

    revision "2021-09-03" {
        description "Update descriptions of attribute";
        reference " 0.2.0.";
    }

    revision "2021-04-30" {
        description "Renamed CLI command segment-routing to sr";
        reference " 0.1.1.";
    }

    revision "2021-04-06" {
        description "Restructured module in accordance with OpenConfig style";
        reference " 0.1.0.";
    }

    grouping ospfv2-debug-config {
        description
            "Grouping for OSPF debug configuration";
        leaf bfd  {
            if-feature feature-list:HAVE_BFD;
            type  empty;
            description "Use this attribute to enable Bidirectional Forwarding Detection (BFD)
                        debug.";
        } // END of bfd definition.

        leaf rate-limit  {
            type  empty;
            description "Use this attribute to enable OSPF Database Timers Rate Limiting Values
                        for LSA Throttling debug.";
        } // END of rate-limit definition.

        leaf segment-routing  {
            if-feature feature-list:HAVE_SR_MPLS;
            type  empty;
            description "Use this attribute to enable Segment Routing debug.";
        } // END of segment-routing definition.

        leaf route  {
            type  ipi-ospf-types:ospf_debug_route_t;
            description "Use this attribute to enable OSPF route information debug.";
        } // END of route definition.

        leaf rib  {
            if-feature feature-list:HAVE_RIBD;
            type  ipi-ospf-types:ospf_debug_rib_t;
            description "Use this attribute to enable OSPF RIB information debug.";
        } // END of rib definition.

        leaf nsm  {
            type  ipi-ospf-types:ospf_debug_nsm_t;
            description "Use this attribute to enable OSPF NSM information debug.";
        } // END of nsm definition.

        leaf nfsm  {
            type  ipi-ospf-types:ospf_debug_nfsm_t;
            description "Use this attribute to enable OSPF Neighbor State Machine debug.";
        } // END of nfsm definition.

        leaf lsa  {
            type  ipi-ospf-types:ospf_debug_lsa_t;
            description "Use this attribute to enable OSPF Link State Advertisement debug.";
        } // END of lsa definition.

        leaf ifsm  {
            type  ipi-ospf-types:ospf_debug_ifsm_t;
            description "Use this attribute to enable OSPF Interface State Machine debug.";
        } // END of ifsm definition.

        leaf events  {
            type  ipi-ospf-types:ospf_debug_event_t;
            description "Use this attribute to enable OSPF events information debug.";
        } // END of events definition.

        leaf cspf-events  {
            if-feature feature-list:HAVE_OSPF_CSPF;
            type  empty;
            description "Use this attribute to enable CSPF Information debug.";
        } // END of cspf-events definition.

        leaf cspf-hexdump  {
            if-feature feature-list:HAVE_OSPF_CSPF;
            type  empty;
            description "Use this attribute to enable CSPF message hexdump debug.";
        } // END of cspf-hexdump definition.

        leaf retransmission  {
            type  empty;
            description "Use this attribute to enable OSPF Debug retransmission information
                        debug.";
        } // END of retransmission definition.

        leaf distribute  {
            if-feature feature-list:HAVE_BGP_LS;
            type  empty;
            description "Use this attribute to enable OSPF distribute linkstate details debug.";
        } // END of distribute definition.

        leaf topology-independent-lfa  {
            if-feature feature-list:HAVE_OSPF_TI_LFA;
            type  empty;
            description "Use this attribute to enable Topology Independent LFA debug.";
        } // END of topology-independent-lfa definition.

        leaf lfa  {
            if-feature feature-list:HAVE_OSPF_LFA;
            type  empty;
            description "Use this attribute to enable OSPF LFA route install details debug.";
        } // END of lfa definition.

        leaf policy  {
            type  empty;
            description "Use this attribute to enable OSPF policy information debug.";
        } // END of policy definition.

        leaf redistribute  {
            type  ipi-ospf-types:ospf_debug_redist_t;
            description "Use this attribute to enable OSPF redistribute information debug.";
        } // END of redistribute definition.

        leaf graceful-restart  {
            type  ipi-ospf-types:ospf_debug_graceful_t;
            description "Use this attribute to enable OSPF graceful-restart debug.";
        } // END of graceful-restart definition.

        leaf packet-hello  {
            type  ipi-ospf-types:ospf_debug_packet_options_t;
            description "OSPF Hello";
        } // END of packet-hello definition.

        leaf packet-dd  {
            type  ipi-ospf-types:ospf_debug_packet_options_t;
            description "OSPF Database Description";
        } // END of packet-dd definition.

        leaf packet-ls-request  {
            type  ipi-ospf-types:ospf_debug_packet_options_t;
            description "OSPF Link State Request";
        } // END of packet-ls-request definition.

        leaf packet-ls-update  {
            type  ipi-ospf-types:ospf_debug_packet_options_t;
            description "OSPF Link State Update";
        } // END of packet-ls-update definition.

        leaf packet-ls-ack  {
            type  ipi-ospf-types:ospf_debug_packet_options_t;
            description "OSPF Link State Acknowledgment";
        } // END of packet-ls-ack definition.

    } // END of ospfv2-debug-config definition.
    grouping ospfv2-debug-terminal-state {
        description
            "Grouping for OSPFv2 debug state for exec mode";
        container terminal-debug-status {
            config false;
            description
                "Runtime attributes for terminal debug";
            leaf bfd  {
                if-feature feature-list:HAVE_BFD;
                type  cml-data-types:cml_on_off_t;
                description "Use this attribute to enable Bidirectional Forwarding Detection (BFD)
                            debug.";
            } // END of bfd definition.

            leaf rate-limit  {
                type  cml-data-types:cml_on_off_t;
                description "Use this attribute to enable OSPF Database Timers Rate Limiting Values
                            for LSA Throttling debug.";
            } // END of rate-limit definition.

            leaf segment-routing  {
                if-feature feature-list:HAVE_SR_MPLS;
                type  cml-data-types:cml_on_off_t;
                description "Use this attribute to enable Segment Routing debug.";
            } // END of segment-routing definition.

            leaf route  {
                type  ipi-ospf-types:ospf_debug_route_t;
                description "Use this attribute to enable OSPF route information debug.";
            } // END of route definition.

            leaf rib  {
                if-feature feature-list:HAVE_RIBD;
                type  ipi-ospf-types:ospf_debug_rib_t;
                description "Use this attribute to enable OSPF RIB information debug.";
            } // END of rib definition.

            leaf nsm  {
                type  ipi-ospf-types:ospf_debug_nsm_t;
                description "Use this attribute to enable OSPF NSM information debug.";
            } // END of nsm definition.

            leaf nfsm  {
                type  ipi-ospf-types:ospf_debug_nfsm_t;
                description "Use this attribute to enable OSPF Neighbor State Machine debug.";
            } // END of nfsm definition.

            leaf lsa  {
                type  ipi-ospf-types:ospf_debug_lsa_t;
                description "Use this attribute to enable OSPF Link State Advertisement debug.";
            } // END of lsa definition.

            leaf ifsm  {
                type  ipi-ospf-types:ospf_debug_ifsm_t;
                description "Use this attribute to enable OSPF Interface State Machine debug.";
            } // END of ifsm definition.

            leaf events  {
                type  ipi-ospf-types:ospf_debug_event_t;
                description "Use this attribute to enable OSPF events information debug.";
            } // END of events definition.

            leaf cspf-events  {
                if-feature feature-list:HAVE_OSPF_CSPF;
                type  cml-data-types:cml_on_off_t;
                description "Use this attribute to enable CSPF Information debug.";
            } // END of cspf-events definition.

            leaf cspf-hexdump  {
                if-feature feature-list:HAVE_OSPF_CSPF;
                type  cml-data-types:cml_on_off_t;
                description "Use this attribute to enable CSPF message hexdump debug.";
            } // END of cspf-hexdump definition.

            leaf retransmission  {
                type  cml-data-types:cml_on_off_t;
                description "Use this attribute to enable OSPF Debug retransmission information
                            debug.";
            } // END of retransmission definition.

            leaf distribute  {
                if-feature feature-list:HAVE_BGP_LS;
                type  cml-data-types:cml_on_off_t;
                description "Use this attribute to enable OSPF distribute linkstate details debug.";
            } // END of distribute definition.

            leaf topology-independent-lfa  {
                if-feature feature-list:HAVE_OSPF_TI_LFA;
                type  cml-data-types:cml_on_off_t;
                description "Use this attribute to enable Topology Independent LFA debug.";
            } // END of topology-independent-lfa definition.

            leaf lfa  {
                if-feature feature-list:HAVE_OSPF_LFA;
                type  cml-data-types:cml_on_off_t;
                description "Use this attribute to enable OSPF LFA route install details debug.";
            } // END of lfa definition.

            leaf policy  {
                type  cml-data-types:cml_on_off_t;
                description "Use this attribute to enable OSPF policy information debug.";
            } // END of policy definition.

            leaf redistribute  {
                type  ipi-ospf-types:ospf_debug_redist_t;
                description "Use this attribute to enable OSPF redistribute information debug.";
            } // END of redistribute definition.

            leaf graceful-restart  {
                type  ipi-ospf-types:ospf_debug_graceful_t;
                description "Use this attribute to enable OSPF graceful-restart debug.";
            } // END of graceful-restart definition.

            leaf packet-hello  {
                type  ipi-ospf-types:ospf_debug_packet_options_t;
                description "OSPF Hello";
            } // END of packet-hello definition.

            leaf packet-dd  {
                type  ipi-ospf-types:ospf_debug_packet_options_t;
                description "OSPF Database Description";
            } // END of packet-dd definition.

            leaf packet-ls-request  {
                type  ipi-ospf-types:ospf_debug_packet_options_t;
                description "OSPF Link State Request";
            } // END of packet-ls-request definition.

            leaf packet-ls-update  {
                type  ipi-ospf-types:ospf_debug_packet_options_t;
                description "OSPF Link State Update";
            } // END of packet-ls-update definition.

            leaf packet-ls-ack  {
                type  ipi-ospf-types:ospf_debug_packet_options_t;
                description "OSPF Link State Acknowledgment";
            } // END of packet-ls-ack definition.

        } // END of terminal-debug-status-container definition.
    } // END of ospfv2-debug-terminal-state definition.
    grouping ospfv2-debug-top {
        description
            "Grouping for OSPF debug";
        container debug {
            description
                "OSPF debug";
            container config {
                description
                    "Configuration data for OSPF debug";
                uses ospfv2-debug-config;
            } // END of config-container definition.
            container state {
                config false;
                description
                    "Operational state data for OSPF debug";
                uses ospfv2-debug-config;
                uses ospfv2-debug-terminal-state;
            } // END of state-container definition.
        } // END of debug-container definition.
    } // END of ospfv2-debug-top definition.


}
