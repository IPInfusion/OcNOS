/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospf-interface-common.yang
*
*/

submodule ipi-ospf-interface-common {

    yang-version 1.1;

    belongs-to  ipi-ospf { prefix ipi-ospf; }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF interface common configurations";


    revision "2023-01-11" {
        description "Customizing interface settings for OpenConfig";
        reference " 0.1.0.";
    }

    grouping ospfv2-interface-common-mpls-ldp-sync-config {
        description
            "Grouping for OSPF-LDP interface mpls ldp sync configuration data";
        leaf ldp-igp-sync-enable  {
            if-feature feature-list:HAVE_LDPD;
            type  empty;
            description "Use this attribute to enable the MPLS LDP IGP SYNC on OSPF.";
        } // END of ldp-igp-sync-enable definition.

    } // END of ospfv2-interface-common-mpls-ldp-sync-config definition.
    grouping ospfv2-interface-common-timers-config {
        description
            "Grouping for OSPF interface common timers configuration data";
        leaf dead-interval  {
            type  uint16 {
                 range "1..65535"  {
                    description "1..65535: Supported range 1 - 65535";
                 }
            }
            units "seconds";
            description "Use this attribute to set the interval during which the router waits
                        to receive an OSPF hello packet from the neighbor before declaring the
                        neighbor down.";
        } // END of dead-interval definition.

        leaf hello-interval  {
            type  uint16 {
                 range "1..65535"  {
                    description "1..65535: Supported range 1 - 65535";
                 }
            }
            units "seconds";
            default "10";
            description "Use this attribute to specify the interval between hello packets.";
        } // END of hello-interval definition.

        leaf retransmission-interval  {
            type  uint16 {
                 range "1..3600"  {
                    description "1..3600: Supported range 1 - 3600";
                 }
            }
            units "seconds";
            default "5";
            description "Use this attribute to specify the time between link-state
                        advertisement (LSA) retransmissions for adjacencies belonging to the
                        interface.";
        } // END of retransmission-interval definition.

    } // END of ospfv2-interface-common-timers-config definition.
    grouping ospfv2-interface-common-database-filter-config {
        description
            "Grouping for OSPF interface database filter configuration data";
        leaf filter-out  {
            type  empty;
            description "Use this attribute to turn on the LSA database-filter for a particular
                        interface.
                        OSPF floods new LSAs over all interfaces in an area, except the
                        interface on which the LSA arrives. This redundancy ensures robust
                        flooding. However, too much redundancy can waste bandwidth and might
                        lead to excessive link and CPU usage in certain topologies, resulting
                        in destabilizing the network. To avoid this, use this attribute to
                        block flooding of LSAs over specified interfaces.";
        } // END of filter-out definition.

    } // END of ospfv2-interface-common-database-filter-config definition.


}
