/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospf.yang
*
*/

module ipi-ospf {

    yang-version 1.1;

    namespace   "http://www.ipinfusion.com/yang/ocnos/ipi-ospf";

    prefix "ipi-ospf";

    import cml-data-types {
        prefix cml-data-types;
        revision-date 2026-05-15;
    }

    import ietf-inet-types {
        prefix inet;
        revision-date 2013-07-15;
    }

    import ietf-yang-types {
        prefix yang;
        revision-date 2013-07-15;
    }

    import ipi-interface {
        prefix ipi-interface;
        revision-date 2026-03-10;
    }

    import ipi-network-instance {
        prefix ipi-network-instance;
        revision-date 2026-08-12;
    }

    import ipi-ospf-types {
        prefix ipi-ospf-types;
        revision-date 2024-09-05;
    }

    import ipi-vrf {
        prefix ipi-vrf;
        revision-date 2026-08-12;
    }

    import feature-list {
        prefix feature-list;
        revision-date 2026-09-15;
    }

    include ipi-ospf-area { revision-date 2026-05-20;}
    include ipi-ospf-debug { revision-date 2023-05-25;}
    include ipi-ospf-distribute-lists { revision-date 2025-03-17;}
    include ipi-ospf-global { revision-date 2022-06-01;}
    include ipi-ospf-multi-area-interface { revision-date 2025-09-04;}
    include ipi-ospf-processes-state { revision-date 2024-09-18;}
    include ipi-ospf-redistribute { revision-date 2022-06-01;}
    include ipi-ospf-te-link { revision-date 2022-06-01;}
    include ipi-ospf-timers { revision-date 2025-01-26;}
    include ipi-ospf-interface { revision-date 2025-09-04;}
    include ipi-ospf-authentication { revision-date 2022-06-01;}
    include ipi-ospf-interface-common { revision-date 2023-01-11;}
    organization
        "IP Infusion Inc.";

    contact
        "Address: 3965 Freedom Circle, Suite 200, Santa Clara, CA 95054
         Phone: +1 408-400-1900
         E-mail: support@ipinfusion.com
         Web: http://www.ipinfusion.com/";

    description
        "Layer-3 Open Shortest Path First (OSPF)";


    revision "2026-05-20" {
        description "Added a when tag for channel-group at ospfv2-area-interface";
        reference " 0.13.0.";
    }

    revision "2026-01-20" {
        description "Updated datatype for nbt-state as CML_LINE_T";
        reference " 0.12.1.";
    }

    revision "2025-12-22" {
        description "Added implicit_delete tag for bfd config container";
        reference " 0.11.3.";
    }

    revision "2025-09-04" {
        description "Removed EVPN_IRB_IF_MODE while configuring IRB interface";
        reference " 0.11.2.";
    }

    revision "2025-08-07" {
        description "Updated the helpstring for Holddown timer for the OSPF ldp-Sync";
        reference " 0.11.1.";
    }

    revision "2025-06-18" {
        description "Fixed autoPopulate tags for ospf capabilities to avoid DB-sync in create and replace cases";
        reference " 0.11.0.";
    }

    revision "2025-05-20" {
        description "Fixed autoPopulate tags for ospf capabilities to avoid DB-syn in replace cases";
        reference " 0.9.7.";
    }

    revision "2025-03-17" {
        description "Updated input help string to the WORD for the attribute access-control-list";
        reference " 0.9.6.";
    }

    revision "2025-02-27" {
        description "Added when tag for disable-traffic-engineering and disable-cspf";
        reference " 0.10.0.";
    }

    revision "2025-01-26" {
        description "Added implicit_delete tag for timers container";
        reference " 0.9.5.";
    }

    revision "2025-01-16" {
        description "Added enclosing container for discovered neighbor object list";
        reference " 0.9.4.";
    }

    revision "2025-01-08" {
        description "Added OSPF neighbor table support to retrieve state attributes";
        reference " 0.9.3.";
    }

    revision "2024-11-05" {
        description "Added vrf-name when tag to multi-area-interface name attribute";
        reference " 0.9.2.";
    }

    revision "2024-10-15" {
        description "Updated the default cost value for the ospfv2 interface";
        reference " 0.9.1.";
    }

    revision "2024-09-18" {
        description "ECMP change for tilfa-repair-path, tilfa-backup-path output";
        reference " 0.9.0.";
    }

    revision "2024-09-05" {
        description "Updated if-feature for datatype OSPF_ROUTE_SOURCE_TYPE_T";
        reference " 0.8.6.";
    }

    revision "2024-08-07" {
        description "Added when tag at ospfv2-area-interface";
        reference " 0.8.5.";
    }

    revision "2024-06-27" {
        description "Added implicit_delete osfp-area config container";
        reference " 0.8.4.";
    }

    revision "2024-05-24" {
        description "Added dependentObjects for multi-area neighbors ";
        reference " 0.8.3.";
    }

    revision "2024-04-25" {
        description "Update Segment Routing entropy CLI, Removing SR dependency for entropy";
        reference " 0.9.6.";
    }

    revision "2024-04-19" {
        description "Added implicit_delete config to ospf config container";
        reference " 0.8.2.";
    }

    revision "2024-03-25" {
        description "Added implicit_delete area to sham-links container";
        reference " 0.8.1.";
    }

    revision "2024-02-15" {
        description "Added implicit delete tag for config of distribute-bgp-ls cli";
        reference " 0.8.0.";
    }

    revision "2023-10-09" {
        description "CLI command updated for unconfiguration message-digest-key";
        reference " 0.7.1.";
    }

    revision "2023-10-07" {
        description "Linking Segment Routing and entropy capabilty";
        reference " 0.9.5.";
    }

    revision "2023-08-09" {
        description "Added Segment Routing capability entropy";
        reference " 0.9.4.";
    }

    revision "2023-08-03" {
        description "OSPF CLI Commands for EVPN IRB Interface";
        reference " 0.9.3.";
    }

    revision "2023-07-25" {
        description "Updated confirmation string for ospfv2-restart-graceful";
        reference " 0.9.2.";
    }

    revision "2023-06-13" {
        description "Added to delete area configs on removing non default vrf from interface";
        reference " 0.9.1.";
    }

    revision "2023-05-25" {
        description "Added new cli 'debug ip ospf all' and 'debug cspf all'";
        reference " 0.9.0.";
    }

    revision "2023-05-19" {
        description "Adding constraint to remove areas/area/interfaces/interface/mpls/igp-ldp-sync when holddown-timer is deleted";
        reference " 0.7.0.";
    }

    revision "2023-05-12" {
        description "container to presence container changes for adjacency";
        reference " 0.6.9.";
    }

    revision "2023-05-11" {
        description "Added OSPF_PASSIVE_MODE_T datatype";
        reference " 0.8.6.";
    }

    revision "2023-03-21" {
        description "Added dependentObjects for multi-area in process/config, and ospf-interface in multi-area-interface/ospfv2-processes/ospfv2-process/multi-areas/multi-area/config";
        reference " 0.6.8.";
    }

    revision "2023-03-09" {
        description "ip ospf need cli-command with suppress-flag for cli error feature";
        reference " 0.6.7.";
    }

    revision "2023-03-08" {
        description "cli Error improvement feature changes";
        reference " 0.6.6.";
    }

    revision "2023-02-27" {
        description "Added tag autoPopulated for interface/area objectlist";
        reference " 0.6.5.";
    }

    revision "2023-02-08" {
        description "Removing OSPF_PASSIVE_MODE_T datatype";
        reference " 0.8.4.";
    }

    revision "2023-02-02" {
        description "Updated missing Description";
        reference " 0.8.3.";
    }

    revision "2023-01-31" {
        description "Added a dependent object delete for prefix-sid-map";
        reference " 0.8.2.";
    }

    revision "2023-01-27" {
        description "Updated implicit_delete tag for ospf-interface/addresses/address container, adding CML_NO_DELETE_API flag to multi-area-interface RDN, and updated its config container with autoPopulate flag";
        reference " 0.8.1.";
    }

    revision "2023-01-11" {
        description "Customizing interface settings for OpenConfig";
        reference " 0.8.0.";
    }

    revision "2023-01-10" {
        description "Leafref correction for config container";
        reference " 0.7.5.";
    }

    revision "2023-01-09" {
        description "Adding implicit_delete tags to administrative-distance config container";
        reference " 0.7.4.";
    }

    revision "2023-01-02" {
        description "Adding constraint to remove interface/timers when holddown-timer is deleted";
        reference " 0.7.3.";
    }

    revision "2022-12-15" {
        description "Updated CLI generation";
        reference " 0.7.2.";
    }

    revision "2022-12-01" {
        description "Updated when expressions";
        reference " 0.7.1.";
    }

    revision "2022-11-21" {
        description "Updated domain-id container with implicit delete tag";
        reference " 0.7.0.";
    }

    revision "2022-09-23" {
        description "Modified the cli structure for fast-reroute perfix tilfa";
        reference " 0.6.8.";
    }

    revision "2022-09-20" {
        description "Changed the validate functions of no-debug-ospf-all from UPDATE to DELETE";
        reference " 0.6.7.";
    }

    revision "2022-09-09" {
        description "Fixed db-sync debug ospf all bug";
        reference " 0.6.6.";
    }

    revision "2022-09-07" {
        description "Added suppress cli for fast-reroute prefix tilfa cli";
        reference " 0.6.5.";
    }

    revision "2022-08-29" {
        description "Updated the when expression with feature";
        reference " 0.6.4.";
    }

    revision "2022-08-24" {
        description "Updated implicit delete in authentication container";
        reference " 0.6.3.";
    }

    revision "2022-08-10" {
        description "Debug hierarchy change";
        reference " 0.6.2.";
    }

    revision "2022-08-02" {
        description "Updation of SRGB starting range value";
        reference " 0.6.1.";
    }

    revision "2022-07-31" {
        description "Stop using inet:ipv4-prefix and inet:ipv6-prefix due to Cisco NSO iterop";
        reference " 0.6.4.";
    }

    revision "2022-07-30" {
        description "Updated when expressions in yang";
        reference " 0.6.0.";
    }

    revision "2022-06-01" {
        description "Updated the yang file with feature";
        reference " 0.5.0.";
    }

    revision "2022-05-13" {
        description "Added state container for max-metric";
        reference " 0.4.4.";
    }

    revision "2022-04-28" {
        description "Created new attributes for remote-lfa and route-map for fast re-route";
        reference " 0.4.3.";
    }

    revision "2022-04-08" {
        description "Added config for max-metric";
        reference " 0.4.2.";
    }

    revision "2022-04-05" {
        description "Removed distance of network adm distance as mandatory and enforce configuration via when";
        reference " 0.4.1.";
    }

    revision "2022-02-09" {
        description "Added When tag constraints for 'debug' container";
        reference " 0.8.5.";
    }

    revision "2022-01-07" {
        description "Modified Submodules";
        reference " 0.4.0.";
    }

    revision "2021-10-25" {
        description "Added debug packet options type";
        reference " 0.3.7.";
    }

    revision "2021-09-10" {
        description "Added debug terminal state tree";
        reference " 0.3.6.";
    }

    revision "2021-09-03" {
        description "Update descriptions of attribute";
        reference " 0.3.5.";
    }

    revision "2021-08-20" {
        description "Add config false for the TE link-delay state container";
        reference " 0.3.4.";
    }

    revision "2021-08-18" {
        description "State attributes for Segment Routing, TI LFA and TE";
        reference " 0.3.3.";
    }

    revision "2021-08-05" {
        description "Graceful restart disable-all-neighbors triggers deletion of disable-all-neighbor when set";
        reference " 0.3.2.";
    }

    revision "2021-07-30" {
        description "Added support for sham-links";
        reference " 0.3.1.";
    }

    revision "2021-07-27" {
        description "Created new datatype OSPF_PASSIVE_ADDR_MODE_T that contains only the option enable to be used in passive-interface IFNAME A.B.C.D";
        reference " 0.3.0.";
    }

    revision "2021-06-11" {
        description "Added the new attribute ldp-igp-sync-enable for the mpls ldp-igp sync ospf";
        reference " 0.2.8.";
    }

    revision "2021-06-02" {
        description "Removed if-feature from leaves that are referenced by leaves that are list keys";
        reference " 0.2.7.";
    }

    revision "2021-05-22" {
        description "Fix passive-interface to allow enable/disable mode";
        reference " 0.2.6.";
    }

    revision "2021-05-07" {
        description "Fix NSSA CLI command to avoid show duplicate nssa input";
        reference " 0.2.5.";
    }

    revision "2021-05-05" {
        description "Update redistribute OSPF data-model";
        reference " 0.2.4.";
    }

    revision "2021-05-01" {
        description "Added attribute passive-interface-all and removed space in cisco helpstring of type OSPF_ABR_TYPE_T";
        reference " 0.2.3.";
    }

    revision "2021-04-30" {
        description "Restructured filter-list prefix-list and acl-list from lists to containers, and value range for ospfv2-processes list";
        reference " 0.2.2.";
    }

    revision "2021-04-29" {
        description "timers lsa min-delay and max-delay range updated to 1-600000";
        reference " 0.2.2.";
    }

    revision "2021-04-28" {
        description "Add on command overflow external LSA a verification to check if is all attributes are filled before accept the configuration";
        reference " 0.2.1.";
    }

    revision "2021-04-06" {
        description "Restructured module in accordance with OpenConfig style";
        reference " 0.2.0.";
    }

    revision "2018-06-21" {
        description "Initial Version";
        reference " 0.1.0.";
    }

    grouping ospfv2-administrative-distance-network-config {
        description
            "Grouping for OSPF network administrative distance configuration data";
        leaf prefix  {
            type  cml-data-types:cml_ipv4_addr_prefix_t;
            description "Use this attribute to specifies the network prefix for administrative
                        distance.";
        } // END of prefix definition.

        leaf distance  {
            type  uint8 {
                 range "1..255"  {
                    description "1..255: Supported range 1 - 255";
                 }
            }
            description "Use this attribute to specifies administrative distance.";
        } // END of distance definition.

        leaf access-control-list  {
            type  string {
                length "1..1965";
                pattern "[^?' =,>|]+";
            }
            description "Use this attribute to specifies administrative distance network ACL.";
        } // END of access-control-list definition.

    } // END of ospfv2-administrative-distance-network-config definition.
    grouping ospfv2-administrative-distance-network-top {
        description
            "Grouping for OSPF network administrative distance";
        container networks {
            description
                "OSPF networks administrative distance";

            list network {
            // when " ipi-ospf:ospfv2/processes/process/administrative-distance/networks/network/config/distance ";
                key "prefix";
                description
                    "List of OSPF networks administrative distance";
                leaf prefix  {
                    type  leafref {
                        path  "../config/prefix";
                    }
                    description "Use this attribute to network for administrative distance.";
                } // END of prefix definition.

                container config {
                    description
                        "Configuration data for OSPF network administrative distance";
                    uses ospfv2-administrative-distance-network-config;
                } // END of config-container definition.
                container state {
                    config false;
                    description
                        "Operational state data for OSPF network administrative distance";
                    uses ospfv2-administrative-distance-network-config;
                } // END of state-container definition.
            } // End of network-list
        } // END of networks-container definition.
    } // END of ospfv2-administrative-distance-network-top definition.
    grouping ospfv2-administrative-distance-ospf-config {
        description
            "Grouping for OSPF administrative distance configuration data";
        leaf intra-area-distance  {
            type  uint8 {
                 range "1..255"  {
                    description "1..255: Supported range 1 - 255";
                 }
            }
            description "Use this attribute to set the distance for all routes within an area.";
        } // END of intra-area-distance definition.

        leaf inter-area-distance  {
            type  uint8 {
                 range "1..255"  {
                    description "1..255: Supported range 1 - 255";
                 }
            }
            description "Use this attribute to set the distance for all routes from one area to
                        another area.";
        } // END of inter-area-distance definition.

        leaf external-routes-distance  {
            type  uint8 {
                 range "1..255"  {
                    description "1..255: Supported range 1 - 255";
                 }
            }
            description "Use this attribute to set distance for routes from other routing
                        domains learned by redistribution.";
        } // END of external-routes-distance definition.

    } // END of ospfv2-administrative-distance-ospf-config definition.
    grouping ospfv2-administrative-distance-ospf-top {
        description
            "Grouping for OSPF administrative distance";
        container ospf {
            description
                "Grouping for OSPF administrative distance";
            container config {
                description
                    "Configuration data for OSPF administrative distance";
                uses ospfv2-administrative-distance-ospf-config;
            } // END of config-container definition.
            container state {
                config false;
                description
                    "Operational state data for OSPF administrative distance";
                uses ospfv2-administrative-distance-ospf-config;
            } // END of state-container definition.
        } // END of ospf-container definition.
    } // END of ospfv2-administrative-distance-ospf-top definition.
    grouping ospfv2-administrative-distance-config {
        description
            "Grouping for OSPF administrative distance configuration data";
        leaf default-distance  {
            type  uint8 {
                 range "1..255"  {
                    description "1..255: Supported range 1 - 255";
                 }
            }
            description "Use this attribute to specifies a default administrative distance used
                        when no other specification exists for a routing information source.";
        } // END of default-distance definition.

    } // END of ospfv2-administrative-distance-config definition.
    grouping ospfv2-administrative-distance-top {
        description
            "Grouping for OSPF administrative distance";
        container administrative-distance {
            description
                "OSPF administrative distance";
            container config {
                description
                    "Configuration data for OSPF administrative distance";
                uses ospfv2-administrative-distance-config;
            } // END of config-container definition.
            container state {
                config false;
                description
                    "Operational state data for OSPF administrative distance";
                uses ospfv2-administrative-distance-config;
            } // END of state-container definition.
            uses ospfv2-administrative-distance-ospf-top;
            uses ospfv2-administrative-distance-network-top;
        } // END of administrative-distance-container definition.
    } // END of ospfv2-administrative-distance-top definition.
    grouping ospfv2-segment-routing-prefix-sid-map-config {
        description
            "Grouping for OSPF segment routing prefix to SID mapping policy
                        configuration data";
        leaf advertise-local  {
            type  empty;
            description "Use this attribute to advertise local mapping server entries to other
                        routers in the segment routing domain.";
        } // END of advertise-local definition.

        leaf disable-receive  {
            type  empty;
            description "Use this attribute to enable or disable receiving prefix SID mappings
                        from a mapping server.";
        } // END of disable-receive definition.

    } // END of ospfv2-segment-routing-prefix-sid-map-config definition.
    grouping ospfv2-segment-routing-prefix-sid-map-top {
        description
            "Grouping for OSPF segment routing prefix to SID mapping policy";
        container prefix-sid-map {
            if-feature feature-list:HAVE_SR_MPLS;
            description
                "OSPF segment routing prefix to SID mapping policy";
            container config {
                description
                    "Configuration data for OSPF segment routing prefix to SID mapping
                            policy";
                uses ospfv2-segment-routing-prefix-sid-map-config;
            } // END of config-container definition.
            container state {
                config false;
                description
                    "Operational state data for OSPF segment routing prefix to SID mapping
                            policy";
                uses ospfv2-segment-routing-prefix-sid-map-config;
            } // END of state-container definition.
        } // END of prefix-sid-map-container definition.
    } // END of ospfv2-segment-routing-prefix-sid-map-top definition.
    grouping ospfv2-segment-routing-global-block-config {
        description
            "Grouping for OSPF segment routing global block configuration data";
        leaf block-base-value  {
            type  uint32 {
                 range "16..1048575"  {
                    description "16..1048575: Supported range 16 - 1048575";
                 }
            }
            description "Use this attribute to set the segment routing block starting range
                        value.";
        } // END of block-base-value definition.

        leaf block-range-size  {
            type  uint32 {
                 range "16..1048575"  {
                    description "16..1048575: Supported range 16 - 1048575";
                 }
            }
            description "Use this attribute to set the segment routing block ending range
                        value.";
        } // END of block-range-size definition.

    } // END of ospfv2-segment-routing-global-block-config definition.
    grouping ospfv2-segment-routing-global-block-top {
        description
            "Grouping for OSPF segment routing global block";
        container global-blocks {
            if-feature feature-list:HAVE_SR_MPLS;
            description
                "OSPF segment routing global blocks";

            list global-block {
                key "block-base-value block-range-size";
                max-elements 1;
                description
                    "List of OSPF segment routing global blocks";
                leaf block-base-value  {
                    type  leafref {
                        path  "../config/block-base-value";
                    }
                    description "Use this attribute to set the segment routing block starting range
                                value.";
                } // END of block-base-value definition.

                leaf block-range-size  {
                    type  leafref {
                        path  "../config/block-range-size";
                    }
                    description "Use this attribute to set the segment routing block ending range
                                value.";
                } // END of block-range-size definition.

                container config {
                    description
                        "Configuration data for OSPF segment routing global block";
                    uses ospfv2-segment-routing-global-block-config;
                } // END of config-container definition.
                container state {
                    config false;
                    description
                        "Operational state data for OSPF segment routing global block";
                    uses ospfv2-segment-routing-global-block-config;
                } // END of state-container definition.
            } // End of global-block-list
        } // END of global-blocks-container definition.
    } // END of ospfv2-segment-routing-global-block-top definition.
    grouping ospfv2-mpls-entropy-config {
        description
            "Grouping for OSPF entropy capability configuration data";
        leaf entropy-capability  {
            type  empty;
            description "Use this attribute to enable segment routing entropy label.";
        } // END of entropy-capability definition.

    } // END of ospfv2-mpls-entropy-config definition.
    grouping ospfv2-mpls-entropy-top {
        description
            "Grouping for OSPF segment routing entropy capability";
        container capability-entropy {
            if-feature feature-list:HAVE_SR_MPLS;
            description
                "OSPF MPLS entropy capability";
            container config {
                description
                    "Configuration data for OSPF MPLS entropy capability";
                uses ospfv2-mpls-entropy-config;
            } // END of config-container definition.
            container state {
                config false;
                description
                    "Operational state data for OSPF segment routing entropy capability";
                uses ospfv2-mpls-entropy-config;
            } // END of state-container definition.
        } // END of capability-entropy-container definition.
    } // END of ospfv2-mpls-entropy-top definition.
    grouping ospfv2-segment-routing-config {
        description
            "Grouping for OSPF segment routing configuration data";
        leaf mpls  {
            type  empty;
            description "Use this attribute to enable MPLS-based segment routing for OSPF.";
        } // END of mpls definition.

    } // END of ospfv2-segment-routing-config definition.
    grouping ospfv2-segment-routing-external-prefix-range-state {
        description
            "Grouping for OSPF segment routing external prefix range state";
        leaf ls-id  {
            type  inet:ipv4-address;
            description "External prefix range LS-ID.";
        } // END of ls-id definition.

        leaf prefix  {
            type  cml-data-types:cml_ipv4_addr_prefix_t;
            description "External prefix range prefix.";
        } // END of prefix definition.

        leaf advertising-router  {
            type  inet:ipv4-address;
            description "External prefix range advertising router.";
        } // END of advertising-router definition.

        leaf range-size  {
            type  uint16;
            description "External prefix range size.";
        } // END of range-size definition.

    } // END of ospfv2-segment-routing-external-prefix-range-state definition.
    grouping ospfv2-segment-routing-external-prefix-range {
        description
            "Grouping for OSPF segment routinng external prefix range";
        container external-prefixes-range {
            config false;
            description
                "OSPF segment routing external prefix range";

            list external-prefix-range {
                key "ls-id";
                config false;
                description
                    "List of OSPF segment routing external prefix range";
                leaf ls-id  {
                    type  leafref {
                        path  "../state/ls-id";
                    }
                    description "Use this attribute to set the segment routing external prefix lsa
                                value.";
                } // END of ls-id definition.

                container state {
                    config false;
                    description
                        "Operational state data for OSPF segment routing global block";
                    uses ospfv2-segment-routing-external-prefix-range-state;
                } // END of state-container definition.
            } // End of external-prefix-range-list
        } // END of external-prefixes-range-container definition.
    } // END of ospfv2-segment-routing-external-prefix-range definition.
    grouping ospfv2-segment-routing-external-prefix-lsa-state {
        description
            "Grouping for OSPF segment routing external prefix lsa state";
        leaf prefix  {
            type  cml-data-types:cml_ipv4_addr_prefix_t;
            description "External prefix LSA prefix.";
        } // END of prefix definition.

        leaf advertising-router  {
            type  inet:ipv4-address;
            description "External prefix LSA advertising router.";
        } // END of advertising-router definition.

        leaf route-type  {
            type  ipi-ospf-types:ospf_prefix_route_type_t;
            description "External prefix LSA route type.";
        } // END of route-type definition.

    } // END of ospfv2-segment-routing-external-prefix-lsa-state definition.
    grouping ospfv2-segment-routing-external-prefix-lsa {
        description
            "Grouping for OSPF segment routinng external prefix lsa";
        container external-prefixes-lsa {
            config false;
            description
                "OSPF segment routing external prefix lsa";

            list external-prefix-lsa {
                key "prefix";
                config false;
                description
                    "List of OSPF segment routing external prefix lsa";
                leaf prefix  {
                    type  leafref {
                        path  "../state/prefix";
                    }
                    description "Use this attribute to set the segment routing external prefix lsa
                                value.";
                } // END of prefix definition.

                container state {
                    config false;
                    description
                        "Operational state data for OSPF segment routing global block";
                    uses ospfv2-segment-routing-external-prefix-lsa-state;
                } // END of state-container definition.
            } // End of external-prefix-lsa-list
        } // END of external-prefixes-lsa-container definition.
    } // END of ospfv2-segment-routing-external-prefix-lsa definition.
    grouping ospfv2-segment-routing-announce-list-state {
        description
            "Grouping for OSPF segment routing announce lists state";
        leaf area-id  {
            type  inet:ipv4-address;
            description "This attribute returns the area-id value.";
        } // END of area-id definition.

        leaf instance  {
            type  uint32;
            description "This attribute returns the instance value.";
        } // END of instance definition.

    } // END of ospfv2-segment-routing-announce-list-state definition.
    grouping ospfv2-segment-routing-announce-lists-top {
        description
            "Grouping for OSPF segment routing announce lists";
        container announce-lists {
            config false;
            description
                "OSPF segment routing announce lists";

            list announce-list {
                key "area-id";
                config false;
                description
                    "List of OSPF segment routing announce lists";
                leaf area-id  {
                    type  leafref {
                        path  "../state/area-id";
                    }
                    description "This attribute returns the area-id value.";
                } // END of area-id definition.

                container state {
                    config false;
                    description
                        "Operational state data for OSPF segment routing global block";
                    uses ospfv2-segment-routing-announce-list-state;
                } // END of state-container definition.
                uses ospfv2-segment-routing-external-prefix-lsa;
                uses ospfv2-segment-routing-external-prefix-range;
            } // End of announce-list-list
        } // END of announce-lists-container definition.
    } // END of ospfv2-segment-routing-announce-lists-top definition.
    grouping ospfv2-segment-routing-mapping-servers-state {
        description
            "Grouping for OSPF segment routing mapping servers state";
        leaf active-entries-count  {
            type  yang:counter32;
            description "Mapping servers active entries count.";
        } // END of active-entries-count definition.

        leaf inactive-entries-count  {
            type  yang:counter32;
            description "Mapping servers inactive entries count.";
        } // END of inactive-entries-count definition.

        leaf conflict-resolution-policy  {
            type  ipi-ospf-types:ospf_resolution_policy_t;
            description "Mapping servers conflict resolution policy.";
        } // END of conflict-resolution-policy definition.

    } // END of ospfv2-segment-routing-mapping-servers-state definition.
    grouping ospfv2-segment-routing-mapping-servers-active-state {
        description
            "Grouping for OSPF segment routing mapping servers active state";
        leaf prefix  {
            type  cml-data-types:cml_ipv4_addr_prefix_t;
            description "Mapping server prefix.";
        } // END of prefix definition.

        leaf sid-index  {
            type  uint32;
            description "Mapping SID index.";
        } // END of sid-index definition.

        leaf range-size  {
            type  uint32;
            description "Mapping server range size.";
        } // END of range-size definition.

        leaf last-prefix  {
            type  cml-data-types:cml_ipv4_addr_prefix_t;
            description "Mapping server last prefix.";
        } // END of last-prefix definition.

        leaf last-sid-index  {
            type  uint32;
            description "Mapping server last SID index.";
        } // END of last-sid-index definition.

        leaf binding-flags  {
            type  empty;
            description "Mapping server binding flags.";
        } // END of binding-flags definition.

        leaf preference  {
            type  uint8;
            description "Mapping server preference.";
        } // END of preference definition.

        leaf status  {
            type  ipi-ospf-types:ospf_sr_mapping_server_status_t;
            description "Mapping server status.";
        } // END of status definition.

        leaf advertising-router  {
            type  inet:ipv4-address;
            description "Mapping server advertising router.";
        } // END of advertising-router definition.

        leaf flags  {
            type  uint8;
            description "Mapping server flags.";
        } // END of flags definition.

    } // END of ospfv2-segment-routing-mapping-servers-active-state definition.
    grouping ospfv2-segment-routing-mapping-servers-active {
        description
            "Grouping for OSPF segment routing mapping servers active";
        container active-servers {
            config false;
            description
                "OSPF segment routing mapping servers active";

            list active-server {
                key "prefix";
                config false;
                description
                    "List of OSPF segment routing mapping servers active";
                leaf prefix  {
                    type  leafref {
                        path  "../state/prefix";
                    }
                    description "Use this attribute to set the segment routing mapping servers active
                                value.";
                } // END of prefix definition.

                container state {
                    config false;
                    description
                        "Operational state data for OSPF segment routing mapping servers active
                                block";
                    uses ospfv2-segment-routing-mapping-servers-active-state;
                } // END of state-container definition.
            } // End of active-server-list
        } // END of active-servers-container definition.
    } // END of ospfv2-segment-routing-mapping-servers-active definition.
    grouping ospfv2-segment-routing-mapping-servers-inactive {
        description
            "Grouping for OSPF segment routing mapping servers inactive";
        container inactive-servers {
            config false;
            description
                "OSPF segment routing mapping servers inactive";

            list inactive-server {
                key "prefix";
                config false;
                description
                    "List of OSPF segment routing mapping servers inactive";
                leaf prefix  {
                    type  leafref {
                        path  "../state/prefix";
                    }
                    description "Use this attribute to set the segment routing mapping servers inactive
                                value.";
                } // END of prefix definition.

                container state {
                    config false;
                    description
                        "Operational state data for OSPF segment routing mapping servers
                                inactive block";
                    uses ospfv2-segment-routing-mapping-servers-active-state;
                } // END of state-container definition.
            } // End of inactive-server-list
        } // END of inactive-servers-container definition.
    } // END of ospfv2-segment-routing-mapping-servers-inactive definition.
    grouping ospfv2-segment-routing-mapping-servers-top {
        description
            "Grouping for OSPF segment routing mapping servers";
        container mapping-servers {
            config false;
            description
                "Operational state data for OSPF segment routing mapping servers";
            container state {
                config false;
                description
                    "Operational state data for OSPF segment routing mapping servers";
                uses ospfv2-segment-routing-mapping-servers-state;
            } // END of state-container definition.
            uses ospfv2-segment-routing-mapping-servers-active;
            uses ospfv2-segment-routing-mapping-servers-inactive;
        } // END of mapping-servers-container definition.
    } // END of ospfv2-segment-routing-mapping-servers-top definition.
    grouping ospfv2-segment-routing-capabilities-state {
        description
            "Grouping for OSPF segment routing capabilities state";
        leaf advertising-router  {
            type  inet:ipv4-address;
            description "Advertising router ID.";
        } // END of advertising-router definition.

        leaf-list algorithms  {
            type  ipi-ospf-types:ospf_sr_algorithm_t;
            description "Algorithm to calculate reachability to other nodes.";
        } // END of algorithms definition.

        leaf entropy-capability  {
            type  empty;
            description "Entropy Capability.";
        } // END of entropy-capability definition.

        leaf entropy-readable-label-depth  {
            type  uint8;
            description "Entropy Label Readable Label Depth.";
        } // END of entropy-readable-label-depth definition.

        leaf mapping-server-preference  {
            type  uint8;
            description "Mapping server preference.";
        } // END of mapping-server-preference definition.

    } // END of ospfv2-segment-routing-capabilities-state definition.
    grouping ospfv2-segment-routing-capability-sid-range-state {
        description
            "Grouping for OSPF segment routing capability sid range state";
        leaf start  {
            type  uint32;
            description "Use this attribute to set the segment routing start range value.";
        } // END of start definition.

        leaf end  {
            type  uint32;
            description "Use this attribute to set the segment routing end range value.";
        } // END of end definition.

    } // END of ospfv2-segment-routing-capability-sid-range-state definition.
    grouping ospfv2-segment-routing-capability-sid-range {
        description
            "Grouping for OSPF segment routing capability ranges";
        container sid-ranges {
            config false;
            description
                "OSPF segment routing capability sid ranges";

            list sid-range {
                key "start end";
                config false;
                description
                    "List of OSPF segment routing capability sid ranges";
                leaf start  {
                    type  leafref {
                        path  "../state/start";
                    }
                    description "Use this attribute to set the segment routing start range value.";
                } // END of start definition.

                leaf end  {
                    type  leafref {
                        path  "../state/end";
                    }
                    description "Use this attribute to set the segment routing end range value.";
                } // END of end definition.

                container state {
                    config false;
                    description
                        "Operational state data for OSPF segment routing ranges block";
                    uses ospfv2-segment-routing-capability-sid-range-state;
                } // END of state-container definition.
            } // End of sid-range-list
        } // END of sid-ranges-container definition.
    } // END of ospfv2-segment-routing-capability-sid-range definition.
    grouping ospfv2-segment-routing-capability-sid-state {
        description
            "Grouping for OSPF segment routing capability sid state";
        leaf total-supported  {
            type  uint32;
            description "Total number of supported ranges.";
        } // END of total-supported definition.

        leaf range-count  {
            type  uint32;
            description "Range count.";
        } // END of range-count definition.

    } // END of ospfv2-segment-routing-capability-sid-state definition.
    grouping ospfv2-segment-routing-capability-sid {
        description
            "Grouping for OSPF segment routing segment identifier";
        container segment-identifier {
            config false;
            description
                "OSPF segment routing capabilities";
            container state {
                config false;
                description
                    "Operational state data for OSPF segment routing segment identifier";
                uses ospfv2-segment-routing-capability-sid-state;
            } // END of state-container definition.
            uses ospfv2-segment-routing-capability-sid-range;
        } // END of segment-identifier-container definition.
    } // END of ospfv2-segment-routing-capability-sid definition.
    grouping ospfv2-segment-routing-capabilities-top {
        description
            "Grouping for OSPF segment routing capabilities";
        container capabilities {
            config false;
            description
                "OSPF segment routing capabilities";

            list capability {
                key "advertising-router";
                config false;
                description
                    "List of OSPF segment routing capabilities";
                leaf advertising-router  {
                    type  leafref {
                        path  "../state/advertising-router";
                    }
                    description "Use this attribute to set the segment routing advertising router ID.";
                } // END of advertising-router definition.

                container state {
                    config false;
                    description
                        "Operational state data for OSPF segment routing capabilities block";
                    uses ospfv2-segment-routing-capabilities-state;
                } // END of state-container definition.
                uses ospfv2-segment-routing-capability-sid;
            } // End of capability-list
        } // END of capabilities-container definition.
    } // END of ospfv2-segment-routing-capabilities-top definition.
    grouping ospfv2-segment-routing-top {
        description
            "Grouping for OSPF segment routing";
        container segment-routing {
            if-feature feature-list:HAVE_SR_MPLS;
            description
                "OSPF segment routing";
            container config {
                description
                    "Configuration data for OSPF segment routing";
                uses ospfv2-segment-routing-config;
            } // END of config-container definition.
            container state {
                config false;
                description
                    "Operational state data for OSPF segment routing";
                uses ospfv2-segment-routing-config;
            } // END of state-container definition.
            uses ospfv2-segment-routing-global-block-top;
            uses ospfv2-segment-routing-prefix-sid-map-top;
            uses ospfv2-segment-routing-announce-lists-top;
            uses ospfv2-segment-routing-mapping-servers-top;
            uses ospfv2-segment-routing-capabilities-top;
        } // END of segment-routing-container definition.
    } // END of ospfv2-segment-routing-top definition.
    grouping ospfv2-default-information-config {
        description
            "Grouping for OSPF default information configuration data";
        leaf originate  {
            type  empty;
            description "Use this attribute to create a default external route into an OSPF
                        routing domain. The system acts like an
                        Autonomous System Boundary Router (ASBR) when you use the
                        default-information originate command
                        to redistribute routes into an OSPF routing domain. An ASBR does not
                        by default generate a default
                        route into the OSPF routing domain";
        } // END of originate definition.

        leaf always-advertise-default-route  {
            // when " ipi-ospf:ospfv2/processes/process/default-information/config/originate ";
            type  empty;
            description "Use this attribute to dvertise the default route regardless of whether
                        there is a default route.";
        } // END of always-advertise-default-route definition.

        leaf metric  {
            // when " ipi-ospf:ospfv2/processes/process/default-information/config/originate ";
            type  uint32 {
                 range "0..16777214"  {
                    description "0..16777214: Supported range 0 - 16777214";
                 }
            }
            default "10";
            description "Use this attribute to set the OSPF area with default metric.";
        } // END of metric definition.

        leaf metric-type  {
            // when " ipi-ospf:ospfv2/processes/process/default-information/config/originate ";
            type  ipi-ospf-types:ospf_metric_type_t;
            default "2";
            description "Use this attribute to set the OSPF area default metric type.";
        } // END of metric-type definition.

        leaf route-map  {
            // when " ipi-ospf:ospfv2/processes/process/default-information/config/originate ";
            type  string {
                length "1..1965";
                pattern "[^?' =,>|]+";
            }
            description "Use this attribute to set route-map instance.";
        } // END of route-map definition.

    } // END of ospfv2-default-information-config definition.
    grouping ospfv2-default-information-top {
        description
            "Grouping for OSPF default information";
        container default-information {
            description
                "Container for OSPF default information";
            container config {
                description
                    "Configuration data for default information";
                uses ospfv2-default-information-config;
            } // END of config-container definition.
            container state {
                config false;
                description
                    "Operational state data for default information";
                uses ospfv2-default-information-config;
            } // END of state-container definition.
        } // END of default-information-container definition.
    } // END of ospfv2-default-information-top definition.
    grouping ospfv2-passive-interface-address-config {
        description
            "Grouping for OSPF passive interface address configuration data";
        leaf address  {
            type  inet:ipv4-address;
            description "Use this attribute to set the specified interface address as passive.";
        } // END of address definition.

        leaf passive-mode  {
            type  ipi-ospf-types:ospf_passive_addr_mode_t;
            mandatory true;
            description "Use this attribute to define the passive mode.";
        } // END of passive-mode definition.

    } // END of ospfv2-passive-interface-address-config definition.
    grouping ospfv2-passive-interface-addresses-top {
        description
            "Grouping for OSPF passive interface address";
        container passive-addresses {
            description
                "Passive interface address";

            list passive-address {
                key "address";
                description
                    "List of OSPF passive interfaces";
                leaf address  {
                    type  leafref {
                        path  "../config/address";
                    }
                    description "Use this attribute to set interface address as passive.";
                } // END of address definition.

                container config {
                    description
                        "Configuration data for OSPF passive interface";
                    uses ospfv2-passive-interface-address-config;
                } // END of config-container definition.
                container state {
                    config false;
                    description
                        "Operational state data for OSPF passive interface state";
                    uses ospfv2-passive-interface-address-config;
                } // END of state-container definition.
            } // End of passive-address-list
        } // END of passive-addresses-container definition.
    } // END of ospfv2-passive-interface-addresses-top definition.
    grouping ospfv2-passive-interface-name-config {
        description
            "Grouping for OSPF passive interface configuration data";
        leaf name  {
            type  leafref {
                path  "/ipi-interface:interfaces/ipi-interface:interface/ipi-interface:name";
            }
            description "Use this attribute to set interface as passive.";
        } // END of name definition.

        leaf passive-mode  {
            type  ipi-ospf-types:ospf_passive_mode_t;
            description "Use this attribute to define the passive mode.";
        } // END of passive-mode definition.

    } // END of ospfv2-passive-interface-name-config definition.
    grouping ospfv2-passive-interface-all-config {
        description
            "Grouping for OSPF passive interface all configuration data";
        leaf passive-interface-all  {
            type  empty;
            description "Use this attribute to set all interfaces as passive.";
        } // END of passive-interface-all definition.

    } // END of ospfv2-passive-interface-all-config definition.
    grouping ospfv2-passive-interface-name-top {
        description
            "Grouping for OSPF passive interface name";

        list passive-interface {
            key "name";
            description
                "List of OSPF passive interfaces";
            leaf name  {
                type  leafref {
                    path  "../config/name";
                }
                description "Use this attribute to set interface as passive.";
            } // END of name definition.

            container config {
                description
                    "Configuration data for OSPF passive interface";
                uses ospfv2-passive-interface-name-config;
            } // END of config-container definition.
            container state {
                config false;
                description
                    "Operational state data for OSPF passive interface state";
                uses ospfv2-passive-interface-name-config;
            } // END of state-container definition.
            uses ospfv2-passive-interface-addresses-top;
        } // End of passive-interface-list
    } // END of ospfv2-passive-interface-name-top definition.
    grouping ospfv2-passive-interface-top {
        description
            "Grouping for OSPF passive interface";
        container passive-interfaces {
            // when " not(/ipi-ospf:ospfv2/ipi-ospf:global/ipi-ospf:config/ipi-ospf:area-interface-config-mode) ";
            description
                "OSPF passive interfaces";
            container config {
                description
                    "Configuration data for OSPF passive interface all";
                uses ospfv2-passive-interface-all-config;
            } // END of config-container definition.
            container state {
                config false;
                description
                    "Operational state data for OSPF passive interface all";
                uses ospfv2-passive-interface-all-config;
            } // END of state-container definition.
            uses ospfv2-passive-interface-name-top;
        } // END of passive-interfaces-container definition.
    } // END of ospfv2-passive-interface-top definition.
    grouping ospfv2-lsdb-overflow-external-lsa-config {
        description
            "Grouping for OSPF LSDB overflow external LSA configuration data";
        leaf max-limit  {
            // when " ../exit-interval ";
            type  uint32 {
                 range "0..2147483647"  {
                    description "0..2147483647: Supported range 0 - 2147483647";
                 }
            }
            mandatory true;
            description "Use this attribute to set the maximum number of external LSAs. This
                        value should be the same on all routers in the AS.";
        } // END of max-limit definition.

        leaf exit-interval  {
            // when " ../max-limit ";
            type  uint16 {
                 range "0..65535"  {
                    description "0..65535: Supported range 0 - 65535";
                 }
            }
            units "seconds";
            mandatory true;
            description "Use this attrobute to set the number of seconds the router waits
                        before trying to exit the database overflow state. If this parameter
                        is 0, the router exits the overflow state only after an explicit
                        administrator command. Default value is 0.";
        } // END of exit-interval definition.

    } // END of ospfv2-lsdb-overflow-external-lsa-config definition.
    grouping ospfv2-lsdb-overflow-external-lsa-top {
        description
            "Grouping for OSPF LSDB overflow external LSA";
        container external-lsa {
            if-feature feature-list:HAVE_OSPF_DB_OVERFLOW;
            description
                "OSPF LSDB overflow external LSA";
            container config {
                presence "Enableing Ospfv2 overflow external lsa config";
                description
                    "Configuration data for OSPF LSDB overflow external LSA";
                uses ospfv2-lsdb-overflow-external-lsa-config;
            } // END of config-container definition.
            container state {
                config false;
                description
                    "Operational state data for OSPF LSDB overflow external LSA";
                uses ospfv2-lsdb-overflow-external-lsa-config;
            } // END of state-container definition.
        } // END of external-lsa-container definition.
    } // END of ospfv2-lsdb-overflow-external-lsa-top definition.
    grouping ospfv2-lsdb-overflow-normal-lsa-config {
        description
            "Grouping for OSPF LSDB overflow normal LSA configuration data";
        leaf max-limit  {
            // when " ../limit-type ";
            type  uint32 {
                 range "0..4294967294"  {
                    description "0..4294967294: Supported range 0 - 4294967294";
                 }
            }
            mandatory true;
            description "Use this attribute to set the maximum number of normal LSAs.";
        } // END of max-limit definition.

        leaf limit-type  {
            // when " ../max-limit ";
            type  ipi-ospf-types:ospf_db_limit_type_t;
            mandatory true;
            description "Use this attribute to set the limit type.
                        Soft limit: Warning message appears if the number of LSAs exceeds the
                        specified value;
                        Hard limit: Shutdown occurs if the number of LSAs exceeds the
                        specified value. Default value is 2.";
        } // END of limit-type definition.

    } // END of ospfv2-lsdb-overflow-normal-lsa-config definition.
    grouping ospfv2-lsdb-overflow-normal-lsa-top {
        description
            "Grouping for OSPF LSDB overflow normal LSA";
        container normal-lsa {
            description
                "OSPF LSDB overflow normal LSA";
            container config {
                presence "Configuring ospfv2 overflow normal lsa";
                description
                    "Configuration data for OSPF LSDB overflow normal LSA";
                uses ospfv2-lsdb-overflow-normal-lsa-config;
            } // END of config-container definition.
            container state {
                config false;
                description
                    "Operational state data for OSPF LSDB overflow normal LSA";
                uses ospfv2-lsdb-overflow-normal-lsa-config;
            } // END of state-container definition.
        } // END of normal-lsa-container definition.
    } // END of ospfv2-lsdb-overflow-normal-lsa-top definition.
    grouping ospfv2-lsdb-top {
        description
            "Grouping for OSPF link-state database (LSDB)";
        container lsdb {
            description
                "OSPF link-state database (LSDB)";
            container overflow {
                description
                    "OSPF LSDB overflow";
                uses ospfv2-lsdb-overflow-normal-lsa-top;
                uses ospfv2-lsdb-overflow-external-lsa-top;
                uses ospfv2-lsdb-overflow-external-lsa;
            } // END of overflow-container definition.
        } // END of lsdb-container definition.
    } // END of ospfv2-lsdb-top definition.
    grouping ospfv2-capability-config {
        description
            "Grouping for OSPF capability configuration data";
        leaf disable-cspf  {
            if-feature feature-list:HAVE_OSPF_CSPF;
            type  empty;
            description "Use this attribute to enable the CSPF (Constrained Shortest Path
                        First) feature. The default value for CSPF is enabled.";
        } // END of disable-cspf definition.

        leaf enable-vrf-lite  {
            if-feature feature-list:HAVE_VRF_OSPF;
            type  empty;
            description "Use this attribute to enable VRF-lite feature.";
        } // END of enable-vrf-lite definition.

        leaf disable-opaque-lsa  {
            if-feature feature-list:HAVE_OPAQUE_LSA;
            type  empty;
            description "Use this attribute to enable opaque-LSAs which are Type 9, 10 and 11
                        LSAs.";
        } // END of disable-opaque-lsa definition.

        leaf disable-traffic-engineering  {
            if-feature feature-list:HAVE_OSPF_TE;
            type  empty;
            description "Use this attribute to enable OSPF Traffic Engineering feature.";
        } // END of disable-traffic-engineering definition.

        leaf disable-graceful-restart  {
            if-feature feature-list:HAVE_RESTART;
            type  empty;
            description "Graceful OSPF Restart.";
        } // END of disable-graceful-restart definition.

        leaf link-local-signaling  {
            if-feature feature-list:HAVE_RESTART;
            type  empty;
            description "Use this attribute to enable link-local signaling feature.";
        } // END of link-local-signaling definition.

    } // END of ospfv2-capability-config definition.
    grouping ospfv2-capability-top {
        description
            "Grouping for OSPF capability";
        container capability {
            description
                "OSPF capability";
            container config {
                description
                    "Configuration data for OSPF capability";
                uses ospfv2-capability-config;
            } // END of config-container definition.
            container state {
                config false;
                description
                    "Operational state data for OSPF capability";
                uses ospfv2-capability-config;
            } // END of state-container definition.
        } // END of capability-container definition.
    } // END of ospfv2-capability-top definition.
    grouping ospfv2-topology-independent-lfa-config {
        description
            "Grouping for OSPF LFA topology independent configuration data";
        leaf area-id  {
            type  ipi-ospf-types:ospf_area_t;
            description "Use this attribute to set the OSPF area ID.";
        } // END of area-id definition.

    } // END of ospfv2-topology-independent-lfa-config definition.
    grouping ospfv2-topology-independent-lfa-top {
        description
            "Grouping for OSPF LFA topology independent";
        container topologies-independent-lfa {
            description
                "OSPF LFA per-prefix";

            list topology-independent-lfa {
                if-feature feature-list:HAVE_OSPF_TI_LFA;
                key "area-id";
                description
                    "OSPF LFA topology independent";
                leaf area-id  {
                    type  leafref {
                        path  "../config/area-id";
                    }
                    description "Use this attribute to set the OSPF area ID.";
                } // END of area-id definition.

                container config {
                    description
                        "Configuration data for OSPF LFA topology independent";
                    uses ospfv2-topology-independent-lfa-config;
                } // END of config-container definition.
                container state {
                    config false;
                    description
                        "Operational state data for OSPF LFA topology independent";
                    uses ospfv2-topology-independent-lfa-config;
                } // END of state-container definition.
                uses ospfv2-topology-independent-lfa-routes;
                uses ospfv2-topology-independent-lfa-neighbors;
                uses ospfv2-topology-independent-lfa-vertices;
                uses ospfv2-topology-independent-lfa-repair-lists;
            } // End of topology-independent-lfa-list
        } // END of topologies-independent-lfa-container definition.
    } // END of ospfv2-topology-independent-lfa-top definition.
    grouping ospfv2-lfa-tie-break-config {
        description
            "Grouping for OSPF LFA tie break configuration data";
        leaf type  {
            type  ipi-ospf-types:ospf_frr_tie_break_t;
            description "Use this attribute to set the tie break type.";
        } // END of type definition.

        leaf idx  {
            type  uint8 {
                 range "1..255"  {
                    description "1..255: Supported range 1 - 255";
                 }
            }
            mandatory true;
            description "Use this attribute to set the tie breaking index. A lower value has
                        higher preference.";
        } // END of idx definition.

    } // END of ospfv2-lfa-tie-break-config definition.
    grouping ospfv2-lfa-tie-breaks-top {
        description
            "Grouping for OSPF LFA tie break";
        container tie-breaks {
            description
                "OSPF LFA tie break";

            list tie-break {
                key "type";
                description
                    "List of OSPF LFA tie break";
                leaf type  {
                    type  leafref {
                        path  "../config/type";
                    }
                    description "Use this attribute to set the tie break type.";
                } // END of type definition.

                container config {
                    description
                        "Configuration data for OSPF LFA tie break";
                    uses ospfv2-lfa-tie-break-config;
                } // END of config-container definition.
                container state {
                    config false;
                    description
                        "Operational state data for OSPF LFA tie break";
                    uses ospfv2-lfa-tie-break-config;
                } // END of state-container definition.
            } // End of tie-break-list
        } // END of tie-breaks-container definition.
    } // END of ospfv2-lfa-tie-breaks-top definition.
    grouping ospfv2-lfa-fast-reroute-config {
        description
            "Grouping for OSPF LFA fast-reroute configuration data";
        leaf keep-all-paths  {
            type  empty;
            description "Use this attribute to enable fast rerouting on all OSPF interfaces.";
        } // END of keep-all-paths definition.

        leaf-list remote-lfa-areas  {
            if-feature feature-list:HAVE_LDPD;
            type  ipi-ospf-types:ospf_area_t;
            description "Use this attribute to set remote-lfa for OSPF area.";
        } // END of remote-lfa-areas definition.

        leaf route-map  {
            type  string {
                length "1..1965";
                pattern "[^?' =,>|]+";
            }
            description "Use this attribute to set route-map for FRR.";
        } // END of route-map definition.

    } // END of ospfv2-lfa-fast-reroute-config definition.
    grouping ospfv2-lfa-fast-reroute-top {
        description
            "Grouping for OSPF LFA fast-reroute";
        container fast-reroute {
            description
                "OSPF LFA fast-reroute";
            container config {
                description
                    "Configuration data for OSPF LFA fast-reroute";
                uses ospfv2-lfa-fast-reroute-config;
            } // END of config-container definition.
            container state {
                config false;
                description
                    "Operational state data for OSPF LFA fast-reroute";
                uses ospfv2-lfa-fast-reroute-config;
            } // END of state-container definition.
            uses ospfv2-lfa-tie-breaks-top;
            uses ospfv2-topology-independent-lfa-top;
        } // END of fast-reroute-container definition.
    } // END of ospfv2-lfa-fast-reroute-top definition.
    grouping ospfv2-lfa-top {
        description
            "Grouping for OSPF Loop Free Alternate (LFA)";
        container lfa {
            if-feature feature-list:HAVE_OSPF_LFA;
            description
                "OSPF Loop Free Alternate (LFA)";
            uses ospfv2-lfa-fast-reroute-top;
        } // END of lfa-container definition.
    } // END of ospfv2-lfa-top definition.
    grouping ospfv2-summary-address-config {
        description
            "Grouping for OSPF summary address configuration data";
        leaf address  {
            type  cml-data-types:cml_ipv4_prefix_t;
            description "Use this attribute to summarize or suppress external routes with the
                        specified address range.";
        } // END of address definition.

        leaf not-advertise  {
            type  empty;
            description "Use this attribute to suppress routes that match the address range.";
        } // END of not-advertise definition.

        leaf tag  {
            type  uint32 {
                 range "0..4294967295"  {
                    description "0..4294967295: Supported range 0 - 4294967295";
                 }
            }
            default "0";
            description "Use this attribute to set the tag value to use as a match value for
                        controlling redistribution via route maps.";
        } // END of tag definition.

    } // END of ospfv2-summary-address-config definition.
    grouping ospfv2-summary-address-top {
        description
            "Grouping for OSPF summary address";
        container summary-addresses {
            description
                "OSPF summary address";

            list summary-address {
                key "address";
                description
                    "List of OSPF summary address";
                leaf address  {
                    type  leafref {
                        path  "../config/address";
                    }
                    description "Use this attribute to summarize or suppress external routes with the
                                specified address range.";
                } // END of address definition.

                container config {
                    description
                        "Configuration data for OSPF summary address";
                    uses ospfv2-summary-address-config;
                } // END of config-container definition.
                container state {
                    config false;
                    description
                        "Operational state data for OSPF summary address";
                    uses ospfv2-summary-address-config;
                } // END of state-container definition.
            } // End of summary-address-list
        } // END of summary-addresses-container definition.
    } // END of ospfv2-summary-address-top definition.
    grouping ospfv2-domain-id-secondary-address-config {
        description
            "Grouping for OSPF secondary domain ID address configuration data";
        leaf secondary-domain-id-address  {
            type  inet:ipv4-address;
            description "Use this attribute to set the domain ID in IPv4 address format.";
        } // END of secondary-domain-id-address definition.

    } // END of ospfv2-domain-id-secondary-address-config definition.
    grouping ospfv2-domain-id-secondary-address-top {
        description
            "Grouping for OSPF secondary domain ID address";
        container addresses {
            description
                "OSPF secondary domain ID address";

            list address {
            when " /ipi-ospf:ospfv2/ipi-ospf:processes/ipi-ospf:process/ipi-ospf:domain-id/ipi-ospf:primary-domain/ipi-ospf:config/ipi-ospf:primary-domain-id-address or /ipi-ospf:ospfv2/ipi-ospf:processes/ipi-ospf:process/ipi-ospf:domain-id/ipi-ospf:primary-domain/ipi-ospf:hexes/ipi-ospf:hex ";
                if-feature feature-list:HAVE_VRF_OSPF;
                key "secondary-domain-id-address";
                description
                    "List of OSPF secondary domain ID address";
                leaf secondary-domain-id-address  {
                    type  leafref {
                        path  "../config/secondary-domain-id-address";
                    }
                    description "Use this attribute to set the secondary domain ID in IPv4 address
                                format.";
                } // END of secondary-domain-id-address definition.

                container config {
                    description
                        "Configuration data for OSPF secondary domain ID address";
                    uses ospfv2-domain-id-secondary-address-config;
                } // END of config-container definition.
                container state {
                    config false;
                    description
                        "Operational state data OSPF secondary domain ID address";
                    uses ospfv2-domain-id-secondary-address-config;
                } // END of state-container definition.
            } // End of address-list
        } // END of addresses-container definition.
    } // END of ospfv2-domain-id-secondary-address-top definition.
    grouping ospfv2-domain-id-secondary-hex-config {
        description
            "Grouping for OSPF secondary domain ID hexadecimal configuration data";
        leaf secondary-hex-type  {
            type  ipi-ospf-types:ospf_domain_type_t;
            description "Use this attribute to set the domain hexadecimal type.";
        } // END of secondary-hex-type definition.

        leaf secondary-domain-id-hex  {
            type  ipi-ospf-types:ospf_domain_id_hex_string_t {
                length "1..1965";
            }
            description "Use this attribute to set domain ID in hexadecimal.";
        } // END of secondary-domain-id-hex definition.

    } // END of ospfv2-domain-id-secondary-hex-config definition.
    grouping ospfv2-domain-id-secondary-hex-top {
        description
            "Grouping for OSPF secondary domain ID hexadecimal";
        container hexes {
            description
                "OSPF secondaries domain ID hexadecimal";

            list hex {
            when " /ipi-ospf:ospfv2/ipi-ospf:processes/ipi-ospf:process/ipi-ospf:domain-id/ipi-ospf:primary-domain/ipi-ospf:config/ipi-ospf:primary-domain-id-address or /ipi-ospf:ospfv2/ipi-ospf:processes/ipi-ospf:process/ipi-ospf:domain-id/ipi-ospf:primary-domain/ipi-ospf:hexes/ipi-ospf:hex ";
                if-feature feature-list:HAVE_VRF_OSPF;
                key "secondary-hex-type secondary-domain-id-hex";
                description
                    "List of OSPF secondaries domain ID hexadecimal";
                leaf secondary-hex-type  {
                    type  leafref {
                        path  "../config/secondary-hex-type";
                    }
                    description "Use this attribute to set the secondary domain hexadecimal type.";
                } // END of secondary-hex-type definition.

                leaf secondary-domain-id-hex  {
                    type  leafref {
                        path  "../config/secondary-domain-id-hex";
                    }
                    description "Use this attribute to set secondary domain ID in hexadecimal.";
                } // END of secondary-domain-id-hex definition.

                container config {
                    description
                        "Configuration data for OSPF secondary domain ID hexadecimal";
                    uses ospfv2-domain-id-secondary-hex-config;
                } // END of config-container definition.
                container state {
                    config false;
                    description
                        "Operational state data for OSPF secondary domain ID hexadecimal";
                    uses ospfv2-domain-id-secondary-hex-config;
                } // END of state-container definition.
            } // End of hex-list
        } // END of hexes-container definition.
    } // END of ospfv2-domain-id-secondary-hex-top definition.
    grouping ospfv2-domain-id-primary-hex-config {
        description
            "Grouping for OSPF primary domain ID hexadecimal configuration data";
        leaf primary-hex-type  {
            type  ipi-ospf-types:ospf_domain_type_t;
            description "Use this attribute to set the domain hexadecimal type.";
        } // END of primary-hex-type definition.

        leaf primary-domain-id-hex  {
            type  ipi-ospf-types:ospf_domain_id_hex_string_t {
                length "1..1965";
            }
            description "Use this attribute to set domain ID in hexadecimal.";
        } // END of primary-domain-id-hex definition.

    } // END of ospfv2-domain-id-primary-hex-config definition.
    grouping ospfv2-domain-id-primary-hex-top {
        description
            "Grouping for OSPF primary domain ID hexadecimal";
        container hexes {
            description
                "OSPF primary domain ID hexadecimal";

            list hex {
            // when " not(/ipi-ospf:ospfv2/ipi-ospf:processes/ipi-ospf:process/ipi-ospf:domain-id/ipi-ospf:primary-domain/ipi-ospf:config/ipi-ospf:primary-domain-id-address) ";
                if-feature feature-list:HAVE_VRF_OSPF;
                key "primary-hex-type primary-domain-id-hex";
                max-elements 1;
                description
                    "List of OSPF primary domain ID hexadecimal";
                leaf primary-hex-type  {
                    type  leafref {
                        path  "../config/primary-hex-type";
                    }
                    description "Use this attribute to set the domain hexadecimal type.";
                } // END of primary-hex-type definition.

                leaf primary-domain-id-hex  {
                    type  leafref {
                        path  "../config/primary-domain-id-hex";
                    }
                    description "Use this attribute to set domain ID in hexadecimal.";
                } // END of primary-domain-id-hex definition.

                container config {
                    description
                        "Configuration data for OSPF primary domain ID hexadecimal";
                    uses ospfv2-domain-id-primary-hex-config;
                } // END of config-container definition.
                container state {
                    config false;
                    description
                        "Operational state data for OSPF primary domain ID hexadecimal";
                    uses ospfv2-domain-id-primary-hex-config;
                } // END of state-container definition.
            } // End of hex-list
        } // END of hexes-container definition.
    } // END of ospfv2-domain-id-primary-hex-top definition.
    grouping ospfv2-domain-id-config {
        description
            "Grouping for OSPF domain ID configuration data";
        leaf primary-domain-id-address  {
            // when " not(/ipi-ospf:ospfv2/ipi-ospf:processes/ipi-ospf:process/ipi-ospf:domain-id/ipi-ospf:primary-domain/ipi-ospf:hexes/ipi-ospf:hex/ipi-ospf:config/ipi-ospf:primary-domain-id-hex) ";
            type  inet:ipv4-address;
            description "Use this attribute to set the domain ID in IPv4 address format.";
        } // END of primary-domain-id-address definition.

    } // END of ospfv2-domain-id-config definition.
    grouping ospfv2-domain-id-top {
        description
            "Grouping for OSPF domain ID";
        container domain-id {
            description
                "OSPF domain ID";
            container primary-domain {
                if-feature feature-list:HAVE_VRF_OSPF;
                description
                    "OSPF primary domain ID";
                container config {
                    description
                        "Configuration data for OSPF primary domain ID";
                    uses ospfv2-domain-id-config;
                } // END of config-container definition.
                container state {
                    config false;
                    description
                        "Operational state data for OSPF primary domain ID";
                    uses ospfv2-domain-id-config;
                } // END of state-container definition.
                uses ospfv2-domain-id-primary-hex-top;
            } // END of primary-domain-container definition.
            container secondary-domain {
                description
                    "OSPF secondary domain ID";
                uses ospfv2-domain-id-secondary-address-top;
                uses ospfv2-domain-id-secondary-hex-top;
            } // END of secondary-domain-container definition.
        } // END of domain-id-container definition.
    } // END of ospfv2-domain-id-top definition.
    grouping ospfv2-distribute-bgp-ls-config {
        description
            "Grouping for OSPF distribute BGP linkstate configuration data";
        leaf enabled  {
            type  empty;
            description "Use this attribute to distribute linkstate and TE Database to BGP.";
        } // END of enabled definition.

        leaf throttle-timer  {
            // when " ipi-ospf:ospfv2/processes/process/distribute/bgp-link-state/config/enabled ";
            type  uint8 {
                 range "5..20"  {
                    description "5..20: Supported range 5 - 20";
                 }
            }
            units "seconds";
            default "5";
            description "Use this attribute to set interval between processing LS DB.";
        } // END of throttle-timer definition.

    } // END of ospfv2-distribute-bgp-ls-config definition.
    grouping ospfv2-distribute-bgp-ls-top {
        description
            "Grouping for OSPF distribute BGP linkstate";
        container bgp-link-state {
            description
                "OSPF distribute BGP linkstate";
            container config {
                description
                    "Configuration data for OSPF distribute BGP linkstate";
                uses ospfv2-distribute-bgp-ls-config;
            } // END of config-container definition.
            container state {
                config false;
                description
                    "Operational state data for OSPF distribute BGP linkstate";
                uses ospfv2-distribute-bgp-ls-config;
            } // END of state-container definition.
        } // END of bgp-link-state-container definition.
    } // END of ospfv2-distribute-bgp-ls-top definition.
    grouping ospfv2-distribute-top {
        description
            "Grouping for OSPF distribute";
        container distribute {
            if-feature feature-list:HAVE_BGP_LS;
            description
                "OSPF distribute";
            uses ospfv2-distribute-bgp-ls-top;
        } // END of distribute-container definition.
    } // END of ospfv2-distribute-top definition.
    grouping ospfv2-neighbor-config {
        description
            "Grouping for OSPF neighbor configuration data";
        leaf address  {
            type  inet:ipv4-address;
            description "Use this attribute to set the interface IP address of the neighbor.";
        } // END of address definition.

        leaf cost  {
            type  uint16 {
                 range "1..65535"  {
                    description "1..65535: Supported range 1 - 65535";
                 }
            }
            default "10";
            description "Use this attribute to set the router cost for point-to-multipoint
                        neighbor.";
        } // END of cost definition.

        leaf priority  {
            type  uint8 {
                 range "0..255"  {
                    description "0..255: Supported range 0 - 255";
                 }
            }
            default "0";
            description "Use this attribute to set the router priority of the non-broadcast
                        neighbor associated with the specified IP address.This parameter does
                        not apply to point-to-multipoint interfaces.";
        } // END of priority definition.

        leaf poll-interval  {
            type  uint32 {
                 range "1..2147483647"  {
                    description "1..2147483647: Supported range 1 - 2147483647";
                 }
            }
            units "seconds";
            default "120";
            description "Use this attribute to set the rate at which routers continue to send
                        hello packets when a neighboring router has become inactive. This
                        value much larger than hello interval.";
        } // END of poll-interval definition.

    } // END of ospfv2-neighbor-config definition.
    grouping ospfv2-discovered-neighbor-state {
        description
            "Grouping for discovered OSPF neighbor data";
        leaf nbr-address  {
            type  inet:ipv4-address;
            config false;
            description "OSPF Neighbor address.";
        } // END of nbr-address definition.

        leaf nbr-router-id  {
            type  inet:ipv4-address;
            config false;
            description "OSPF Neighbor Router ID.";
        } // END of nbr-router-id definition.

        leaf nbr-priority  {
            type  uint8;
            config false;
            description "OSPF Neighbor Priority.";
        } // END of nbr-priority definition.

        leaf nbr-state  {
            type  cml-data-types:cml_line_t {
                length "1..1965";
            }
            config false;
            description "OSPF Neighbor State.";
        } // END of nbr-state definition.

        leaf dead-time  {
            type  string {
                length "1..1965";
                pattern "[^?' =,>|]+";
            }
            config false;
            description "OSPF Neighbor Dead time.";
        } // END of dead-time definition.

        leaf if-name  {
            type  string {
                length "1..1965";
                pattern "[^?' =,>|]+";
            }
            config false;
            description "OSPF Neighbor Interface name.";
        } // END of if-name definition.

        leaf instanceid  {
            type  uint8;
            config false;
            description "OSPF Neighbor Instance ID.";
        } // END of instanceid definition.

    } // END of ospfv2-discovered-neighbor-state definition.
    grouping ospfv2-discovered-neighbors-top {
        description
            "Grouping for OSPF discovered neighbor";
        container discovered-neighbors {
            config false;
            description
                "OSPF discovered neighbor data";

            list discovered-neighbor {
                key "nbr-address";
                config false;
                description
                    "List of discovered OSPF neighbors";
                leaf nbr-address  {
                    type  leafref {
                        path  "../state/nbr-address";
                    }
                    description "OSPF Neighbor address.";
                } // END of nbr-address definition.

                container state {
                    config false;
                    description
                        "Operational state data";
                    uses ospfv2-discovered-neighbor-state;
                } // END of state-container definition.
            } // End of discovered-neighbor-list
        } // END of discovered-neighbors-container definition.
    } // END of ospfv2-discovered-neighbors-top definition.
    grouping ospfv2-neighbor-top {
        description
            "Grouping for OSPF neighbor";
        container neighbors {
            description
                "OSPF neighbors";

            list neighbor {
                key "address";
                description
                    "List of OSPF neighbors";
                leaf address  {
                    type  leafref {
                        path  "../config/address";
                    }
                    description "Use this attribute to set the interface IP address of the neighbor.";
                } // END of address definition.

                container config {
                    description
                        "Configuration data for OSPF neighbor";
                    uses ospfv2-neighbor-config;
                } // END of config-container definition.
                container state {
                    config false;
                    description
                        "Operational state data for OSPF neighbor";
                    uses ospfv2-neighbor-config;
                } // END of state-container definition.
                uses ospfv2-neighbor-state-change;
                uses ospfv2-tx-retransmit;
            } // End of neighbor-list
        } // END of neighbors-container definition.
    } // END of ospfv2-neighbor-top definition.
    grouping ospfv2-process-config {
        description
            "Grouping for OSPF process configuration data";
        leaf ospf-id  {
            type  uint16;
            description "Use this attribute to set the OSPF process ID.";
        } // END of ospf-id definition.

        leaf vrf-name  {
            if-feature feature-list:HAVE_VRF;
            type  leafref {
                path  "/ipi-network-instance:network-instances/ipi-network-instance:network-instance/ipi-vrf:vrf/ipi-vrf:config/ipi-vrf:vrf-name";
            }
            mandatory true;
            description "Use this attribute to set the VRF name to associate with this
                        instance.";
        } // END of vrf-name definition.

        leaf router-id  {
            type  inet:ipv4-address;
            description "Use this attribute to set a router ID for the OSPF process. Configure
                        each router OSPF with an unique router ID.";
        } // END of router-id definition.

        leaf flood-reduction  {
            type  empty;
            description "Use this attribute to enable flood reduction on all OSPF interfaces.";
        } // END of flood-reduction definition.

        leaf rfc1583-compatibility  {
            type  empty;
            description "Use this attribute to restore the method used to calculate summary
                        route costs per RFC 1583.";
        } // END of rfc1583-compatibility definition.

        leaf database-summary  {
            type  empty;
            description "Use this attribute to enable the database summary list optimization.";
        } // END of database-summary definition.

        leaf bfd-enable-all-interfaces  {
            if-feature feature-list:HAVE_BFD;
            type  empty;
            description "Use this attribute to enable Bidirectional Forwarding Detection (BFD)
                        on all interfaces.";
        } // END of bfd-enable-all-interfaces definition.

        leaf log-adjacency-changes  {
            type  ipi-ospf-types:ospf_log_adj_opt_t;
            default "brief";
            description "Use this attribute for the router to send a SYSLOG message when an
                        OSPF neighbor goes up or down.";
        } // END of log-adjacency-changes definition.

        leaf shutdown  {
            type  empty;
            description "Use this attribute to shutdown OSPF process.";
        } // END of shutdown definition.

        leaf area-border-type  {
            type  ipi-ospf-types:ospf_abr_type_t;
            default "cisco";
            description "Use this attribute to set an OSPF Area Border Router (ABR) type.";
        } // END of area-border-type definition.

        leaf reference-bandwidth  {
            type  uint32 {
                 range "1..4294967"  {
                    description "1..4294967: Supported range 1 - 4294967";
                 }
            }
            units "mbps";
            default "100";
            description "Use this attribute to control how OSPF calculates the default metric
                        for the interface.";
        } // END of reference-bandwidth definition.

        leaf max-database-descriptors  {
            type  uint16 {
                 range "1..65535"  {
                    description "1..65535: Supported range 1 - 65535";
                 }
            }
            default "64";
            description "Use this attribute to limit the number of Database Descriptors (DD)
                        that can be processed concurrently.";
        } // END of max-database-descriptors definition.

        leaf p2p-rfc-incompatible  {
            type  empty;
            description "Use this attribute to enable unicast packet on point-point interface.";
        } // END of p2p-rfc-incompatible definition.

        leaf context-name  {
            type  string {
                length "1..32";
                pattern "[^?' =,>|]+";
            }
            description "Use this attribute to set the SNMP context name for OSPF instance.";
        } // END of context-name definition.

    } // END of ospfv2-process-config definition.
    grouping ospfv2-max-metric-on-startup-config {
        description
            "Grouping for OSPF max metrics configuration data";
        leaf max-on-startup  {
            type  uint32 {
                 range "5..86400"  {
                    description "5..86400: Supported range 5 - 86400";
                 }
            }
            mandatory true;
            description "Use this attribute to set the metric for router LSA on-startup for the
                        transit link to the default max metric.";
        } // END of max-on-startup definition.

        leaf max-on-startup-external-lsa  {
            type  uint32 {
                 range "1..16777215"  {
                    description "1..16777215: Supported range 1 - 16777215";
                 }
            }
            description "Use this attribute to sets the metric for the transit link in the
                        router lsa and external lsa to the default max metric.";
        } // END of max-on-startup-external-lsa definition.

        leaf max-on-startup-summary-lsa  {
            type  uint32 {
                 range "1..16777215"  {
                    description "1..16777215: Supported range 1 - 16777215";
                 }
            }
            description "Use this attribute to set the summary LSA max metric";
        } // END of max-on-startup-summary-lsa definition.

        leaf on-startup-include-stub  {
            type  empty;
            description "Use this attribute to set the metric of a stub link in the router LSA
                        to the default max metric.";
        } // END of on-startup-include-stub definition.

    } // END of ospfv2-max-metric-on-startup-config definition.
    grouping ospfv2-max-metric-config {
        description
            "Grouping for OSPF max metrics configuration data";
        leaf enable-max-router-lsa  {
            type  empty;
            mandatory true;
            description "Use this attribute to set the metric in the router LSA to the default
                        max metric.";
        } // END of enable-max-router-lsa definition.

        leaf max-external-lsa  {
            type  uint32 {
                 range "1..16777215"  {
                    description "1..16777215: Supported range 1 - 16777215";
                 }
            }
            description "Use this attribute to sets the metric for the transit link in the
                        router lsa and external lsa to the default max metric.";
        } // END of max-external-lsa definition.

        leaf max-summary-lsa  {
            type  uint32 {
                 range "1..16777215"  {
                    description "1..16777215: Supported range 1 - 16777215";
                 }
            }
            description "Use this attribute to set the summary LSA max metric";
        } // END of max-summary-lsa definition.

        leaf include-stub  {
            type  empty;
            description "Use this attribute to set the metric of a stub link in the router LSA
                        to the default max metric.";
        } // END of include-stub definition.

    } // END of ospfv2-max-metric-config definition.
    grouping ospfv2-max-metric-router-lsa-top {
        description
            "Grouping for OSPF max metrics configuration data";
        container max-metric {
            if-feature feature-list:HAVE_OSPF_STUB_ROUTER;
            description
                "OSPF processes";
            container config {
                presence "max-metric router lsa config";
                description
                    "Configuration data for OSPF process";
                uses ospfv2-max-metric-config;
            } // END of config-container definition.
            container state {
                config false;
                description
                    "Operational state data for OSPF max metric";
                uses ospfv2-max-metric-config;
            } // END of state-container definition.
        } // END of max-metric-container definition.
    } // END of ospfv2-max-metric-router-lsa-top definition.
    grouping ospfv2-max-metric-on-startup-top {
        description
            "Grouping for OSPF max metrics configuration data";
        container max-metric-on-startup {
            if-feature feature-list:HAVE_OSPF_STUB_ROUTER;
            description
                "OSPF processes";
            container config {
                presence "max-metric on-startup config";
                description
                    "Configuration data for OSPF process";
                uses ospfv2-max-metric-on-startup-config;
            } // END of config-container definition.
            container state {
                config false;
                description
                    "Operational state data for OSPF on start up max metric";
                uses ospfv2-max-metric-on-startup-config;
            } // END of state-container definition.
        } // END of max-metric-on-startup-container definition.
    } // END of ospfv2-max-metric-on-startup-top definition.
    grouping ospfv2-processes-top {
        description
            "Grouping for OSPF process";
        container processes {
            description
                "OSPF processes";

            list process {
                key "ospf-id";
                description
                    "List of OSPF processes";
                leaf ospf-id  {
                    type  leafref {
                        path  "../config/ospf-id";
                    }
                    description "Use this attribute to set the OSPF process ID.";
                } // END of ospf-id definition.

                container config {
                    description
                        "Configuration data for OSPF process";
                    uses ospfv2-process-config;
                } // END of config-container definition.
                container state {
                    config false;
                    description
                        "Operational state data for OSPF process";
                    container statistics {
                        config false;
                        description
                            "OSPFv2 statistics status";
                        container router {
                            config false;
                            description
                                "OSPFv2 router status";
                            uses ospfv2-router-state;
                        } // END of router-container definition.
                        container database-description-exchanges {
                            config false;
                            description
                                "OSPFv2 database description exchanges status";
                            uses ospfv2-db-desc-exchanges;
                        } // END of database-description-exchanges-container definition.
                        container link-state-advertisement {
                            config false;
                            description
                                "OSPFv2 link state advertisement status";
                            uses ospfv2-statistics-lsa;
                        } // END of link-state-advertisement-container definition.
                        container router-event {
                            config false;
                            description
                                "OSPFv2 router event status";
                            container packet {
                                config false;
                                description
                                    "OSPFv2 router event packets status";
                                uses ospfv2-router-event-packets;
                            } // END of packet-container definition.
                            container lsa {
                                config false;
                                description
                                    "OSPFv2 router event lsa status";
                                uses ospfv2-router-event-lsa;
                            } // END of lsa-container definition.
                            container spf {
                                config false;
                                description
                                    "OSPFv2 router event spf status";
                                uses ospfv2-router-event-spf;
                            } // END of spf-container definition.
                            container neighbor {
                                config false;
                                description
                                    "OSPFv2 router event neighbor status";
                                uses ospfv2-router-event-neighbor;
                            } // END of neighbor-container definition.
                            uses ospfv2-router-event;
                        } // END of router-event-container definition.
                        container error {
                            config false;
                            description
                                "OSPFv2 error status";
                            uses ospfv2-statistics-error;
                        } // END of error-container definition.
                        container traffic {
                            config false;
                            description
                                "OSPFv2 traffic status";
                            uses ospfv2-statistics-traffic;
                        } // END of traffic-container definition.
                        uses ospfv2-statistics;
                    } // END of statistics-container definition.
                    uses ospfv2-process-config;
                    uses ospfv2-processes-state;
                } // END of state-container definition.
                uses ospfv2-link-state-database;
                uses ospfv2-passive-interface-top;
                uses ospfv2-default-information-top;
                uses ospfv2-segment-routing-top;
                uses ospfv2-capability-top;
                uses ospfv2-area-top;
                uses ospfv2-lsdb-top;
                uses ospfv2-lfa-top;
                uses ospfv2-administrative-distance-top;
                uses ospfv2-summary-address-top;
                uses ospfv2-distribute-list-top;
                uses ospfv2-domain-id-top;
                uses ospfv2-distribute-top;
                uses ospfv2-neighbor-top;
                uses ospfv2-timers-top;
                uses ospfv2-redistribute-top;
                uses ospfv2-originate-lsa;
                uses ospfv2-max-metric-router-lsa-top;
                uses ospfv2-max-metric-on-startup-top;
                uses ospfv2-mpls-entropy-top;
                uses ospfv2-discovered-neighbors-top;
            } // End of process-list
        } // END of processes-container definition.
    } // END of ospfv2-processes-top definition.
    grouping ospfv2-neighbor-state-change {
        description
            "Grouping for OSPF neighbor state change";
        container neighbor-state-change {
            config false;
            description
                "Neighbor state change";
            leaf router-id  {
                type  inet:ipv4-address;
                description "Router ID for the OSPF process.";
            } // END of router-id definition.

            leaf address  {
                type  inet:ipv4-address;
                description "Neighbor IPv4 address.";
            } // END of address definition.

            leaf neighbor-address-less-index  {
                type  uint32;
                description "Neighbor address less index.";
            } // END of neighbor-address-less-index definition.

            leaf neighbor-router-id  {
                type  inet:ipv4-address;
                description "Neighbor router ID.";
            } // END of neighbor-router-id definition.

            leaf neighbor-state  {
                type  ipi-ospf-types:ospf_neighbor_state_change_t;
                description "Neighbor state.";
            } // END of neighbor-state definition.

        } // END of neighbor-state-change-container definition.
    } // END of ospfv2-neighbor-state-change definition.
    grouping ospfv2-tx-retransmit {
        description
            "ospfv2-tx-retransmit";
        container tx-retransmit {
            config false;
            description
                "OSPF TX retransmit";
            leaf router-id  {
                type  inet:ipv4-address;
                description "Router ID for the OSPF process.";
            } // END of router-id definition.

            leaf address  {
                type  inet:ipv4-address;
                description "Neighbor IPv4 address.";
            } // END of address definition.

            leaf neighbor-address-less-index  {
                type  uint32;
                description "Neighbor address less index.";
            } // END of neighbor-address-less-index definition.

            leaf neighbor-router-id  {
                type  inet:ipv4-address;
                description "Neighbor router ID.";
            } // END of neighbor-router-id definition.

            leaf packet-type  {
                type  ipi-ospf-types:ospf_packet_type_t;
                description "OSPF patcket type.";
            } // END of packet-type definition.

            leaf lsdb-type  {
                type  ipi-ospf-types:ospf_lsdb_type_t;
                description "LSDB Type.";
            } // END of lsdb-type definition.

            leaf lsdb-lsid  {
                type  inet:ipv4-address;
                description "The Link State ID.";
            } // END of lsdb-lsid definition.

            leaf lsdb-router-id  {
                type  inet:ipv4-address;
                description "LSDB router ID.";
            } // END of lsdb-router-id definition.

        } // END of tx-retransmit-container definition.
    } // END of ospfv2-tx-retransmit definition.
    grouping ospfv2-originate-lsa {
        description
            "OSPFv2 originate LSA grouping";
        container originate-lsa {
            config false;
            description
                "Originate LSA";
            leaf router-id  {
                type  leafref {
                    path  "/ospfv2/processes/process/state/router-id";
                }
                config false;
                description "The originator Router ID.";
            } // END of router-id definition.

            leaf lsdb-area-id  {
                type  inet:ipv4-address;
                config false;
                description "LSDB area ID.";
            } // END of lsdb-area-id definition.

            leaf lsdb-type  {
                type  ipi-ospf-types:ospf_lsdb_type_t;
                config false;
                description "LSDB Type.";
            } // END of lsdb-type definition.

            leaf lsdb-id  {
                type  inet:ipv4-address;
                config false;
                description "LSDB ID.";
            } // END of lsdb-id definition.

            leaf lsdb-router-id  {
                type  inet:ipv4-address;
                config false;
                description "LSDB router ID.";
            } // END of lsdb-router-id definition.

        } // END of originate-lsa-container definition.
    } // END of ospfv2-originate-lsa definition.
    grouping ospfv2-lsdb-overflow-external-lsa {
        description
            "OSPFv2 LSDB overflow external LSA notification grouping";
        container lsdb-overflow-external-lsa {
            config false;
            description
                "LSDB overflow external LSA";
            leaf router-id  {
                type  leafref {
                    path  "/ospfv2/processes/process/state/router-id";
                }
                config false;
                description "Router ID for the OSPF process.";
            } // END of router-id definition.

            leaf max-limit  {
                type  uint32;
                config false;
                description "Maximum limit maximum number of normal LSAs.";
            } // END of max-limit definition.

        } // END of lsdb-overflow-external-lsa-container definition.
    } // END of ospfv2-lsdb-overflow-external-lsa definition.

    grouping  ospfv2-grouping {
    description
        "Grouping for Open Shortest Path First (OSPF)";
    container ospfv2 {
        if-feature feature-list:HAVE_OSPFD;
        description
            "Grouping for Open Shortest Path First (OSPF)";
        uses ospfv2-global-top;
        uses ospfv2-processes-top;
        uses ospfv2-traffic-engineering-link-top;
        uses ospfv2-multi-area-interface-top;
        uses ospfv2-debug-top;
        uses interfaces-grouping;
    } // END of ospfv2-container definition.
    } // END of ospfv2-grouping definition.

    uses ospfv2-grouping;

    rpc ospfv2-terminal-debug-ospf-all-on {
        if-feature feature-list:HAVE_OSPFD;
        description "Enable all debugging";
    }

    rpc ospfv2-terminal-debug-ospf-all-off {
        if-feature feature-list:HAVE_OSPFD;
        description "Enable all debugging";
    }

    rpc ospfv2-terminal-debug-bfd-on {
        if-feature feature-list:HAVE_BFD;
        if-feature feature-list:HAVE_OSPFD;
        description "Bidirectional Forwarding Detection (BFD)";
    }

    rpc ospfv2-terminal-debug-bfd-off {
        if-feature feature-list:HAVE_BFD;
        if-feature feature-list:HAVE_OSPFD;
        description "Bidirectional Forwarding Detection (BFD)";
    }

    rpc ospfv2-terminal-debug-rate-limit-on {
        if-feature feature-list:HAVE_OSPFD;
        description "OSPF Database Timers Rate Limiting Values for LSA Throttling";
    }

    rpc ospfv2-terminal-debug-rate-limit-off {
        if-feature feature-list:HAVE_OSPFD;
        description "OSPF Database Timers Rate Limiting Values for LSA Throttling";
    }

    rpc ospfv2-terminal-debug-sr-on {
        if-feature feature-list:HAVE_SR_MPLS;
        if-feature feature-list:HAVE_OSPFD;
        description "Segment Routing";
    }

    rpc ospfv2-terminal-debug-sr-off {
        if-feature feature-list:HAVE_SR_MPLS;
        if-feature feature-list:HAVE_OSPFD;
        description "Segment Routing";
    }

    rpc ospfv2-terminal-debug-route-on {
        if-feature feature-list:HAVE_OSPFD;
        description "OSPF route information";
        input  {
            leaf route  {
                type ipi-ospf-types:ospf_debug_route_t;
                mandatory true;
                description "Use this attribute to enable OSPF route information debug.";
            }
        }
    }

    rpc ospfv2-terminal-debug-route-off {
        if-feature feature-list:HAVE_OSPFD;
        description "OSPF route information";
        input  {
            leaf route  {
                type ipi-ospf-types:ospf_debug_route_t;
                mandatory true;
                description "Use this attribute to enable OSPF route information debug.";
            }
        }
    }

    rpc ospfv2-terminal-debug-rib-on {
        if-feature feature-list:HAVE_RIBD;
        if-feature feature-list:HAVE_OSPFD;
        description "OSPF RIB information";
        input  {
            leaf rib  {
                type ipi-ospf-types:ospf_debug_rib_t;
                mandatory true;
                description "Use this attribute to enable OSPF RIB information debug.";
            }
        }
    }

    rpc ospfv2-terminal-debug-rib-off {
        if-feature feature-list:HAVE_RIBD;
        if-feature feature-list:HAVE_OSPFD;
        description "OSPF RIB information";
        input  {
            leaf rib  {
                type ipi-ospf-types:ospf_debug_rib_t;
                mandatory true;
                description "Use this attribute to enable OSPF RIB information debug.";
            }
        }
    }

    rpc ospfv2-terminal-debug-packet-all-on {
        if-feature feature-list:HAVE_OSPFD;
        description "OSPF packets";
        input  {
            leaf all  {
                type ipi-ospf-types:ospf_debug_packet_options_t;
                mandatory true;
                description "Use this attribute to enable OSPF packets debug.";
            }
        }
    }

    rpc ospfv2-terminal-debug-packet-all-off {
        if-feature feature-list:HAVE_OSPFD;
        description "OSPF packets";
        input  {
            leaf all  {
                type ipi-ospf-types:ospf_debug_packet_options_t;
                mandatory true;
                description "Use this attribute to enable OSPF packets debug.";
            }
        }
    }

    rpc ospfv2-terminal-debug-packet-hello-on {
        if-feature feature-list:HAVE_OSPFD;
        description "OSPF packet hello";
        input  {
            leaf hello  {
                type ipi-ospf-types:ospf_debug_packet_options_t;
                mandatory true;
                description "OSPF Hello";
            }
        }
    }

    rpc ospfv2-terminal-debug-packet-hello-off {
        if-feature feature-list:HAVE_OSPFD;
        description "OSPF packet hello";
        input  {
            leaf hello  {
                type ipi-ospf-types:ospf_debug_packet_options_t;
                mandatory true;
                description "OSPF Hello";
            }
        }
    }

    rpc ospfv2-terminal-debug-packet-dd-on {
        if-feature feature-list:HAVE_OSPFD;
        description "OSPF packet database description";
        input  {
            leaf dd  {
                type ipi-ospf-types:ospf_debug_packet_options_t;
                mandatory true;
                description "OSPF Database Description";
            }
        }
    }

    rpc ospfv2-terminal-debug-packet-dd-off {
        if-feature feature-list:HAVE_OSPFD;
        description "OSPF packet database description";
        input  {
            leaf dd  {
                type ipi-ospf-types:ospf_debug_packet_options_t;
                mandatory true;
                description "OSPF Database Description";
            }
        }
    }

    rpc ospfv2-terminal-debug-packet-ls-request-on {
        if-feature feature-list:HAVE_OSPFD;
        description "OSPF packet link state request";
        input  {
            leaf ls-request  {
                type ipi-ospf-types:ospf_debug_packet_options_t;
                mandatory true;
                description "OSPF Link State Request";
            }
        }
    }

    rpc ospfv2-terminal-debug-packet-ls-request-off {
        if-feature feature-list:HAVE_OSPFD;
        description "OSPF packet link state request";
        input  {
            leaf ls-request  {
                type ipi-ospf-types:ospf_debug_packet_options_t;
                mandatory true;
                description "OSPF Link State Request";
            }
        }
    }

    rpc ospfv2-terminal-debug-packet-ls-update-on {
        if-feature feature-list:HAVE_OSPFD;
        description "OSPF packet link state update";
        input  {
            leaf ls-update  {
                type ipi-ospf-types:ospf_debug_packet_options_t;
                mandatory true;
                description "OSPF Link State Update";
            }
        }
    }

    rpc ospfv2-terminal-debug-packet-ls-update-off {
        if-feature feature-list:HAVE_OSPFD;
        description "OSPF packet link state update";
        input  {
            leaf ls-update  {
                type ipi-ospf-types:ospf_debug_packet_options_t;
                mandatory true;
                description "OSPF Link State Update";
            }
        }
    }

    rpc ospfv2-terminal-debug-packet-ls-ack-on {
        if-feature feature-list:HAVE_OSPFD;
        description "OSPF packet link state acknowledgment";
        input  {
            leaf ls-ack  {
                type ipi-ospf-types:ospf_debug_packet_options_t;
                mandatory true;
                description "OSPF Link State Acknowledgment";
            }
        }
    }

    rpc ospfv2-terminal-debug-packet-ls-ack-off {
        if-feature feature-list:HAVE_OSPFD;
        description "OSPF packet link state acknowledgment";
        input  {
            leaf ls-ack  {
                type ipi-ospf-types:ospf_debug_packet_options_t;
                mandatory true;
                description "OSPF Link State Acknowledgment";
            }
        }
    }

    rpc ospfv2-terminal-debug-nsm-on {
        if-feature feature-list:HAVE_OSPFD;
        description "OSPF NSM information";
        input  {
            leaf nsm  {
                type ipi-ospf-types:ospf_debug_nsm_t;
                mandatory true;
                description "Use this attribute to enable OSPF NSM information debug.";
            }
        }
    }

    rpc ospfv2-terminal-debug-nsm-off {
        if-feature feature-list:HAVE_OSPFD;
        description "OSPF NSM information";
        input  {
            leaf nsm  {
                type ipi-ospf-types:ospf_debug_nsm_t;
                mandatory true;
                description "Use this attribute to enable OSPF NSM information debug.";
            }
        }
    }

    rpc ospfv2-terminal-debug-nfsm-on {
        if-feature feature-list:HAVE_OSPFD;
        description "OSPF Neighbor State Machine";
        input  {
            leaf nfsm  {
                type ipi-ospf-types:ospf_debug_nfsm_t;
                mandatory true;
                description "Use this attribute to enable OSPF Neighbor State Machine debug.";
            }
        }
    }

    rpc ospfv2-terminal-debug-nfsm-off {
        if-feature feature-list:HAVE_OSPFD;
        description "OSPF Neighbor State Machine";
        input  {
            leaf nfsm  {
                type ipi-ospf-types:ospf_debug_nfsm_t;
                mandatory true;
                description "Use this attribute to enable OSPF Neighbor State Machine debug.";
            }
        }
    }

    rpc ospfv2-terminal-debug-lsa-on {
        if-feature feature-list:HAVE_OSPFD;
        description "OSPF Link State Advertisement";
        input  {
            leaf lsa  {
                type ipi-ospf-types:ospf_debug_lsa_t;
                mandatory true;
                description "Use this attribute to enable OSPF Link State Advertisement debug.";
            }
        }
    }

    rpc ospfv2-terminal-debug-lsa-off {
        if-feature feature-list:HAVE_OSPFD;
        description "OSPF Link State Advertisement";
        input  {
            leaf lsa  {
                type ipi-ospf-types:ospf_debug_lsa_t;
                mandatory true;
                description "Use this attribute to enable OSPF Link State Advertisement debug.";
            }
        }
    }

    rpc ospfv2-terminal-debug-ifsm-on {
        if-feature feature-list:HAVE_OSPFD;
        description "OSPF Interface State Machine";
        input  {
            leaf ifsm  {
                type ipi-ospf-types:ospf_debug_ifsm_t;
                mandatory true;
                description "Use this attribute to enable OSPF Interface State Machine debug.";
            }
        }
    }

    rpc ospfv2-terminal-debug-ifsm-off {
        if-feature feature-list:HAVE_OSPFD;
        description "OSPF Interface State Machine";
        input  {
            leaf ifsm  {
                type ipi-ospf-types:ospf_debug_ifsm_t;
                mandatory true;
                description "Use this attribute to enable OSPF Interface State Machine debug.";
            }
        }
    }

    rpc ospfv2-terminal-debug-events-on {
        if-feature feature-list:HAVE_OSPFD;
        description "OSPF events information";
        input  {
            leaf events  {
                type ipi-ospf-types:ospf_debug_event_t;
                mandatory true;
                description "Use this attribute to enable OSPF events information debug.";
            }
        }
    }

    rpc ospfv2-terminal-debug-events-off {
        if-feature feature-list:HAVE_OSPFD;
        description "OSPF events information";
        input  {
            leaf events  {
                type ipi-ospf-types:ospf_debug_event_t;
                mandatory true;
                description "Use this attribute to enable OSPF events information debug.";
            }
        }
    }

    rpc ospfv2-terminal-debug-cspf-all-on {
        if-feature feature-list:HAVE_OSPF_CSPF;
        if-feature feature-list:HAVE_OSPFD;
        description "CSPF Information";
    }

    rpc ospfv2-terminal-debug-cspf-all-off {
        if-feature feature-list:HAVE_OSPF_CSPF;
        if-feature feature-list:HAVE_OSPFD;
        description "CSPF Information";
    }

    rpc ospfv2-terminal-debug-cspf-events-on {
        if-feature feature-list:HAVE_OSPF_CSPF;
        if-feature feature-list:HAVE_OSPFD;
        description "CSPF Information";
    }

    rpc ospfv2-terminal-debug-cspf-events-off {
        if-feature feature-list:HAVE_OSPF_CSPF;
        if-feature feature-list:HAVE_OSPFD;
        description "CSPF Information";
    }

    rpc ospfv2-terminal-debug-cspf-hexdump-on {
        if-feature feature-list:HAVE_OSPF_CSPF;
        if-feature feature-list:HAVE_OSPFD;
        description "CSPF message hexdump";
    }

    rpc ospfv2-terminal-debug-cspf-hexdump-off {
        if-feature feature-list:HAVE_OSPF_CSPF;
        if-feature feature-list:HAVE_OSPFD;
        description "CSPF message hexdump";
    }

    rpc ospfv2-terminal-debug-all-on {
        if-feature feature-list:HAVE_OSPFD;
        description "Turn on all OSPF debug information";
    }

    rpc ospfv2-terminal-debug-all-off {
        if-feature feature-list:HAVE_OSPFD;
        description "Turn off all OSPF debug information";
    }

    rpc ospfv2-terminal-debug-retransmission-on {
        if-feature feature-list:HAVE_OSPFD;
        description "OSPF Debug retransmission information";
    }

    rpc ospfv2-terminal-debug-retransmission-off {
        if-feature feature-list:HAVE_OSPFD;
        description "OSPF Debug retransmission information";
    }

    rpc ospfv2-terminal-debug-dist-ls-on {
        if-feature feature-list:HAVE_BGP_LS;
        if-feature feature-list:HAVE_OSPFD;
        description "OSPF distribute linkstate details";
    }

    rpc ospfv2-terminal-debug-dist-ls-off {
        if-feature feature-list:HAVE_BGP_LS;
        if-feature feature-list:HAVE_OSPFD;
        description "OSPF distribute linkstate details";
    }

    rpc ospfv2-terminal-debug-topology-independent-lfa-on {
        if-feature feature-list:HAVE_OSPF_TI_LFA;
        if-feature feature-list:HAVE_OSPFD;
        description "Topology Independent LFA";
    }

    rpc ospfv2-terminal-debug-topology-independent-lfa-off {
        if-feature feature-list:HAVE_OSPF_TI_LFA;
        if-feature feature-list:HAVE_OSPFD;
        description "Topology Independent LFA";
    }

    rpc ospfv2-terminal-debug-lfa-on {
        if-feature feature-list:HAVE_OSPF_LFA;
        if-feature feature-list:HAVE_OSPFD;
        description "OSPF lfa route install details";
    }

    rpc ospfv2-terminal-debug-lfa-off {
        if-feature feature-list:HAVE_OSPF_LFA;
        if-feature feature-list:HAVE_OSPFD;
        description "OSPF lfa route install details";
    }

    rpc ospfv2-terminal-debug-policy-on {
        if-feature feature-list:HAVE_OSPFD;
        description "OSPF policy information";
    }

    rpc ospfv2-terminal-debug-policy-off {
        if-feature feature-list:HAVE_OSPFD;
        description "OSPF policy information";
    }

    rpc ospfv2-terminal-debug-redistribute-on {
        if-feature feature-list:HAVE_OSPFD;
        description "OSPF redistribute information";
        input  {
            leaf redistribute  {
                type ipi-ospf-types:ospf_debug_redist_t;
                mandatory true;
                description "Use this attribute to enable OSPF redistribute information debug.";
            }
        }
    }

    rpc ospfv2-terminal-debug-redistribute-off {
        if-feature feature-list:HAVE_OSPFD;
        description "OSPF redistribute information";
        input  {
            leaf redistribute  {
                type ipi-ospf-types:ospf_debug_redist_t;
                mandatory true;
                description "Use this attribute to enable OSPF redistribute information debug.";
            }
        }
    }

    rpc ospfv2-terminal-debug-graceful-restart-on {
        if-feature feature-list:HAVE_OSPFD;
        description "OSPF graceful-restart";
        input  {
            leaf graceful-restart  {
                type ipi-ospf-types:ospf_debug_graceful_t;
                mandatory true;
                description "Use this attribute to enable OSPF graceful-restart debug.";
            }
        }
    }

    rpc ospfv2-terminal-debug-graceful-restart-off {
        if-feature feature-list:HAVE_OSPFD;
        description "OSPF graceful-restart";
        input  {
            leaf graceful-restart  {
                type ipi-ospf-types:ospf_debug_graceful_t;
                mandatory true;
                description "Use this attribute to enable OSPF graceful-restart debug.";
            }
        }
    }

    rpc ospfv2-clear-process {
        if-feature feature-list:HAVE_OSPFD;
        description "Clear and restart OSPFv2 process";
        input  {
            leaf process-id  {
                type uint16 {
                    range "0..65535";
                }
                mandatory true;
                description "Use this attribute to specify OSPFv2 processes to clear.";
            }
        }
    }

    rpc ospfv2-clear-process-all {
        if-feature feature-list:HAVE_OSPFD;
        description "Clear and restart all OSPFv2 processes";
    }

    rpc ospfv2-restart-graceful {
        if-feature feature-list:HAVE_RESTART;
        if-feature feature-list:HAVE_OSPFD;
        description "Restart gracefully restart OSPFv2. After this command is executed, the
                    router immediately shuts down. NSM is notified that OSPF has shut down
                    gracefully. NSM preserves routes installed by OSPF until the grace
                    period expires.";
        input  {
            leaf grace-period  {
                type uint16 {
                    range "2..1800";
                }
                mandatory true;
                description "Use this attribute to set the grace period for restarting the router.";
            }
        }
    }

    rpc ospfv2-snmp-restart {
        if-feature feature-list:HAVE_SNMP;
        if-feature feature-list:HAVE_OSPFD;
        description "Restart SNMP in OSPFv2";
    }

    notification ospfv2-neighbor-state-change {
        if-feature feature-list:HAVE_OSPFD;

        description "Notification for OSPFv2 interface link state change.";

        leaf severity {
            type cml-data-types:cml_notif_severity_t;
            description "Notification severity level (value: CRITICAL)";
        }

        leaf eventClass {
            type cml-data-types:cml_notif_class_t;
            description "Notification event class (value: STATE)";
        }

        leaf address {
            type  inet:ipv4-address;
        description
            "Use this attribute to set the interface IP address of the neighbor.";
        }

        leaf ospf-id {
            type  uint16;
        description
            "Use this attribute to set the OSPF process ID.";
        }

        leaf router-id {
            type  inet:ipv4-address;
        description
            "Router ID for the OSPF process.";
        }

        leaf neighbor-address-less-index {
            type  uint32;
        description
            "Neighbor address less index.";
        }

        leaf neighbor-router-id {
            type  inet:ipv4-address;
        description
            "Neighbor router ID.";
        }

        leaf neighbor-state {
            type ipi-ospf-types:ospf_neighbor_state_change_t;
        description
            "Neighbor state.";
        }
    }

    notification ospfv2-tx-retransmit {
        if-feature feature-list:HAVE_OSPFD;

        description "Notification for OSPFv2 re-transmission.";

        leaf severity {
            type cml-data-types:cml_notif_severity_t;
            description "Notification severity level (value: INFO)";
        }

        leaf eventClass {
            type cml-data-types:cml_notif_class_t;
            description "Notification event class (value: STATE)";
        }

        leaf address {
            type  inet:ipv4-address;
        description
            "Use this attribute to set the interface IP address of the neighbor.";
        }

        leaf ospf-id {
            type  uint16;
        description
            "Use this attribute to set the OSPF process ID.";
        }

        leaf router-id {
            type  inet:ipv4-address;
        description
            "Router ID for the OSPF process.";
        }

        leaf neighbor-address-less-index {
            type  uint32;
        description
            "Neighbor address less index.";
        }

        leaf neighbor-router-id {
            type  inet:ipv4-address;
        description
            "Neighbor router ID.";
        }

        leaf packet-type {
            type ipi-ospf-types:ospf_packet_type_t;
        description
            "OSPF patcket type.";
        }

        leaf lsdb-type {
            type ipi-ospf-types:ospf_lsdb_type_t;
        description
            "LSDB Type.";
        }

        leaf lsdb-lsid {
            type  inet:ipv4-address;
        description
            "The Link State ID.";
        }

        leaf lsdb-router-id {
            type  inet:ipv4-address;
        description
            "LSDB router ID.";
        }
    }

    notification ospfv2-originate-lsa {
        if-feature feature-list:HAVE_OSPFD;

        description "Notification for OSPFv2 originate LSA.";

        leaf severity {
            type cml-data-types:cml_notif_severity_t;
            description "Notification severity level (value: INFO)";
        }

        leaf eventClass {
            type cml-data-types:cml_notif_class_t;
            description "Notification event class (value: STATE)";
        }

        leaf ospf-id {
            type  uint16;
        description
            "Use this attribute to set the OSPF process ID.";
        }

        leaf router-id {
            type  inet:ipv4-address;
        description
            "The originator Router ID.";
        }

        leaf lsdb-area-id {
            type  inet:ipv4-address;
        description
            "LSDB area ID.";
        }

        leaf lsdb-type {
            type ipi-ospf-types:ospf_lsdb_type_t;
        description
            "LSDB Type.";
        }

        leaf lsdb-id {
            type  inet:ipv4-address;
        description
            "LSDB ID.";
        }

        leaf lsdb-router-id {
            type  inet:ipv4-address;
        description
            "LSDB router ID.";
        }
    }

    notification ospfv2-lsdb-overflow-external-lsa {
        if-feature feature-list:HAVE_OSPFD;

        description "Notification for OSPFv2 LSDB overflow external LSA.";

        leaf severity {
            type cml-data-types:cml_notif_severity_t;
            description "Notification severity level (value: INFO)";
        }

        leaf eventClass {
            type cml-data-types:cml_notif_class_t;
            description "Notification event class (value: STATE)";
        }

        leaf ospf-id {
            type  uint16;
        description
            "Use this attribute to set the OSPF process ID.";
        }

        leaf router-id {
            type  inet:ipv4-address;
        description
            "Router ID for the OSPF process.";
        }

        leaf max-limit {
            type  uint32;
        description
            "Maximum limit maximum number of normal LSAs.";
        }
    }

    notification ospfv2-virtual-link-interface-config-error {
        if-feature feature-list:HAVE_OSPFD;

        description "Notification for OSPFv2 virtual link interface configuration error.";

        leaf severity {
            type cml-data-types:cml_notif_severity_t;
            description "Notification severity level (value: WARNING)";
        }

        leaf eventClass {
            type cml-data-types:cml_notif_class_t;
            description "Notification event class (value: STATE)";
        }

        leaf remote-router-id {
            type  inet:ipv4-address;
        description
            "Use this attribute to set the interface IP address of the neighbor.";
        }

        leaf area-id {
            type ipi-ospf-types:ospf_area_t;
        description
            "Use this attribute to set the OSPF area ID.";
        }

        leaf ospf-id {
            type  uint16;
        description
            "Use this attribute to set the OSPF process ID.";
        }

        leaf router-id {
            type  inet:ipv4-address;
        description
            "The originator Router ID.";
        }

        leaf error-type {
            type ipi-ospf-types:ospf_config_error_type_t;
        description
            "Error type.";
        }

        leaf packet-type {
            type ipi-ospf-types:ospf_packet_type_t;
        description
            "OSPF packet type.";
        }
    }

    notification ospfv2-virtual-link-interface-state-change {
        if-feature feature-list:HAVE_OSPFD;

        description "Notification for OSPFv2 virtual link interface state change.";

        leaf severity {
            type cml-data-types:cml_notif_severity_t;
            description "Notification severity level (value: CRITICAL)";
        }

        leaf eventClass {
            type cml-data-types:cml_notif_class_t;
            description "Notification event class (value: STATE)";
        }

        leaf remote-router-id {
            type  inet:ipv4-address;
        description
            "Use this attribute to set the interface IP address of the neighbor.";
        }

        leaf area-id {
            type ipi-ospf-types:ospf_area_t;
        description
            "Use this attribute to set the OSPF area ID.";
        }

        leaf ospf-id {
            type  uint16;
        description
            "Use this attribute to set the OSPF process ID.";
        }

        leaf router-id {
            type  inet:ipv4-address;
        description
            "The originator Router ID.";
        }

        leaf interface-state {
            type ipi-ospf-types:ospf_interface_state_t;
        description
            "Interface status.";
        }
    }

    notification ospfv2-virtual-neighbor-state-change {
        if-feature feature-list:HAVE_OSPFD;

        description "Notification for OSPFv2 virtual neighbor state change.";

        leaf severity {
            type cml-data-types:cml_notif_severity_t;
            description "Notification severity level (value: CRITICAL)";
        }

        leaf eventClass {
            type cml-data-types:cml_notif_class_t;
            description "Notification event class (value: STATE)";
        }

        leaf remote-router-id {
            type  inet:ipv4-address;
        description
            "Use this attribute to set the interface IP address of the neighbor.";
        }

        leaf area-id {
            type ipi-ospf-types:ospf_area_t;
        description
            "Use this attribute to set the OSPF area ID.";
        }

        leaf ospf-id {
            type  uint16;
        description
            "Use this attribute to set the OSPF process ID.";
        }

        leaf router-id {
            type  inet:ipv4-address;
        description
            "The originator Router ID.";
        }

        leaf neighbor-state {
            type ipi-ospf-types:ospf_neighbor_state_change_t;
        description
            "Neighbor state.";
        }
    }

    notification ospfv2-virtual-link-interface-rx-bad-packet {
        if-feature feature-list:HAVE_OSPFD;

        description "Notification for OSPFv2 interface bad backet reception.";

        leaf severity {
            type cml-data-types:cml_notif_severity_t;
            description "Notification severity level (value: WARNING)";
        }

        leaf eventClass {
            type cml-data-types:cml_notif_class_t;
            description "Notification event class (value: STATE)";
        }

        leaf remote-router-id {
            type  inet:ipv4-address;
        description
            "Use this attribute to set the interface IP address of the neighbor.";
        }

        leaf area-id {
            type ipi-ospf-types:ospf_area_t;
        description
            "Use this attribute to set the OSPF area ID.";
        }

        leaf ospf-id {
            type  uint16;
        description
            "Use this attribute to set the OSPF process ID.";
        }

        leaf router-id {
            type  inet:ipv4-address;
        description
            "Router ID for the OSPF process.";
        }

        leaf packet-type {
            type ipi-ospf-types:ospf_packet_type_t;
        description
            "OSPF packet type.";
        }
    }

    notification ospfv2-virtual-link-interface-tx-retransmit {
        if-feature feature-list:HAVE_OSPFD;

        description "Notification for OSPFv2 Virtual Interface re-transmission.";

        leaf severity {
            type cml-data-types:cml_notif_severity_t;
            description "Notification severity level (value: INFO)";
        }

        leaf eventClass {
            type cml-data-types:cml_notif_class_t;
            description "Notification event class (value: STATE)";
        }

        leaf remote-router-id {
            type  inet:ipv4-address;
        description
            "Use this attribute to set the interface IP address of the neighbor.";
        }

        leaf area-id {
            type ipi-ospf-types:ospf_area_t;
        description
            "Use this attribute to set the OSPF area ID.";
        }

        leaf ospf-id {
            type  uint16;
        description
            "Use this attribute to set the OSPF process ID.";
        }

        leaf router-id {
            type  inet:ipv4-address;
        description
            "Use this attribute to set a router ID for the OSPF process. Configure
                    each router OSPF with an unique router ID.";
        }

        leaf packet-type {
            type ipi-ospf-types:ospf_packet_type_t;
        description
            "OSPF patcket type.";
        }

        leaf lsdb-type {
            type ipi-ospf-types:ospf_lsdb_type_t;
        description
            "LSDB Type.";
        }

        leaf lsdb-lsid {
            type  inet:ipv4-address;
        description
            "The Link State ID.";
        }

        leaf lsdb-router-id {
            type  inet:ipv4-address;
        description
            "LSDB router ID.";
        }
    }

    notification ospfv2-interface-link-state-change {
        if-feature feature-list:HAVE_OSPFD;

        description "Notification for OSPFv2 interface link state change.";

        leaf severity {
            type cml-data-types:cml_notif_severity_t;
            description "Notification severity level (value: CRITICAL)";
        }

        leaf eventClass {
            type cml-data-types:cml_notif_class_t;
            description "Notification event class (value: STATE)";
        }

        leaf name {
            type  string;
        description
            "The interface name to configure the OSPF parameters.";
        }

        leaf router-id {
            type  inet:ipv4-address;
        description
            "OSPF router ID.";
        }

        leaf interface-address {
            type  inet:ipv4-address;
        description
            "Interface address.";
        }

        leaf address-less-interface {
            type  uint32;
        description
            "Address less interface.";
        }

        leaf interface-state {
            type ipi-ospf-types:ospf_interface_state_t;
        description
            "Interface status.";
        }
    }

    notification ospfv2-interface-rx-bad-packet {
        if-feature feature-list:HAVE_OSPFD;

        description "Notification for OSPFv2 interface bad backet reception.";

        leaf severity {
            type cml-data-types:cml_notif_severity_t;
            description "Notification severity level (value: WARNING)";
        }

        leaf eventClass {
            type cml-data-types:cml_notif_class_t;
            description "Notification event class (value: STATE)";
        }

        leaf name {
            type  string;
        description
            "The interface name to configure the OSPF parameters.";
        }

        leaf router-id {
            type  inet:ipv4-address;
        description
            "OSPF router ID.";
        }

        leaf interface-address {
            type  inet:ipv4-address;
        description
            "Interface address.";
        }

        leaf address-less-interface {
            type  uint32;
        description
            "Address less interface.";
        }

        leaf packet-src {
            type  inet:ipv4-address;
        description
            "Source address.";
        }

        leaf packet-type {
            type ipi-ospf-types:ospf_packet_type_t;
        description
            "Packet type.";
        }
    }

    notification ospfv2-interface-config-error {
        if-feature feature-list:HAVE_OSPFD;

        description "Notification for OSPFv2 interface configuration error.";

        leaf severity {
            type cml-data-types:cml_notif_severity_t;
            description "Notification severity level (value: WARNING)";
        }

        leaf eventClass {
            type cml-data-types:cml_notif_class_t;
            description "Notification event class (value: STATE)";
        }

        leaf name {
            type  string;
        description
            "The interface name to configure the OSPF parameters.";
        }

        leaf router-id {
            type  inet:ipv4-address;
        description
            "OSPF router ID.";
        }

        leaf interface-address {
            type  inet:ipv4-address;
        description
            "Interface address.";
        }

        leaf address-less-interface {
            type  uint32;
        description
            "Address less interface.";
        }

        leaf error-type {
            type ipi-ospf-types:ospf_config_error_type_t;
        description
            "Error type.";
        }

        leaf packet-type {
            type ipi-ospf-types:ospf_packet_type_t;
        description
            "Packet type.";
        }
    }

}
