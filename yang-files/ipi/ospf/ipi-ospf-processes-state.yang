/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospf-processes-state.yang
*
*/

submodule ipi-ospf-processes-state {

    yang-version 1.1;

    belongs-to  ipi-ospf { prefix ipi-ospf; }

    import feature-list {
        prefix feature-list;
        revision-date 2026-09-15;
    }

    import ietf-yang-types {
        prefix yang;
        revision-date 2013-07-15;
    }

    import ietf-inet-types {
        prefix inet;
        revision-date 2013-07-15;
    }

    import cml-data-types {
        prefix cml-data-types;
        revision-date 2026-05-15;
    }

    import ipi-ospf-types {
        prefix ipi-ospf-types;
        revision-date 2024-09-05;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF process state";


    revision "2024-09-18" {
        description "ECMP change for tilfa-repair-path and tilfa-backup-path output";
        reference " 0.7.0.";
    }

    revision "2023-02-02" {
        description "Updated missing Description";
        reference " 0.6.0.";
    }

    revision "2022-07-31" {
        description "Stop using inet:ipv4-prefix and inet:ipv6-prefix due to Cisco NSO iterop";
        reference " 0.5.0.";
    }

    revision "2022-06-01" {
        description "Updated the yang file with feature";
        reference " 0.4.0.";
    }

    revision "2021-09-03" {
        description "Update descriptions of attribute";
        reference "Initial Version";
    }

    revision "2021-08-18" {
        description "State attributes for Segment Routing, TI LFA and TE";
        reference "Initial Version";
    }

    revision "2021-04-06" {
        description "Restructured module in accordance with OpenConfig style";
        reference "Initial Version";
    }

    grouping ospfv2-processes-state {
        description
            "Grouping for OSPF processes state";
        leaf dste-status  {
            type  ipi-ospf-types:ospf_dste_status;
            description "This attribute provides dste-status value.";
        } // END of dste-status definition.

    } // END of ospfv2-processes-state definition.
    grouping ospfv2-statistics {
        description
            "Grouping for OSPF processes state statistics";
        leaf up-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "This attribute provides processes uptime.";
        } // END of up-time definition.

    } // END of ospfv2-statistics definition.
    grouping ospfv2-router-state {
        description
            "Grouping for OSPF router state statistics";
        leaf area-counter  {
            type  yang:counter64;
            description "This attribute provides area-counter.";
        } // END of area-counter definition.

    } // END of ospfv2-router-state definition.
    grouping ospfv2-db-desc-exchanges {
        description
            "Grouping for OSPF db-desc-exchanges statistics";
        leaf in  {
            type  yang:counter64;
            description "This attribute provides database description exchanges in.";
        } // END of in definition.

        leaf out  {
            type  yang:counter64;
            description "This attribute provides database description exchanges out.";
        } // END of out definition.

    } // END of ospfv2-db-desc-exchanges definition.
    grouping ospfv2-statistics-lsa {
        description
            "Grouping for OSPF statistics-lsa statistics";
        leaf originate  {
            type  yang:counter64;
            description "This attribute provides originate attribute link state advertisement.";
        } // END of originate definition.

        leaf received  {
            type  yang:counter64;
            description "This attribute provides received attribute link state advertisement.";
        } // END of received definition.

        leaf external  {
            type  yang:counter64;
            description "This attribute provides external attribute link state advertisement.";
        } // END of external definition.

        leaf opaque  {
            type  yang:counter64;
            description "This attribute provides opaque attribute link state advertisement.";
        } // END of opaque definition.

        leaf non-default-external  {
            type  yang:counter64;
            description "This attribute provides non-default-external attribute link state
                        advertisement.";
        } // END of non-default-external definition.

    } // END of ospfv2-statistics-lsa definition.
    grouping ospfv2-router-event {
        description
            "Grouping for OSPF router event statistics";
        leaf router-id-changes  {
            type  yang:counter64;
            description "This attribute provides router-id-changes router event status.";
        } // END of router-id-changes definition.

        leaf designated-router-election  {
            type  yang:counter64;
            description "This attribute provides designated-router-election router event
                        status.";
        } // END of designated-router-election definition.

    } // END of ospfv2-router-event definition.
    grouping ospfv2-router-event-packets {
        description
            "Grouping for OSPF router event packets statistics";
        leaf packets-send-buffer  {
            type  yang:counter64;
            description "This attribute provides packets-send-buffer for router event status.";
        } // END of packets-send-buffer definition.

        leaf unused-packets  {
            type  yang:counter64;
            description "This attribute provides unused-packets for router event status.";
        } // END of unused-packets definition.

        leaf max-unused-packets  {
            type  yang:counter64;
            description "This attribute provides max-unused-packets for router event status.";
        } // END of max-unused-packets definition.

    } // END of ospfv2-router-event-packets definition.
    grouping ospfv2-router-event-lsa {
        description
            "Grouping for OSPF router event lsa statistics";
        leaf older-lsa-received  {
            type  yang:counter64;
            description "This attribute provides older-lsa-received for router event status.";
        } // END of older-lsa-received definition.

        leaf lsa-buffer  {
            type  uint32;
            description "This attribute provides lsa-buffer for router event status.";
        } // END of lsa-buffer definition.

    } // END of ospfv2-router-event-lsa definition.
    grouping ospfv2-router-event-spf {
        description
            "Grouping for OSPF router event spf statistics";
        leaf full  {
            type  yang:counter64;
            description "This attribute provides SPF full for router event status.";
        } // END of full definition.

        leaf summary  {
            type  yang:counter64;
            description "This attribute provides SPF summary for router event status.";
        } // END of summary definition.

        leaf external  {
            type  yang:counter64;
            description "This attribute provides SPF external for router event status.";
        } // END of external definition.

    } // END of ospfv2-router-event-spf definition.
    grouping ospfv2-router-event-neighbor {
        description
            "Grouping for OSPF router event neighbor statistics";
        leaf state-change  {
            type  yang:counter64;
            description "This attribute provides neighbor state-change for router event status.";
        } // END of state-change definition.

        leaf dead-interval-expiration  {
            type  yang:counter64;
            description "This attribute provides neighbor dead-interval-expiration for router
                        event status.";
        } // END of dead-interval-expiration definition.

        leaf bad-link-state-request  {
            type  yang:counter64;
            description "This attribute provides neighbor bad-link-state-request for router
                        event status.";
        } // END of bad-link-state-request definition.

        leaf sequence-number-mismatch  {
            type  yang:counter64;
            description "This attribute provides neighbor sequence-number-mismatch for router
                        event status.";
        } // END of sequence-number-mismatch definition.

    } // END of ospfv2-router-event-neighbor definition.
    grouping ospfv2-statistics-error {
        description
            "Grouping for OSPF error statistics";
        leaf discarded-in  {
            type  yang:counter64;
            description "This attribute provides discarded-in for errors status.";
        } // END of discarded-in definition.

        leaf discarded-out  {
            type  yang:counter64;
            description "This attribute provides discarded-out for errors status.";
        } // END of discarded-out definition.

        leaf hello-in  {
            type  yang:counter64;
            description "This attribute provides hello-in for errors status.";
        } // END of hello-in definition.

        leaf database-descriptor-in  {
            type  yang:counter64;
            description "This attribute provides database-descriptor-in for errors status.";
        } // END of database-descriptor-in definition.

        leaf ls-request-in  {
            type  yang:counter64;
            description "This attribute provides ls-request-in for errors status.";
        } // END of ls-request-in definition.

        leaf ls-update-in  {
            type  yang:counter64;
            description "This attribute provides ls-update-in for errors status.";
        } // END of ls-update-in definition.

        leaf ls-acknowledge-in  {
            type  yang:counter64;
            description "This attribute provides ls-acknowledge-in for errors status.";
        } // END of ls-acknowledge-in definition.

        leaf unknown-in  {
            type  yang:counter64;
            description "This attribute provides unknown-in for errors status.";
        } // END of unknown-in definition.

        leaf unknown-out  {
            type  yang:counter64;
            description "This attribute provides unknown-outfor errors status.";
        } // END of unknown-out definition.

        leaf bad-version  {
            type  yang:counter64;
            description "This attribute provides bad-version for errors status.";
        } // END of bad-version definition.

        leaf bad-crc  {
            type  yang:counter64;
            description "This attribute provides bad-crc for errors status.";
        } // END of bad-crc definition.

        leaf invalid-source  {
            type  yang:counter64;
            description "This attribute provides invalid-source for errors status.";
        } // END of invalid-source definition.

        leaf invalid-destination  {
            type  yang:counter64;
            description "This attribute provides invalid-destination for errors status.";
        } // END of invalid-destination definition.

        leaf no-neighbor  {
            type  yang:counter64;
            description "This attribute provides no-neighbor for errors status.";
        } // END of no-neighbor definition.

        leaf passive  {
            type  yang:counter64;
            description "This attribute provides passive for errors status.";
        } // END of passive definition.

        leaf wrong-area  {
            type  yang:counter64;
            description "This attribute provides wrong-area for errors status.";
        } // END of wrong-area definition.

        leaf packets-length  {
            type  yang:counter64;
            description "This attribute provides packets-length for errors status.";
        } // END of packets-length definition.

        leaf bad-authentication  {
            type  yang:counter64;
            description "This attribute provides bad-authentication for errors status.";
        } // END of bad-authentication definition.

    } // END of ospfv2-statistics-error definition.
    grouping ospfv2-statistics-traffic {
        description
            "Grouping for OSPF traffic statistics";
        leaf total-packets-in  {
            type  yang:counter64;
            description "This attribute provides total-packets-in for traffic status.";
        } // END of total-packets-in definition.

        leaf total-packets-out  {
            type  yang:counter64;
            description "This attribute provides total-packets-out for traffic status.";
        } // END of total-packets-out definition.

        leaf hello-packets-in  {
            type  yang:counter64;
            description "This attribute provides hello-packets-in for traffic status.";
        } // END of hello-packets-in definition.

        leaf hello-packets-out  {
            type  yang:counter64;
            description "This attribute provides hello-packets-out for traffic status.";
        } // END of hello-packets-out definition.

        leaf database-descriptor-packets-in  {
            type  yang:counter64;
            description "This attribute provides database-descriptor-packets-in for traffic
                        status.";
        } // END of database-descriptor-packets-in definition.

        leaf database-descriptor-packets-out  {
            type  yang:counter64;
            description "This attribute provides database-descriptor-packets-out for traffic
                        status.";
        } // END of database-descriptor-packets-out definition.

        leaf ls-request-packets-in  {
            type  yang:counter64;
            description "This attribute provides ls-request-packets-in for traffic status.";
        } // END of ls-request-packets-in definition.

        leaf ls-request-packets-out  {
            type  yang:counter64;
            description "This attribute provides ls-request-packets-out for traffic status.";
        } // END of ls-request-packets-out definition.

        leaf ls-update-packets-in  {
            type  yang:counter64;
            description "This attribute provides ls-update-packets-in for traffic status.";
        } // END of ls-update-packets-in definition.

        leaf ls-update-packets-out  {
            type  yang:counter64;
            description "This attribute provides ls-update-packets-out for traffic status.";
        } // END of ls-update-packets-out definition.

        leaf ls-acknowledge-packets-in  {
            type  yang:counter64;
            description "This attribute provides ls-acknowledge-packets-in for traffic status.";
        } // END of ls-acknowledge-packets-in definition.

        leaf ls-acknowledge-packets-out  {
            type  yang:counter64;
            description "This attribute provides ls-acknowledge-packets-out for traffic status.";
        } // END of ls-acknowledge-packets-out definition.

    } // END of ospfv2-statistics-traffic definition.
    grouping ospfv2-link-state-database {
        description
            "Grouping for OSPF link state database statistics";
        container link-state-database {
            config false;
            description
                "OSPFv2 link state database statistics";
            container state {
                config false;
                description
                    "Operational state data for OSPF process";
                leaf external-checksum  {
                    type  yang:phys-address {
                        pattern "([0-9a-fA-F]{2}(:[0-9a-fA-F]{2})*)?";
                        }
                        description "Number of AS external LSAs and checksum.";
                    } // END of external-checksum definition.

                    leaf opaque-checksum  {
                        type  yang:phys-address {
                            pattern "([0-9a-fA-F]{2}(:[0-9a-fA-F]{2})*)?";
                            }
                            description "Number of AS opaque LSAs and checksum.";
                        } // END of opaque-checksum definition.

            } // END of state-container definition.
        } // END of link-state-database-container definition.
    } // END of ospfv2-link-state-database definition.
    grouping ospfv2-topology-independent-lfa-nodes-state {
        description
            "Grouping for OSPF topology independent LFA nodes state attributes";
        leaf pq-node  {
            type  inet:ipv4-address;
            description "This attribute returns the pq-node value.";
        } // END of pq-node definition.

        leaf p-node-disjoint  {
            type  inet:ipv4-address;
            description "This attribute returns the disjoint p-node value.";
        } // END of p-node-disjoint definition.

        leaf q-node-disjoint  {
            type  inet:ipv4-address;
            description "This attribute returns the disjoint q-node value.";
        } // END of q-node-disjoint definition.

    } // END of ospfv2-topology-independent-lfa-nodes-state definition.
    grouping ospfv2-topology-independent-lfa-routes-state {
        description
            "Grouping for OSPF topology independent LFA route state attributes";
        leaf prefix  {
            type  cml-data-types:cml_ipv4_addr_prefix_t;
            description "This attribute returns the prefix value.";
        } // END of prefix definition.

    } // END of ospfv2-topology-independent-lfa-routes-state definition.
    grouping ospfv2-topology-independent-lfa-routes-primary-nexthop-state {
        description
            "Grouping for OSPF topology independent LFA route primary path state
                        attributes";
        leaf primary-path-nexthop  {
            type  inet:ipv4-address;
            description "This attribute returns the primary nh value.";
        } // END of primary-path-nexthop definition.

        leaf primary-interface-name  {
            type  string {
                length "1..1965";
                pattern "[^?' =,>|]+";
            }
            description "This attribute returns the primary interface name.";
        } // END of primary-interface-name definition.

    } // END of ospfv2-topology-independent-lfa-routes-primary-nexthop-state definition.
    grouping ospfv2-topology-independent-lfa-routes-primary-nexthop {
        description
            "Grouping for OSPF topology independent LFA route state attributes";
        container primary-nexthop-infos {
            config false;
            description
                "OSPFv2 topology independent LFA repair lists nexthop info";

            list primary-nexthop-info {
                key "primary-path-nexthop";
                config false;
                description
                    "List of OSPF nexthop info";
                leaf primary-path-nexthop  {
                    type  leafref {
                        path  "../state/primary-path-nexthop";
                    }
                    description "This attribute returns the primary nexthop value.";
                } // END of primary-path-nexthop definition.

                container state {
                    config false;
                    description
                        "Operational state data";
                    uses ospfv2-topology-independent-lfa-routes-primary-nexthop-state;
                    uses ospfv2-topology-independent-lfa-nodes-state;
                } // END of state-container definition.
            } // End of primary-nexthop-info-list
        } // END of primary-nexthop-infos-container definition.
    } // END of ospfv2-topology-independent-lfa-routes-primary-nexthop definition.
    grouping ospfv2-topology-independent-lfa-routes {
        description
            "Grouping for OSPF topology independent LFA routes";
        container routes {
            if-feature feature-list:HAVE_OSPF_TI_LFA;
            config false;
            description
                "OSPFv2 topology independent LFA routes info";

            list route {
                key "prefix";
                config false;
                description
                    "List of OSPF routes";
                leaf prefix  {
                    type  leafref {
                        path  "../state/prefix";
                    }
                    description "This attribute returns the prefix value.";
                } // END of prefix definition.

                container state {
                    config false;
                    description
                        "Operational state data";
                    uses ospfv2-topology-independent-lfa-routes-state;
                } // END of state-container definition.
                uses ospfv2-topology-independent-lfa-routes-primary-nexthop;
            } // End of route-list
        } // END of routes-container definition.
    } // END of ospfv2-topology-independent-lfa-routes definition.
    grouping ospfv2-topology-independent-lfa-neighbors-state {
        description
            "Grouping for OSPF topology independent LFA neighbor state attributes";
        leaf address  {
            type  inet:ipv4-address;
            description "This attribute returns the prefix value.";
        } // END of address definition.

    } // END of ospfv2-topology-independent-lfa-neighbors-state definition.
    grouping ospfv2-topology-independent-lfa-neighbors {
        description
            "Grouping for OSPF topology independent LFA neighbors";
        container neighbors {
            if-feature feature-list:HAVE_OSPF_TI_LFA;
            config false;
            description
                "OSPFv2 topology independent LFA neighbors info";

            list neighbor {
                key "address";
                config false;
                description
                    "List of OSPF neighbors";
                leaf address  {
                    type  leafref {
                        path  "../state/address";
                    }
                    description "This attribute returns the neighbor address value.";
                } // END of address definition.

                container state {
                    config false;
                    description
                        "Operational state data";
                    uses ospfv2-topology-independent-lfa-neighbors-state;
                    uses ospfv2-topology-independent-lfa-nodes-state;
                } // END of state-container definition.
            } // End of neighbor-list
        } // END of neighbors-container definition.
    } // END of ospfv2-topology-independent-lfa-neighbors definition.
    grouping ospfv2-topology-independent-lfa-vertices-nodes-state {
        description
            "Grouping for OSPF topology independent LFA vertices nodes state
                        attributes";
        leaf address  {
            type  inet:ipv4-address;
            description "This attribute returns the node address value.";
        } // END of address definition.

        leaf distance  {
            type  uint32;
            description "This attribute returns the distance value.";
        } // END of distance definition.

    } // END of ospfv2-topology-independent-lfa-vertices-nodes-state definition.
    grouping ospfv2-topology-independent-lfa-vertices-pnodes {
        description
            "Grouping for OSPF topology independent LFA vertices pnodes";
        container p-nodes {
            config false;
            description
                "OSPFv2 topology independent LFA p-nodes info";

            list p-node {
                key "address";
                config false;
                description
                    "List of OSPF p-nodes";
                leaf address  {
                    type  leafref {
                        path  "../state/address";
                    }
                    description "This attribute returns the node address value.";
                } // END of address definition.

                container state {
                    config false;
                    description
                        "Operational state data";
                    uses ospfv2-topology-independent-lfa-vertices-nodes-state;
                } // END of state-container definition.
            } // End of p-node-list
        } // END of p-nodes-container definition.
    } // END of ospfv2-topology-independent-lfa-vertices-pnodes definition.
    grouping ospfv2-topology-independent-lfa-vertices-qnodes {
        description
            "Grouping for OSPF topology independent LFA vertices qnodes";
        container q-nodes {
            config false;
            description
                "OSPFv2 topology independent LFA qnodes info";

            list q-node {
                key "address";
                config false;
                description
                    "List of OSPF q-nodes";
                leaf address  {
                    type  leafref {
                        path  "../state/address";
                    }
                    description "This attribute returns the node address value.";
                } // END of address definition.

                container state {
                    config false;
                    description
                        "Operational state data";
                    uses ospfv2-topology-independent-lfa-vertices-nodes-state;
                } // END of state-container definition.
            } // End of q-node-list
        } // END of q-nodes-container definition.
    } // END of ospfv2-topology-independent-lfa-vertices-qnodes definition.
    grouping ospfv2-topology-independent-lfa-vertices-backup-info-state {
        description
            "Grouping for OSPF topology independent LFA backup info state";
        leaf primary-interface-name  {
            type  string {
                length "1..1965";
                pattern "[^?' =,>|]+";
            }
            description "This attribute returns the primary interface name.";
        } // END of primary-interface-name definition.

        leaf backup-out-interface-name  {
            type  string {
                length "1..1965";
                pattern "[^?' =,>|]+";
            }
            description "This attribute returns the backup interface name.";
        } // END of backup-out-interface-name definition.

    } // END of ospfv2-topology-independent-lfa-vertices-backup-info-state definition.
    grouping ospfv2-topology-independent-lfa-vertices-primary-interface-state {
        description
            "Grouping for OSPF topology independent LFA backup state";
        leaf primary-interface-name  {
            type  string {
                length "1..1965";
                pattern "[^?' =,>|]+";
            }
            description "This attribute returns the primary interface name.";
        } // END of primary-interface-name definition.

    } // END of ospfv2-topology-independent-lfa-vertices-primary-interface-state definition.
    grouping ospfv2-topology-independent-lfa-backup-info {
        description
            "Grouping for OSPF topology independent LFA backup info";
        container backup-infos {
            config false;
            description
                "OSPFv2 topology independent LFA primary interface info";

            list backup-info {
                key "primary-interface-name";
                config false;
                description
                    "List of OSPF primary interface";
                leaf primary-interface-name  {
                    type  leafref {
                        path  "../state/primary-interface-name";
                    }
                    description "This attribute returns the primary interface name.";
                } // END of primary-interface-name definition.

                container state {
                    config false;
                    description
                        "Operational state data";
                    uses ospfv2-topology-independent-lfa-vertices-backup-info-state;
                    uses ospfv2-topology-independent-lfa-nodes-state;
                } // END of state-container definition.
                uses ospfv2-topology-independent-lfa-vertices-pnodes;
                uses ospfv2-topology-independent-lfa-vertices-qnodes;
            } // End of backup-info-list
        } // END of backup-infos-container definition.
    } // END of ospfv2-topology-independent-lfa-backup-info definition.
    grouping ospfv2-topology-independent-lfa-vertices-state {
        description
            "Grouping for OSPF topology independent LFA vertex state attributes";
        leaf ls-id  {
            type  inet:ipv4-address;
            description "This attribute returns the ls-id value.";
        } // END of ls-id definition.

    } // END of ospfv2-topology-independent-lfa-vertices-state definition.
    grouping ospfv2-topology-independent-lfa-vertices {
        description
            "Grouping for OSPF topology independent LFA vertices";
        container vertices {
            if-feature feature-list:HAVE_OSPF_TI_LFA;
            config false;
            description
                "OSPFv2 topology independent LFA vertices info";

            list vertex {
                key "ls-id";
                config false;
                description
                    "List of OSPF vertices";
                leaf ls-id  {
                    type  leafref {
                        path  "../state/ls-id";
                    }
                    description "This attribute returns the ls-id value.";
                } // END of ls-id definition.

                container state {
                    config false;
                    description
                        "Operational state data";
                    uses ospfv2-topology-independent-lfa-vertices-state;
                } // END of state-container definition.
                uses ospfv2-topology-independent-lfa-backup-info;
            } // End of vertex-list
        } // END of vertices-container definition.
    } // END of ospfv2-topology-independent-lfa-vertices definition.
    grouping ospfv2-topology-independent-lfa-repair-lists-primary-info-state {
        description
            "Grouping for OSPF topology independent LFA repair lists primary info
                        attributes";
        leaf metric  {
            type  uint32;
            description "This attribute returns the metric value.";
        } // END of metric definition.

        leaf route-ftn-idx  {
            type  uint32;
            description "This attribute returns the id value of FEC to Next Hop Label Forward
                        Entry.";
        } // END of route-ftn-idx definition.

        leaf route-ilm-idx  {
            type  uint32;
            description "This attribute returns the id value of Incoming Label to Next Hop
                        Label Forward Entry.";
        } // END of route-ilm-idx definition.

        leaf sr-in-label  {
            type  uint32;
            description "This attribute returns the segment routing incoming label value.";
        } // END of sr-in-label definition.

    } // END of ospfv2-topology-independent-lfa-repair-lists-primary-info-state definition.
    grouping ospfv2-topology-independent-lfa-repair-lists-primary-info {
        description
            "Grouping for OSPF topology independent for primary path info";
        container primary-info {
            config false;
            description
                "OSPFv2 topology independent LFA repair lists primary path info";
            container state {
                config false;
                description
                    "Operational state data";
                uses ospfv2-topology-independent-lfa-repair-lists-primary-info-state;
            } // END of state-container definition.
        } // END of primary-info-container definition.
    } // END of ospfv2-topology-independent-lfa-repair-lists-primary-info definition.
    grouping ospfv2-topology-independent-lfa-repair-lists-state {
        description
            "Grouping for OSPF topology independent LFA repair lists attributes";
        leaf prefix  {
            type  cml-data-types:cml_ipv4_addr_prefix_t;
            description "This attribute returns the prefix value.";
        } // END of prefix definition.

    } // END of ospfv2-topology-independent-lfa-repair-lists-state definition.
    grouping ospfv2-topology-independent-lfa-repair-lists-nexthop-info-state {
        description
            "Grouping for OSPF topology independent LFA repair lists nexthop info
                        attributes";
        leaf primary-path-nexthop  {
            type  inet:ipv4-address;
            description "This attribute returns the next-hop address value.";
        } // END of primary-path-nexthop definition.

        leaf primary-path-interface  {
            type  string {
                length "1..1965";
                pattern "[^?' =,>|]+";
            }
            description "This attribute returns the primary interface name.";
        } // END of primary-path-interface definition.

        leaf segment-routing-outgoing-label  {
            type  uint32;
            description "This attribute returns the segment routing outgoing label value.";
        } // END of segment-routing-outgoing-label definition.

        leaf backup-outgoing-label  {
            type  uint32;
            description "This attribute returns the backup value for outgoing label.";
        } // END of backup-outgoing-label definition.

        leaf bypass-trunk-id  {
            type  uint32;
            description "This attribute returns the bypass trunk id value.";
        } // END of bypass-trunk-id definition.

        leaf backup-interface-name  {
            type  string {
                length "1..1965";
                pattern "[^?' =,>|]+";
            }
            description "This attribute returns the backup interface name.";
        } // END of backup-interface-name definition.

    } // END of ospfv2-topology-independent-lfa-repair-lists-nexthop-info-state definition.
    grouping ospfv2-topology-independent-lfa-sr-trunks-state {
        description
            "Grouping for OSPF topology independent LFA segment routing trunks
                        attributes";
        leaf trunk-name  {
            type  string {
                length "1..1965";
                pattern "[^?' =,>|]+";
            }
            description "This attribute returns the trunk name.";
        } // END of trunk-name definition.

        leaf trunk-id  {
            type  uint32;
            description "This attribute returns the trunk id value.";
        } // END of trunk-id definition.

        leaf ftn-id  {
            type  uint32;
            description "This attribute returns the id value of FEC to Next Hop Label Forward
                        Entry.";
        } // END of ftn-id definition.

        leaf ref-cnt  {
            type  uint32;
            description "This attribute returns the ref cnt.";
        } // END of ref-cnt definition.

        leaf outgoing-label-count  {
            type  yang:counter32;
            description "This attribute returns the number of outgoing labels.";
        } // END of outgoing-label-count definition.

        leaf-list outgoing-labels  {
            type  uint32;
            description "This attribute returns the list value of outgoing labels.";
        } // END of outgoing-labels definition.

        leaf next-hop  {
            type  inet:ipv4-address;
            description "This attribute returns the next hop address.";
        } // END of next-hop definition.

    } // END of ospfv2-topology-independent-lfa-sr-trunks-state definition.
    grouping ospfv2-topology-independent-lfa-sr-trunks {
        description
            "Grouping for OSPF topology independent LFA segment routing trunk";
        container segment-routing-trunks {
            config false;
            description
                "OSPFv2 topology independent LFA segment routing trunks";

            list segment-routing-trunk {
                key "trunk-name";
                config false;
                description
                    "List of OSPF segment routing trunks";
                leaf trunk-name  {
                    type  leafref {
                        path  "../state/trunk-name";
                    }
                    description "This attribute returns the trunk name.";
                } // END of trunk-name definition.

                container state {
                    config false;
                    description
                        "Operational state data";
                    uses ospfv2-topology-independent-lfa-sr-trunks-state;
                } // END of state-container definition.
            } // End of segment-routing-trunk-list
        } // END of segment-routing-trunks-container definition.
    } // END of ospfv2-topology-independent-lfa-sr-trunks definition.
    grouping ospfv2-topology-independent-lfa-repair-lists-nexthop-info {
        description
            "Grouping for OSPF topology independent LFA repair lists nexthop info";
        container nexthop-infos {
            config false;
            description
                "OSPFv2 topology independent LFA repair lists nexthop info";

            list nexthop-info {
                key "primary-path-nexthop";
                config false;
                description
                    "List of OSPF nexthop info";
                leaf primary-path-nexthop  {
                    type  leafref {
                        path  "../state/primary-path-nexthop";
                    }
                    description "This attribute returns the primary nexthop value.";
                } // END of primary-path-nexthop definition.

                container state {
                    config false;
                    description
                        "Operational state data";
                    uses ospfv2-topology-independent-lfa-repair-lists-nexthop-info-state;
                    uses ospfv2-topology-independent-lfa-nodes-state;
                } // END of state-container definition.
            } // End of nexthop-info-list
        } // END of nexthop-infos-container definition.
    } // END of ospfv2-topology-independent-lfa-repair-lists-nexthop-info definition.
    grouping ospfv2-topology-independent-lfa-repair-lists {
        description
            "Grouping for OSPF topology independent LFA repair lists";
        container repair-lists {
            config false;
            description
                "OSPFv2 topology independent LFA repair lists";

            list repair-list {
                key "prefix";
                config false;
                description
                    "List of OSPF repairs";
                leaf prefix  {
                    type  leafref {
                        path  "../state/prefix";
                    }
                    description "This attribute returns the prefix value.";
                } // END of prefix definition.

                container state {
                    config false;
                    description
                        "Operational state data";
                    uses ospfv2-topology-independent-lfa-repair-lists-state;
                } // END of state-container definition.
                uses ospfv2-topology-independent-lfa-repair-lists-primary-info;
                uses ospfv2-topology-independent-lfa-repair-lists-nexthop-info;
                uses ospfv2-topology-independent-lfa-sr-trunks;
            } // End of repair-list-list
        } // END of repair-lists-container definition.
    } // END of ospfv2-topology-independent-lfa-repair-lists definition.


}
