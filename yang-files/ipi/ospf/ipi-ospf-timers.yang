/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospf-timers.yang
*
*/

submodule ipi-ospf-timers {

    yang-version 1.1;

    belongs-to  ipi-ospf { prefix ipi-ospf; }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF timers";


    revision "2025-01-26" {
        description "Added implicit_delete tag for timers container";
        reference " 0.6.0.";
    }

    revision "2022-06-01" {
        description "Updated the yang file with feature";
        reference " 0.5.0.";
    }

    revision "2021-09-03" {
        description "Update descriptions of attribute";
        reference "Initial Version";
    }

    revision "2021-04-30" {
        description "Allow value update on RDN attributes on timers lsa delays list";
        reference "Initial Version";
    }

    revision "2021-04-29" {
        description "timers lsa min-delay and max-delay range updated to 1-600000";
        reference "Initial Version";
    }

    revision "2021-04-06" {
        description "Restructured module in accordance with OpenConfig style";
        reference "Initial Version";
    }

    grouping ospfv2-area-virtual-link-timers-state {
        description
            "Grouping for OSPF virtual link timers operational state";
        leaf wait-interval  {
            type  uint32;
            config false;
            description "Virtual link wait interval state.";
        } // END of wait-interval definition.

    } // END of ospfv2-area-virtual-link-timers-state definition.
    grouping ospfv2-area-virtual-link-timers-config {
        description
            "Grouping for OSPF virtual link timers configuration data";
        leaf dead-interval  {
            type  uint16 {
                 range "1..65535"  {
                    description "1..65535: Supported range 1 - 65535";
                 }
            }
            units "seconds";
            description "Dead router detection time. Interval during which no packets are
                        received and after which the router acknowledges a neighboring router
                        as off-line.";
        } // END of dead-interval definition.

        leaf hello-interval  {
            type  uint16 {
                 range "1..65535"  {
                    description "1..65535: Supported range 1 - 65535";
                 }
            }
            units "seconds";
            default "10";
            description "Hello packet interval. Interval the router waits before it sends a
                        hello packet.";
        } // END of hello-interval definition.

        leaf transmit-delay  {
            type  uint16 {
                 range "1..3600"  {
                    description "1..3600: Supported range 1 - 3600";
                 }
            }
            units "seconds";
            default "1";
            description "LSA transmission delay. Interval the router waits before it transmits
                        a packet.";
        } // END of transmit-delay definition.

        leaf retransmission-interval  {
            type  uint16 {
                 range "1..3600"  {
                    description "1..3600: Supported range 1 - 3600";
                 }
            }
            units "seconds";
            default "5";
            description "LSA retransmit interval. Interval the router waits before it sends a
                        hello packet.";
        } // END of retransmission-interval definition.

    } // END of ospfv2-area-virtual-link-timers-config definition.
    grouping ospfv2-area-virtual-link-timers-top {
        description
            "Grouping for OSPF area virtual link timers";
        container timers {
            description
                "OSPF virtual link timers";
            container config {
                description
                    "Configuration data for OSPF area virtual link timers";
                uses ospfv2-area-virtual-link-timers-config;
            } // END of config-container definition.
            container state {
                config false;
                description
                    "Operational state data for OSPF area virtual link timers";
                uses ospfv2-area-virtual-link-timers-config;
            } // END of state-container definition.
        } // END of timers-container definition.
    } // END of ospfv2-area-virtual-link-timers-top definition.
    grouping ospfv2-timers-spf-delay-config {
        description
            "Grouping for OSPF SPF delay timers configuration data";
        leaf min-delay  {
            type  uint32 {
                 range "0..2147483647"  {
                    description "0..2147483647: Supported range 0 - 2147483647";
                 }
            }
            units "milliseconds";
            mandatory true;
            description "Use this attribute to set the minimum delay between receiving a change
                        to SPF calculation.";
        } // END of min-delay definition.

        leaf max-delay  {
            type  uint32 {
                 range "0..2147483647"  {
                    description "0..2147483647: Supported range 0 - 2147483647";
                 }
            }
            units "milliseconds";
            mandatory true;
            description "Use this attribute to set the maximum delay between receiving a change
                        to SPF calculation.";
        } // END of max-delay definition.

    } // END of ospfv2-timers-spf-delay-config definition.
    grouping ospfv2-timers-spf-delay-top {
        description
            "Grouping for OSPF SPF delay timers";
        container delay {
            description
                "OSPF SPF delay timers";
            container config {
                presence "yes";
                description
                    "Configuration data for OSPF SPF delay timers";
                uses ospfv2-timers-spf-delay-config;
            } // END of config-container definition.
            container state {
                config false;
                description
                    "Operational state data for OSPF SPF delay timers";
                uses ospfv2-timers-spf-delay-config;
            } // END of state-container definition.
        } // END of delay-container definition.
    } // END of ospfv2-timers-spf-delay-top definition.
    grouping ospfv2-timers-spf-top {
        description
            "Grouping for OSPF SPF timers";
        container spf {
            description
                "OSPF SPF timers";
            uses ospfv2-timers-spf-delay-top;
        } // END of spf-container definition.
    } // END of ospfv2-timers-spf-top definition.
    grouping ospfv2-timers-lsa-delay-config {
        description
            "Grouping for OSPF LSA delay timers configuration data";
        leaf start-delay  {
            type  uint32 {
                 range "0..600000"  {
                    description "0..600000: Supported range 0 - 600000";
                 }
            }
            units "milliseconds";
            default "0";
            description "Use this attribute to set the minimum delay in milliseconds for the
                        generation of LSAs. The first instance of LSA is always generated
                        immediately upon a local OSPF topology change.";
        } // END of start-delay definition.

        leaf min-delay  {
            type  uint32 {
                 range "1..600000"  {
                    description "1..600000: Supported range 1 - 600000";
                 }
            }
            units "milliseconds";
            default "5000";
            description "Use this attribute to set the hold time in milliseconds. This value is
                        used to calculate the subsequent rate limiting times for LSA
                        generation.";
        } // END of min-delay definition.

        leaf max-delay  {
            type  uint32 {
                 range "1..600000"  {
                    description "1..600000: Supported range 1 - 600000";
                 }
            }
            units "milliseconds";
            default "5000";
            description "Use this attribute to set the maximum wait time in milliseconds
                        between generation of the same LSA.";
        } // END of max-delay definition.

    } // END of ospfv2-timers-lsa-delay-config definition.
    grouping ospfv2-timers-lsa-delay-top {
        description
            "Grouping for OSPF LSA delay timers";
        container delays {
            description
                "OSPF LSA delay timers";

            list delay {
                key "start-delay min-delay max-delay";
                max-elements 1;
                description
                    "List of OSPF LSA delay timers";
                leaf start-delay  {
                    type  leafref {
                        path  "../config/start-delay";
                    }
                    description "Use this attribute to set the minimum delay in milliseconds for the
                                generation of LSAs. The first instance of LSA is always generated
                                immediately upon a local OSPF topology change.";
                } // END of start-delay definition.

                leaf min-delay  {
                    type  leafref {
                        path  "../config/min-delay";
                    }
                    description "Use this attribute to set the hold time in milliseconds. This value is
                                used to calculate the subsequent rate limiting times for LSA
                                generation.";
                } // END of min-delay definition.

                leaf max-delay  {
                    type  leafref {
                        path  "../config/max-delay";
                    }
                    description "Use this attribute to set the maximum wait time in milliseconds
                                between generation of the same LSA.";
                } // END of max-delay definition.

                container config {
                    description
                        "Configuration data for OSPF LSA delay timers";
                    uses ospfv2-timers-lsa-delay-config;
                } // END of config-container definition.
                container state {
                    config false;
                    description
                        "Operational state data for OSPF LSA delay timers";
                    uses ospfv2-timers-lsa-delay-config;
                } // END of state-container definition.
            } // End of delay-list
        } // END of delays-container definition.
    } // END of ospfv2-timers-lsa-delay-top definition.
    grouping ospfv2-timers-lsa-config {
        description
            "Grouping for OSPF LSA timers configuration data";
        leaf min-arrival-interval  {
            type  uint32 {
                 range "0..600000"  {
                    description "0..600000: Supported range 0 - 600000";
                 }
            }
            units "milliseconds";
            default "1000";
            description "Use this attribute to set the minimum interval to accept the same
                        link-state advertisement (LSA) from OSPF neighbors.";
        } // END of min-arrival-interval definition.

    } // END of ospfv2-timers-lsa-config definition.
    grouping ospfv2-timers-lsa-top {
        description
            "Grouping for OSPF LSA timers";
        container lsa {
            description
                "OSPF LSA timers";
            container config {
                description
                    "Configuration data for OSPF LSA timers";
                uses ospfv2-timers-lsa-config;
            } // END of config-container definition.
            container state {
                config false;
                description
                    "Operational state data for OSPF LSA timers";
                uses ospfv2-timers-lsa-config;
            } // END of state-container definition.
            uses ospfv2-timers-lsa-delay-top;
        } // END of lsa-container definition.
    } // END of ospfv2-timers-lsa-top definition.
    grouping ospfv2-timers-lfa-config {
        description
            "Grouping for OSPF LFA timers configuration data";
        leaf termination-hold-interval  {
            if-feature feature-list:HAVE_OSPF_LFA;
            type  uint32 {
                 range "100..100000"  {
                    description "100..100000: Supported range 100 - 100000";
                 }
            }
            units "milliseconds";
            default "6000";
            description "Use this attribute to set the LFA termination hold on interval. It
                        represents the delay of primary route installation (to avoid micro
                        loop) after a failover.";
        } // END of termination-hold-interval definition.

    } // END of ospfv2-timers-lfa-config definition.
    grouping ospfv2-timers-lfa-top {
        description
            "Grouping for OSPF LFA timers";
        container lfa {
            description
                "OSPF LFA timers";
            container config {
                description
                    "Configuration data for OSPF LFA timers";
                uses ospfv2-timers-lfa-config;
            } // END of config-container definition.
            container state {
                config false;
                description
                    "Operational state data for OSPF LFA timers";
                uses ospfv2-timers-lfa-config;
            } // END of state-container definition.
        } // END of lfa-container definition.
    } // END of ospfv2-timers-lfa-top definition.
    grouping ospfv2-timers-config {
        description
            "Grouping for OSPF timers configuration data";
    } // END of ospfv2-timers-config definition.
    grouping ospfv2-timers-top {
        description
            "Grouping for OSPF timers";
        container timers {
            description
                "OSPF timers";
            container config {
                description
                    "Configuration data for OSPF timers";
                uses ospfv2-timers-config;
            } // END of config-container definition.
            container state {
                config false;
                description
                    "Operational state data for OSPF timers";
                uses ospfv2-timers-config;
            } // END of state-container definition.
            uses ospfv2-timers-lfa-top;
            uses ospfv2-timers-lsa-top;
            uses ospfv2-timers-spf-top;
        } // END of timers-container definition.
    } // END of ospfv2-timers-top definition.


}
