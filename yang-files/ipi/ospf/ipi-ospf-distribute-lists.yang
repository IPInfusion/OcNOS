/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospf-distribute-lists.yang
*
*/

submodule ipi-ospf-distribute-lists {

    yang-version 1.1;

    belongs-to  ipi-ospf { prefix ipi-ospf; }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF distribute list";


    revision "2025-03-17" {
        description "Updated input help string to the WORD for the attribute access-control-list";
        reference " 0.4.0.";
    }

    revision "2022-06-01" {
        description "Updated the yang file with feature";
        reference " 0.4.0.";
    }

    revision "2021-09-03" {
        description "Update descriptions of attribute";
        reference "Initial Version";
    }

    revision "2021-04-30" {
        description "Restructured value range for ospfv2-processes list";
        reference "Initial Version";
    }

    revision "2021-04-06" {
        description "Restructured module in accordance with OpenConfig style";
        reference "Initial Version";
    }

    grouping ospfv2-filter-out-ospf-process-config {
        description
            "Grouping for OSPF distribute list filter out OSPF process
                        configuration data";
        leaf ospf-process-id  {
            type  uint16 {
                 range "0..65535"  {
                    description "0..65535: Supported range 0 - 65535";
                 }
            }
            description "Use this attribute to set the OSPF ID in distribution list filter out.";
        } // END of ospf-process-id definition.

        leaf access-control-list-out-ospf  {
            type  string {
                length "1..1965";
                pattern "[^?' =,>|]+";
            }
            description "Use this attribute to set the access control list name in distribution
                        list.";
        } // END of access-control-list-out-ospf definition.

    } // END of ospfv2-filter-out-ospf-process-config definition.
    grouping ospfv2-filter-out-ospf-process-top {
        description
            "Grouping for OSPF distribute list filter out OSPF process";
        container ospfv2-processes {
            description
                "OSPF distribute list filter out OSPF processes";

            list ospfv2-process {
                key "ospf-process-id";
                description
                    "OSPF distribute list filter out OSPF processes";
                leaf ospf-process-id  {
                    type  leafref {
                        path  "../config/ospf-process-id";
                    }
                    description "Use this attribute to set the OSPF ID in distribution list filter out.";
                } // END of ospf-process-id definition.

                container config {
                    description
                        "Configuration data for OSPF distribute list filter out OSPF process";
                    uses ospfv2-filter-out-ospf-process-config;
                } // END of config-container definition.
                container state {
                    config false;
                    description
                        "Operational state data for OSPF distribute list filter out OSPF
                                process";
                    uses ospfv2-filter-out-ospf-process-config;
                } // END of state-container definition.
            } // End of ospfv2-process-list
        } // END of ospfv2-processes-container definition.
    } // END of ospfv2-filter-out-ospf-process-top definition.
    grouping ospfv2-filter-out-routing-protocol-config {
        description
            "Grouping for OSPF distribute list filter out configuration data";
        leaf access-control-list-isis  {
            type  string {
                length "1..1965";
                pattern "[^?' =,>|]+";
            }
            description "Use this attribute to set the access control list name for ISIS
                        protocol.";
        } // END of access-control-list-isis definition.

        leaf access-control-list-bgp  {
            type  string {
                length "1..1965";
                pattern "[^?' =,>|]+";
            }
            description "Use this attribute to set the access control list name for BGP
                        protocol.";
        } // END of access-control-list-bgp definition.

        leaf access-control-list-rip  {
            type  string {
                length "1..1965";
                pattern "[^?' =,>|]+";
            }
            description "Use this attribute to set the access control list name for RIP
                        protocol.";
        } // END of access-control-list-rip definition.

        leaf access-control-list-static  {
            type  string {
                length "1..1965";
                pattern "[^?' =,>|]+";
            }
            description "Use this attribute to set the access control list name for static
                        routes.";
        } // END of access-control-list-static definition.

        leaf access-control-list-connected  {
            type  string {
                length "1..1965";
                pattern "[^?' =,>|]+";
            }
            description "Use this attribute to set the access control list name for connected
                        networks.";
        } // END of access-control-list-connected definition.

        leaf access-control-list-kernel  {
            type  string {
                length "1..1965";
                pattern "[^?' =,>|]+";
            }
            description "Use this attribute to set the access control list name for KERNEL
                        routes.";
        } // END of access-control-list-kernel definition.

    } // END of ospfv2-filter-out-routing-protocol-config definition.
    grouping ospfv2-distribute-lists-filter-out-top {
        description
            "Grouping for OSPF distribute list filter out";
        container filter-out {
            description
                "OSPF distribute list filter out";
            container config {
                description
                    "Configuration data for OSPF distribute list filter out";
                uses ospfv2-filter-out-routing-protocol-config;
            } // END of config-container definition.
            container state {
                config false;
                description
                    "Operational state data for OSPF distribute list filter out";
                uses ospfv2-filter-out-routing-protocol-config;
            } // END of state-container definition.
            uses ospfv2-filter-out-ospf-process-top;
        } // END of filter-out-container definition.
    } // END of ospfv2-distribute-lists-filter-out-top definition.
    grouping ospfv2-distribute-lists-in-config {
        description
            "Grouping for OSPF distribute list configuration data";
        leaf access-control-list  {
            type  string {
                length "1..1965";
                pattern "[^?' =,>|]+";
            }
            description "Use this attribute to set the access control list name in distribution
                        list.";
        } // END of access-control-list definition.

    } // END of ospfv2-distribute-lists-in-config definition.
    grouping ospfv2-distribute-list-top {
        description
            "Grouping for OSPF distribute list";
        container distribute-list {
            if-feature feature-list:HAVE_ACL;
            description
                "OSPF distribute list";
            container filter-in {
                description
                    "OSPF distribute list filter in";
                container config {
                    description
                        "Configuration data for OSPF distribute list filter in";
                    uses ospfv2-distribute-lists-in-config;
                } // END of config-container definition.
                container state {
                    config false;
                    description
                        "Operational state data for OSPF distribute list filter in";
                    uses ospfv2-distribute-lists-in-config;
                } // END of state-container definition.
            } // END of filter-in-container definition.
            uses ospfv2-distribute-lists-filter-out-top;
        } // END of distribute-list-container definition.
    } // END of ospfv2-distribute-list-top definition.


}
