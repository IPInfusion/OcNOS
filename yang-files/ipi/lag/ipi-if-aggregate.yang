/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-if-aggregate.yang
*
*/

module ipi-if-aggregate {

    yang-version 1.1;

    namespace   "http://www.ipinfusion.com/yang/ocnos/ipi-if-aggregate";

    prefix "ipi-if-aggregate";

    import cml-data-types {
        prefix cml-data-types;
        revision-date 2026-05-15;
    }

    import ipi-lag-types {
        prefix ipi-lag-types;
        revision-date 2025-09-08;
    }

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Interface level configurations for LAG";


    revision "2026-04-15" {
        description "Consider the interface name to reject link-aggregation when macsec is enabled on interface";
        reference " 0.12.9.";
    }

    revision "2026-04-02" {
        description "Reject link-aggregation when macsec is enabled on interface";
        reference " 0.12.8.";
    }

    revision "2025-12-28" {
        description "Changed the helpstring to static-channel-group for static ";
        reference " 0.12.7.";
    }

    revision "2025-11-10" {
        description "Added dependency for channel-group CLI and mlag aggregation";
        reference " 0.12.6.";
    }

    revision "2025-09-08" {
        description "Added UP timestamp for LAG interface";
        reference " 0.12.4.";
    }

    revision "2025-06-19" {
        description "Added dependency for channel-group CLI and lag-shaper";
        reference " 0.12.5.";
    }

    revision "2025-06-18" {
        description "Removed the CML_RESET_INSTANCE_FORCE for aggregate id and lacp mode";
        reference " 0.12.3.";
    }

    revision "2025-04-25" {
        description "Ordering issue between member-aggregation and load-interval";
        reference " 0.12.2.";
    }

    revision "2025-04-04" {
        description "Removed some DCBX custom triggers that are no longer needed";
        reference " 0.12.1.";
    }

    revision "2025-02-19" {
        description "Added streaming telemetry support";
        reference " 0.12.0.";
    }

    revision "2024-12-17" {
        description "Added CML_RESET_INSTANCE_FORCE for aggregate-id";
        reference " 0.11.5.";
    }

    revision "2024-12-05" {
        description "Added custom db triggers related to dcbx-enable persistence that fix issues with dcbx in port channels.";
        reference " 0.11.4.";
    }

    revision "2024-11-05" {
        description "Removed custom db triggers related to  dcbx-enable persistence.";
        reference " 0.11.3.";
    }

    revision "2024-10-22" {
        description "Fixed dcbx-enable persistence and db-sync issues.";
        reference " 0.11.2.";
    }

    revision "2024-09-24" {
        description "Revert load-balance changes";
        reference " 0.11.1.";
    }

    revision "2024-07-29" {
        description "Added support for global Port Selection Criteria configuration";
        reference " 0.11.0.";
    }

    revision "2024-07-24" {
        description "Fixed circular dependencies";
        reference " 0.10.4.";
    }

    revision "2024-07-08" {
        description "Fixed port mirror / interface dependencies";
        reference " 0.10.3.";
    }

    revision "2024-05-28" {
        description "Updated max port channel weight to 32 for Marvell Platform";
        reference " 0.10.2.";
    }

    revision "2024-04-05" {
        description "Handled range validation for Q1 Q2 and marvel platform for the CLI port-channel weight";
        reference " 0.10.1.";
    }

    revision "2024-02-14" {
        description "Added dependentObject for member-aggregation config";
        reference " 0.11.6.";
    }

    revision "2024-01-03" {
        description "Updated max port channel weight to 64";
        reference " 0.10.0.";
    }

    revision "2023-12-15" {
        description "Added port-channel-weight command for Marvell";
        reference " 0.9.1.";
    }

    revision "2023-09-19" {
        description "Added implicit_delete tag under port-channel-weight container";
        reference " 0.9.0.";
    }

    revision "2022-11-29" {
        description "Addressed make cmlgen warnings";
        reference " 0.8.1.";
    }

    revision "2022-11-04" {
        description "Modified helpstring for port-channel min-banwidth";
        reference " 0.8.0.";
    }

    revision "2022-09-30" {
        description "Import cml-data-types used by notifications";
        reference " 0.7.0.";
    }

    revision "2022-06-01" {
        description "Updated the yang file with feature";
        reference " 0.6.0.";
    }

    revision "2022-05-16" {
        description "Added runtime attributes for static LAG group members";
        reference " 0.5.0.";
    }

    revision "2022-04-20" {
        description "Added changes for port channel weight";
        reference " 0.4.0.";
    }

    revision "2021-09-03" {
        description "Update descriptions of attribute";
        reference " 0.3.0.";
    }

    revision "2020-12-15" {
        description "Change to have data-types in lower case instead of camel case";
        reference " 0.2.0.";
    }

    revision "2018-06-21" {
        description "Initial Version";
        reference " 0.1.0.";
    }

    grouping port-channel-weight-config {
        description
            "Configuration data for port channel weight";
        leaf weight  {
            type  uint16 {
                 range "1..64"  {
                    description "1..64:Feature : HAVE_DNX Supported range 1 - 16Feature : HAVE_MARVELL
                            Supported range 1 - 32Not Feature : HAVE_DNX,HAVE_MARVELL  Supported
                            range 1 - 64";
                 }
            }
            description "Set the port channel weight";
        } // END of weight definition.

    } // END of port-channel-weight-config definition.
    grouping aggregated-interface-config {
        description
            "Aggregated configuration data attributes group";
        leaf agg-type  {
            type  ipi-lag-types:lag_link_agg_type_t;
            mandatory true;
            description "Sets the type of LAG, how it is configured / maintained";
        } // END of agg-type definition.

        leaf aggregate-id  {
            type  uint16 {
                 range "1..65535"  {
                    description "1..65535:Not Feature : HAVE_MLAG  Supported range 1 - 65535Feature :
                            HAVE_MLAG Supported range 1 - 16383";
                 }
            }
            mandatory true;
            description "Channel group identifier";
        } // END of aggregate-id definition.

        leaf lacp-mode  {
            type  ipi-lag-types:lacp_mode_t;
            mandatory true;
            description "Use this command to add a port to a channel group specified by the
                        channel group number (1-12). This command enables link aggregation on
                        a port, so that it may be selected for aggregation by the local
                        system.";
        } // END of lacp-mode definition.

    } // END of aggregated-interface-config definition.
    grouping aggregator-interface-config {
        description
            "Aggregator configuration data attributes group";
        leaf load-balance-criteria  {
            if-feature feature-list:HAVE_SWFWDR;
            if-feature feature-list:HAVE_LACP;
            type  ipi-lag-types:lag_load_balancing_criteria_t;
            description "Use this attribute to configure LACP port-channel load-balancing and
                        set port selection criteria (PSC) on an aggregator.";
        } // END of load-balance-criteria definition.

        leaf min-links  {
            if-feature feature-list:HAVE_LACP;
            type  uint8 {
                 range "2..32"  {
                    description "2..32: Supported range 2 - 32";
                 }
            }
            description "Minimum number of active links required in this aggregator";
        } // END of min-links definition.

        leaf min-bandwidth  {
            if-feature feature-list:HAVE_LACP;
            type  string {
                length "1..1965";
                pattern "[^?' =,>|]+";
            }
            description "Minimum number of bandwidth required in this aggregator";
        } // END of min-bandwidth definition.

    } // END of aggregator-interface-config definition.
    grouping aggregator-interface-state {
        description
            "Aggregator interface operational data";
        leaf agg-min-links-state  {
            type  ipi-lag-types:lag_agg_min_links_status;
            config false;
            description "Aggregator is 'up' if 'min-links' number of active links in
                        aggregator, else 'down'";
        } // END of agg-min-links-state definition.

        leaf agg-up-timestamp  {
            type  ipi-lag-types:lag_up_time_t {
                length "1..1965";
            }
            config false;
            description "Total time that aggregator is 'up'";
        } // END of agg-up-timestamp definition.

    } // END of aggregator-interface-state definition.
    grouping aggregator-member-state {
        description
            "Operational attributes of aggregated Links";
        leaf link-name  {
            type  string {
                length "1..1965";
                pattern "[^?' =,>|]+";
            }
            description "Name of Aggregated Link";
        } // END of link-name definition.

        leaf link-state  {
            type  ipi-lag-types:lag_member_link_status_t;
            description "Indicates link synchronization state";
        } // END of link-state definition.

    } // END of aggregator-member-state definition.
    grouping aggregator-members-top {
        description
            "Grouping for aggregator members";
        container members {
            config false;
            description
                "Links of aggregator";

            list member {
                key "link-name";
                config false;
                description
                    "List of links in aggregator";
                leaf link-name  {
                    type  leafref {
                        path  "../state/link-name";
                    }
                    description "Aggregated Link Name";
                } // END of link-name definition.

                container state {
                    config false;
                    description
                        "Operational data for links in aggregator";
                    uses aggregator-member-state;
                } // END of state-container definition.
            } // End of member-list
        } // END of members-container definition.
    } // END of aggregator-members-top definition.

    grouping  member-aggregation-grouping {
    description
        "NSM LACP interface related operations";
    container member-aggregation {
        if-feature feature-list:HAVE_LACP;
        description
            "NSM LACP interface related operations";
        container config {
            presence "yes";
            description
                "Configuration data for aggregated interface level";
            uses aggregated-interface-config;
        } // END of config-container definition.
        container state {
            config false;
            description
                "Operation state data for static/lacp aggregators";
            uses aggregated-interface-config;
        } // END of state-container definition.
        container port-channel-weight {
            if-feature feature-list:HAVE_DUNE_OR_HAVE_MARVELL;
            description
                "configure port channel weight";
            container config {
                description
                    "Configuration data for port channel weight";
                uses port-channel-weight-config;
            } // END of config-container definition.
            container state {
                config false;
                description
                    "Operation state data for port channel weight";
                uses port-channel-weight-config;
            } // END of state-container definition.
        } // END of port-channel-weight-container definition.
    } // END of member-aggregation-container definition.
    } // END of member-aggregation-grouping definition.

    grouping  aggregator-grouping {
    description
        "NSM LACP aggregator related operations";
    container aggregator {
        if-feature feature-list:HAVE_LACP;
        description
            "NSM LACP aggregator related operations";
        container config {
            description
                "Configuration data for aggregator inerfaced";
            uses aggregator-interface-config;
        } // END of config-container definition.
        container state {
            config false;
            description
                "Operational data for static/lacp aggregators";
            uses aggregator-interface-config;
            uses aggregator-interface-state;
        } // END of state-container definition.
        uses aggregator-members-top;
    } // END of aggregator-container definition.
    } // END of aggregator-grouping definition.

    augment /ipi-interface:interfaces/ipi-interface:interface {
    when " /ipi-interface:interfaces/ipi-interface:interface/ipi-interface:name ";
    // when " not(/ipi-macsec:macsec/ipi-macsec-interface:interfaces/ipi-macsec-interface:interface/ipi-macsec-interface:config) ";
        description
            "NSM LACP interface related operations";
        uses member-aggregation-grouping;
    }

    augment /ipi-interface:interfaces/ipi-interface:interface {
        description
            "NSM LACP aggregator related operations";
        uses aggregator-grouping;
    }


    notification agg-min-links-state-update {
        if-feature feature-list:HAVE_LACP;

        description "Notify when a total Active (link-UP) LAG member count becomes less than the configured min-link count. Severity level is CRITICAL for interface going down and INFO for interface moving to UP state..";

        leaf severity {
            type cml-data-types:cml_notif_severity_t;
            description "Notification severity level";
        }

        leaf eventClass {
            type cml-data-types:cml_notif_class_t;
            description "Notification event class (value: STATE)";
        }

        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf agg-min-links-state {
            type ipi-lag-types:lag_agg_min_links_status;
        description
            "Aggregator is 'up' if 'min-links' number of active links in
                    aggregator, else 'down'";
        }
    }

}
