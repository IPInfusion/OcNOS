/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-lacp-types.yang
*
*/

module ipi-lacp-types {

    yang-version 1.1;

    namespace   "http://www.ipinfusion.com/yang/ocnos/ipi-lacp-types";

    prefix "ipi-lacp-types";

    organization
        "IP Infusion Inc.";

    contact
        "Address: 3965 Freedom Circle, Suite 200, Santa Clara, CA 95054
         Phone: +1 408-400-1900
         E-mail: support@ipinfusion.com
         Web: http://www.ipinfusion.com/";

    description
        "This module defines data types related to the Layer-2 LAG model";


    revision "2022-08-10" {
        description "Initial version";
        reference " 0.1.0.";
    }



    typedef  lacp_activity_type_t {
        type enumeration {
            enum passive {
                value 0;
                description "Set LACP membership type is passive";
            }
            enum active {
                value 1;
                description "Set LACP membership type is active";
            }
        }
        description "type definition for LACP_ACTIVITY_TYPE_T";
    }

    typedef  lacp_timeout_type_t {
        type enumeration {
            enum long {
                value 0;
                description "Set LACP long timeout";
            }
            enum short {
                value 1;
                description "Set LACP short timeout";
            }
        }
        description "type definition for LACP_TIMEOUT_TYPE_T";
    }

    typedef  lacp_synchronization_type_t {
        type enumeration {
            enum out-of-sync {
                value 0;
                description "LACP synchronization is out of sync";
            }
            enum in-sync {
                value 1;
                description "LACP synchronization is in sync";
            }
        }
        description "type definition for LACP_SYNCHRONIZATION_TYPE_T";
    }

    typedef  lacp_bridgetype_t {
        type enumeration {
            enum customer-bridge-group-address {
                value 0;
                description "customer bridge group address";
            }
            enum multicast-group-address {
                value 1;
                description "multicast group address";
            }
            enum non-tmpr-group-address {
                value 2;
                description "non TPMR group address";
            }
        }
        description "type definition for LACP_BRIDGETYPE_T";
    }

    typedef  lacp_debug_t {
        type bits {
            bit event {
                position 0;
                description "Set the debug options for LACP events";
            }
            bit cli {
                position 1;
                description "Echo commands to console";
            }
            bit timer {
                position 2;
                description "Echo timer expiry to console";
            }
            bit packet {
                position 3;
                description "Set the debug option for LACP packet";
            }
            bit rx {
                position 4;
                description "Echo receiving of LACP PDUs to console";
            }
            bit tx {
                position 5;
                description "Echo transmission of LACP PDUs to console";
            }
            bit sync {
                position 6;
                description "Echo synchronization to console";
            }
            bit ha {
                position 7;
                description "Echo High availability events to console";
            }
        }
        description "type definition for LACP_DEBUG_T";
    }

    typedef  lacp_rcv_state_t {
        type enumeration {
            enum Invalid {
                value 0;
                description "LACP Receive machine state is Invalid";
            }
            enum Initialize {
                value 1;
                description "LACP Receive machine state is Initialize";
            }
            enum Port-disabled {
                value 2;
                description "Port,LACP Receive machine state is Port disabled";
            }
            enum LACP-disabled {
                value 3;
                description "LACP,LACP Receive machine state is LACP disabled";
            }
            enum Expired {
                value 4;
                description "LACP Receive machine state is Expired";
            }
            enum Defaulted {
                value 5;
                description "LACP Receive machine state is Defaulted";
            }
            enum Current {
                value 6;
                description "LACP Receive machine state is Current";
            }
        }
        description "type definition for LACP_RCV_STATE_T";
    }

    typedef  lacp_periodic_tx_state_t {
        type enumeration {
            enum Invalid {
                value 0;
                description "LACP Periodic Transmission machine state is Invalid";
            }
            enum No-periodic {
                value 1;
                description "LACP Periodic Transmission machine state is No, periodic";
            }
            enum Fast-periodic {
                value 2;
                description "LACP Periodic Transmission machine state is Fast, periodic";
            }
            enum Slow-periodic {
                value 3;
                description "LACP Periodic Transmission machine state is Slow, periodic";
            }
            enum Periodic {
                value 4;
                description "LACP Periodic Transmission machine state is Periodic";
            }
        }
        description "type definition for LACP_PERIODIC_TX_STATE_T";
    }

    typedef  lacp_mux_state_t {
        type enumeration {
            enum Detached {
                value 0;
                description "LACP Mux machine state is Detached";
            }
            enum Waiting {
                value 1;
                description "LACP Mux machine state is Waiting";
            }
            enum Attached {
                value 2;
                description "LACP Mux machine state is Attached";
            }
            enum Collecting {
                value 3;
                description "LACP Mux machine state is Collecting";
            }
            enum Distributing {
                value 4;
                description "LACP Mux machine state is Distributing";
            }
            enum Collecting-Distributing {
                value 5;
                description "LACP Mux machine state is Collecting, Distributing";
            }
        }
        description "type definition for LACP_MUX_STATE_T";
    }

    typedef  lacp_individual_aggregator_t {
        type enumeration {
            enum aggregator {
                value 0;
                description "Aggregator represents an Aggregate";
            }
            enum individual {
                value 1;
                description "Aggregator represents an Individual link";
            }
        }
        description "type definition for LACP_INDIVIDUAL_AGGREGATOR_T";
    }

}
