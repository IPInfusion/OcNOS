/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-sflow-ipfix.yang
*
*/

module ipi-sflow-ipfix {

    yang-version 1.1;

    namespace   "http://www.ipinfusion.com/yang/ocnos/ipi-sflow-ipfix";

    prefix "ipi-sflow-ipfix";

    import ipi-sflow-types {
        prefix ipi-sflow-types;
        revision-date 2025-03-06;
    }

    import ietf-inet-types {
        prefix inet;
        revision-date 2013-07-15;
    }

    import ipi-interface {
        prefix ipi-interface;
        revision-date 2026-03-10;
    }

    import ipi-network-instance {
        prefix ipi-network-instance;
        revision-date 2026-08-12;
    }

    import ipi-vrf {
        prefix ipi-vrf;
        revision-date 2026-08-12;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module provides user with the possibility to configure ipfix
                parameters";


    revision "2025-03-06" {
        description "Update revision date due improvements on sflow-types yang model.";
        reference " 0.2.0.";
    }

    revision "2024-12-04" {
        description "Limit samples-per-message to 1 or 8";
        reference " 0.1.9.";
    }

    revision "2024-04-02" {
        description "Fix interface display string";
        reference " 0.1.8.";
    }

    revision "2024-03-18" {
        description "Unique names for the key attribute from exporter, monitor and interface";
        reference " 0.1.7.";
    }

    revision "2024-01-29" {
        description "Add default value for Template Refresh Interval";
        reference " 0.1.6.";
    }

    revision "2024-01-28" {
        description "Make the exporter dependent of the interface";
        reference " 0.1.5.";
    }

    revision "2024-01-17" {
        description "Set a pattern for VRF and change the collector-ip type from a CML_HOSTNAME_T to a CML_IPV4_ADDR_T. See: JIRA-76361, JIRA-76365";
        reference " 0.1.4.";
    }

    revision "2024-01-10" {
        description "Set a pattern for exporter and flow names";
        reference " 0.1.3.";
    }

    revision "2023-12-21" {
        description "Restrict IPFIX to As 7535 28XB platform";
        reference " 0.1.2.";
    }

    revision "2023-12-20" {
        description "Removed trigger-threshold-timer attribute";
        reference " 0.1.1.";
    }

    revision "2023-12-02" {
        description "Initial version";
        reference " 0.1.0.";
    }

    grouping ipfix-ip-flow-exporter-config {
        description
            "ipfix-ip-flow-exporter-config";
        leaf exporter-name  {
            type  string {
                length "1..33";
                pattern "[a-zA-Z0-9_-]+";
            }
            description "The IP Flow Exporter name.";
        } // END of exporter-name definition.

        leaf source-if  {
            type  leafref {
                path  "/ipi-interface:interfaces/ipi-interface:interface/ipi-interface:name";
            }
            description "Source interface";
        } // END of source-if definition.

        leaf collector-ip  {
            type  inet:ipv4-address;
            description "The IP address of the IP Flow Collector.";
        } // END of collector-ip definition.

        leaf collector-port  {
            // when " ../collector-ip ";
            type  inet:port-number {
                 range "1024..65535"  {
                    description "1024..65535: Supported range 1024 - 65535";
                 }
            }
            description "The IP port of the IP Flow Collector.";
        } // END of collector-port definition.

        leaf collector-vrf  {
            // when " ../collector-ip ";
            if-feature feature-list:HAVE_VRF;
            type  leafref {
                path  "/ipi-network-instance:network-instances/ipi-network-instance:network-instance/ipi-vrf:vrf/ipi-vrf:config/ipi-vrf:vrf-name";
            }
            description "VRF Name associated with this instance";
        } // END of collector-vrf definition.

        leaf template-id  {
            type  uint32 {
                 range "256..65535"  {
                    description "256..65535: Supported range 256 - 65535";
                 }
            }
            description "Template ID for flow";
        } // END of template-id definition.

        leaf template-refresh-interval  {
            type  uint32 {
                 range "60..86400"  {
                    description "60..86400: Supported range 60 - 86400";
                 }
            }
            units "seconds";
            description "Interval to send periodic template updates to IP Flow Exporter.";
        } // END of template-refresh-interval definition.

        leaf samples-per-message  {
            type  ipi-sflow-types:sflow_samples_per_message_t;
            description "Samples per message";
        } // END of samples-per-message definition.

    } // END of ipfix-ip-flow-exporter-config definition.
    grouping ipfix-ip-flow-exporters-top {
        description
            "ipfix-ip-flow-exporters-top";
        container ip-flow-exporters {
            description
                "IP Flow Exporter parameters";

            list ip-flow-exporter {
                key "exporter-name";
                max-elements 1;
                description
                    "IP Flow Exporter parameters";
                leaf exporter-name  {
                    type  leafref {
                        path  "../config/exporter-name";
                    }
                    description "The IP Flow Exporter name.";
                } // END of exporter-name definition.

                container config {
                    description
                        "IP Flow Exporter configuration parameters";
                    uses ipfix-ip-flow-exporter-config;
                } // END of config-container definition.
                container state {
                    config false;
                    description
                        "IP Flow Exporter state data";
                    uses ipfix-ip-flow-exporter-config;
                } // END of state-container definition.
            } // End of ip-flow-exporter-list
        } // END of ip-flow-exporters-container definition.
    } // END of ipfix-ip-flow-exporters-top definition.
    grouping ipfix-ip-flow-monitor-config {
        description
            "ipfix-ip-flow-monitor-config";
        leaf monitor-name  {
            type  string {
                length "1..33";
                pattern "[a-zA-Z0-9_-]+";
            }
            description "The IP Flow Monitor name.";
        } // END of monitor-name definition.

        leaf flow-exporter  {
            type  leafref {
                path  "/ipfix/ip-flow-exporters/ip-flow-exporter/exporter-name";
            }
            description "Exporter Name associated with this instance";
        } // END of flow-exporter definition.

        leaf sampling-rate  {
            type  uint32 {
                 range "1024..16777215"  {
                    description "1024..16777215: Supported range 1024 - 16777215";
                 }
            }
            units "packets";
            description "Sampling Rate. One packet sampled after every 'sampling-rate' packets";
        } // END of sampling-rate definition.

        leaf observation-domain-id  {
            type  uint32 {
                 range "0..4294967295"  {
                    description "0..4294967295: Supported range 0 - 4294967295";
                 }
            }
            description "Observation Domain ID.";
        } // END of observation-domain-id definition.

    } // END of ipfix-ip-flow-monitor-config definition.
    grouping ipfix-ip-flow-monitors-top {
        description
            "ipfix-ip-flow-monitors-top";
        container ip-flow-monitors {
            description
                "IP Flow Monitor parameters";

            list ip-flow-monitor {
                key "monitor-name";
                max-elements 1;
                description
                    "IP Flow Monitor parameters";
                leaf monitor-name  {
                    type  leafref {
                        path  "../config/monitor-name";
                    }
                    description "The IP Flow Monitor name.";
                } // END of monitor-name definition.

                container config {
                    description
                        "IP Flow Monitor configuration parameters";
                    uses ipfix-ip-flow-monitor-config;
                } // END of config-container definition.
                container state {
                    config false;
                    description
                        "IP Flow Monitorr state data";
                    uses ipfix-ip-flow-monitor-config;
                } // END of state-container definition.
            } // End of ip-flow-monitor-list
        } // END of ip-flow-monitors-container definition.
    } // END of ipfix-ip-flow-monitors-top definition.
    grouping ipfix-ip-flow-interface-config {
        description
            "ipfix-ip-flow-interface-config";
        leaf interface-name  {
            type  leafref {
                path  "/ipi-interface:interfaces/ipi-interface:interface/ipi-interface:name";
            }
            description "The IP Flow interface name.";
        } // END of interface-name definition.

        leaf flow-monitor  {
            type  leafref {
                path  "/ipfix/ip-flow-monitors/ip-flow-monitor/config/monitor-name";
            }
            description "Monitor Name associated with this instance";
        } // END of flow-monitor definition.

    } // END of ipfix-ip-flow-interface-config definition.
    grouping ipfix-ip-flow-interfaces-top {
        description
            "ipfix-ip-flow-interfaces-top";
        container interfaces {
            description
                "IP Flow Interfaces";

            list interface {
                key "interface-name";
                description
                    "IP Flow Interface";
                leaf interface-name  {
                    type  leafref {
                        path  "../config/interface-name";
                    }
                    description "The IP Flow interface name.";
                } // END of interface-name definition.

                container config {
                    description
                        "IP Flow interface parameters";
                    uses ipfix-ip-flow-interface-config;
                } // END of config-container definition.
                container state {
                    config false;
                    description
                        "IP Flow Monitor Interface data";
                    uses ipfix-ip-flow-interface-config;
                } // END of state-container definition.
            } // End of interface-list
        } // END of interfaces-container definition.
    } // END of ipfix-ip-flow-interfaces-top definition.

    grouping  ipfix-grouping {
    description
        "Container for all data related to ipfix";
    container ipfix {
        if-feature feature-list:HAVE_SFLOW;
        if-feature feature-list:HAVE_IPFIX;
        description
            "Container for all data related to ipfix";
        uses ipfix-ip-flow-exporters-top;
        uses ipfix-ip-flow-monitors-top;
        uses ipfix-ip-flow-interfaces-top;
    } // END of ipfix-container definition.
    } // END of ipfix-grouping definition.

    uses ipfix-grouping;

}
