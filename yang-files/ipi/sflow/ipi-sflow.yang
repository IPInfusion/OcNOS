/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-sflow.yang
*
*/

module ipi-sflow {

    yang-version 1.1;

    namespace   "http://www.ipinfusion.com/yang/ocnos/ipi-sflow";

    prefix "ipi-sflow";

    import ipi-sflow-types {
        prefix ipi-sflow-types;
        revision-date 2025-03-06;
    }

    import ietf-inet-types {
        prefix inet;
        revision-date 2013-07-15;
    }

    import cml-data-types {
        prefix cml-data-types;
        revision-date 2026-05-15;
    }

    import ipi-network-instance {
        prefix ipi-network-instance;
        revision-date 2026-08-12;
    }

    import ipi-vrf {
        prefix ipi-vrf;
        revision-date 2026-08-12;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "sFlow module provides user with the possibility to configure sFlow
                parameters";


    revision "2025-12-01" {
        description "Added new cli for update-port-pvid for sampled packets";
        reference " 0.14.4.";
    }

    revision "2025-10-11" {
        description "Add CLI to clear history of Dynamic-load-balance events.";
        reference " 0.14.3.";
    }

    revision "2025-10-01" {
        description "Change ordering of 'no sflow collector' command to collector-id, IP, port no.";
        reference " 0.14.2.";
    }

    revision "2025-07-28" {
        description "Fix CLI description for 'no sflow collector-id' command";
        reference " 0.14.1.";
    }

    revision "2025-06-10" {
        description "Modify sample sending behavior to send all samples to all collectors. Add interface configuration to disable collector-ids. Add default values for collector port, receiver-time-out, and max-datagram-size";
        reference " 0.14.0.";
    }

    revision "2025-05-17" {
        description "Change sampling configuration verification";
        reference " 0.13.4.";
    }

    revision "2025-04-07" {
        description "Modify sampling direction CLI submenu level prompt";
        reference " 0.13.3.";
    }

    revision "2025-03-14" {
        description "Add verification to avoid sflow sampling object without meaningful configuration";
        reference " 0.13.1.";
    }

    revision "2025-03-06" {
        description "Change sflow sampling CLI format";
        reference " 0.13.0.";
    }

    revision "2025-03-05" {
        description "Adding access-list log-cache to CoPP access-list";
        reference " 0.13.2.";
    }

    revision "2024-12-04" {
        description "Updating the import of types in sflow-ipfix";
        reference " 0.12.0.";
    }

    revision "2024-06-20" {
        description "Added support to configure global sampling-rate and polling-interval";
        reference " 0.11.0.";
    }

    revision "2024-01-23" {
        description "Added HAVE_VRF flag";
        reference " 0.10.0.";
    }

    revision "2024-01-10" {
        description "Added collector ID attribute";
        reference " 0.9.0.";
    }

    revision "2023-05-29" {
        description "Added When tag for no-debug-all command";
        reference " 0.8.0.";
    }

    revision "2022-11-16" {
        description "Added missing cliprependstr tags";
        reference " 0.7.0.";
    }

    revision "2022-09-30" {
        description "Import cml-data-types used by notifications";
        reference " 0.6.1.";
    }

    revision "2022-08-10" {
        description "Debug hierarchy change";
        reference " 0.6.0.";
    }

    revision "2022-06-01" {
        description "Updated the yang file with feature";
        reference " 0.5.0.";
    }

    revision "2021-09-11" {
        description "Changing sflow container to presence container";
        reference "Initial Version";
    }

    revision "2021-09-03" {
        description "Update descriptions of attribute";
        reference "Initial Version";
    }

    revision "2021-07-30" {
        description "Sflow restructured";
        reference "Initial Version";
    }

    revision "2018-06-21" {
        description "Initial Version";
        reference "Initial Version";
    }

    grouping sflow-debug-terminal-state {
        description
            "sflow-debug-terminal-state";
        leaf terminal-debug-status  {
            type  ipi-sflow-types:sflow_debug_t;
            description "Terminal debug sFlow debug level";
        } // END of terminal-debug-status definition.

    } // END of sflow-debug-terminal-state definition.
    grouping sflow-debug-config {
        description
            "sflow-debug-config";
        leaf options  {
            type  ipi-sflow-types:sflow_debug_t;
            description "Set sFlow debug in config mode";
        } // END of options definition.

    } // END of sflow-debug-config definition.
    grouping sflow-debug-top {
        description
            "sflow-debug-top";
        container debug {
            when " /ipi-sflow:sampling/ipi-sflow:sflow/ipi-sflow:config/ipi-sflow:enabled ";
            description
                "Container for sFlow debug";
            container config {
                description
                    "Container for sFlow debug configuration";
                uses sflow-debug-config;
            } // END of config-container definition.
            container state {
                config false;
                description
                    "Operational state data";
                uses sflow-debug-config;
                uses sflow-debug-terminal-state;
            } // END of state-container definition.
        } // END of debug-container definition.
    } // END of sflow-debug-top definition.
    grouping sflow-logging-config {
        description
            "sflow-logging-config";
        leaf max-entries  {
            type  uint16 {
                 range "1000..10000"  {
                    description "1000..10000: Supported range 1000 - 10000";
                 }
            }
            default "1000";
            description "Specifies the maximum number of log entries that are cached, default
                        is 1000 entries";
        } // END of max-entries definition.

        leaf rate-limit  {
            if-feature feature-list:HAVE_BROADCOM;
            if-feature feature-list:NOT_HAVE_COPP_FILTER;
            type  uint16 {
                 range "0..1000"  {
                    description "0..1000: Supported range 0 - 1000";
                 }
            }
            default "200";
            description "Configures rate limits in packets per second, Default is 200
                        packets/sec";
        } // END of rate-limit definition.

    } // END of sflow-logging-config definition.
    grouping sflow-logging-top {
        description
            "sflow-logging-top";
        container logging {
            if-feature feature-list:HAVE_CUSTOM1_ACL_OR_HAVE_COPP_FILTER;
            description
                "Container of sflow logging info";
            container config {
                description
                    "sFlow logging configuration parameters";
                uses sflow-logging-config;
            } // END of config-container definition.
            container state {
                config false;
                description
                    "sFlow logging state data";
                uses sflow-logging-config;
            } // END of state-container definition.
        } // END of logging-container definition.
    } // END of sflow-logging-top definition.
    grouping sflow-collector-config {
        description
            "sflow-collector-config";
        leaf address  {
            // when " ../max-datagram-size + ../port + ../receiver-timeout ";
            type  inet:ipv4-address;
            description "The IP address of the sFlow collector.If set to 0.0.0.0 no sFlow
                        datagrams will be sent.";
        } // END of address definition.

        leaf port  {
            // when " ../max-datagram-size + ../address + ../receiver-timeout ";
            type  inet:port-number {
                 range "1024..65535"  {
                    description "1024..65535: Supported range 1024 - 65535";
                 }
            }
            description "The destination port for sFlow datagrams.Default port number is 6343.";
        } // END of port definition.

        leaf receiver-timeout  {
            // when " ../port + ../address ";
            type  uint32 {
                 range "0..2147483647"  {
                    description "0..2147483647: Supported range 0 - 2147483647";
                 }
            }
            default "0";
            description "The time (in seconds) remaining before the sampler is released and
                        stops sampling. When set, the owner establishes control for the
                        specified period. When read, the remaining time in the interval is
                        returned.A management entity wanting to maintain control of the
                        sampler is responsible for setting a new value before the old one
                        expires.When the interval expires, the agent is responsible for
                        restoring all other entities in this row to their default values. It
                        must also free all other resources associated with this sFlowRcvrTable
                        entry.";
        } // END of receiver-timeout definition.

        leaf max-datagram-size  {
            // when " ../address + ../port ";
            type  uint16 {
                 range "200..9000"  {
                    description "200..9000: Supported range 200 - 9000";
                 }
            }
            default "1560";
            description "The maximum number of data bytes that can be sent in a single sample
                        datagram. The manager should set this value to avoid fragmentation of
                        the sFlow datagrams.";
        } // END of max-datagram-size definition.

        leaf collector-id  {
            type  uint8 {
                 range "1..5"  {
                    description "1..5: Supported range 1 - 5";
                 }
            }
            description "The ID of the collector to be used (1-5). The default value is 1.";
        } // END of collector-id definition.

        leaf vrf-name  {
            if-feature feature-list:HAVE_VRF;
            type  leafref {
                path  "/ipi-network-instance:network-instances/ipi-network-instance:network-instance/ipi-vrf:vrf/ipi-vrf:config/ipi-vrf:vrf-name";
            }
            mandatory true;
            description "The VRF name from which this collector is reachable.";
        } // END of vrf-name definition.

    } // END of sflow-collector-config definition.
    grouping sflow-collectors-top {
        description
            "sflow-collectors-top";
        container collectors {
            when " /ipi-sflow:sampling/ipi-sflow:sflow/ipi-sflow:config/ipi-sflow:enabled ";
            description
                "sFlow collectors parameters";

            list collector {
                key "address port collector-id";
                max-elements 5;
                description
                    "sFlow collectors parameters";
                leaf address  {
                    type  leafref {
                        path  "../config/address";
                    }
                    description "The IP address of the sFlow collector.If set to 0.0.0.0 no sFlow
                                datagrams will be sent.";
                } // END of address definition.

                leaf port  {
                    type  leafref {
                        path  "../config/port";
                    }
                    description "The destination port for sFlow datagrams.Default port number is 6343.";
                } // END of port definition.

                leaf collector-id  {
                    type  leafref {
                        path  "../config/collector-id";
                    }
                    description "The ID of the collector to be used (1-5). The default value is 1.";
                } // END of collector-id definition.

                container config {
                    description
                        "sFlow collectors configuration parameters";
                    uses sflow-collector-config;
                } // END of config-container definition.
                container state {
                    config false;
                    description
                        "sFlow collectors state data";
                    uses sflow-collector-config;
                } // END of state-container definition.
            } // End of collector-list
        } // END of collectors-container definition.
    } // END of sflow-collectors-top definition.
    grouping sflow-global-sampling-config {
        description
            "sflow-global-sampling-config";
        leaf sampling-direction  {
            type  ipi-sflow-types:sflow_sampling_direction_t;
            description "sflow sampling direction";
        } // END of sampling-direction definition.

        leaf rate  {
            // when " ipi-sflow:sampling/sflow/global/samplings/sampling/config/max-header-size ";
            type  uint32 {
                 range "1024..16777215"  {
                    description "1024..16777215: Supported range 1024 - 16777215";
                 }
            }
            default "16777215";
            description "The statistical sampling rate for packet sampling from this source.
                        Set to N to sample 1/Nth of the packets in the monitored flows.An
                        agent should choose its own algorithm to introduce variance into the
                        sampling so that exactly every Nth packet is not counted. A sampling
                        rateof 1 counts all packets. A sampling rate of 0 disables
                        sampling.The agent is permitted to have minimum and maximum allowable
                        values for the sampling rate. A minimum rate lets the agent designer
                        set an upper bound on the overhead associated with sampling, and a
                        maximum rate may be the result of hardware restrictions (such as
                        counter size). In addition not all values between the maximum and
                        minimum may be realizable as the sampling rate (again because of
                        implementation considerations).When the sampling rate is set the agent
                        is free to adjust the value so that it lies between the maximum and
                        minimum values and has the closest achievable value.When read, the
                        agent must return the actual sampling rate it will be using (after the
                        adjustments previously described). The sampling algorithm must
                        converge so that over time the number of packets sampled approaches
                        1/Nth of the total number of packets in the monitored flows.";
        } // END of rate definition.

        leaf max-header-size  {
            // when " ipi-sflow:sampling/sflow/global/samplings/sampling/config/rate ";
            type  uint16 {
                 range "16..256"  {
                    description "16..256: Supported range 16 - 256";
                 }
            }
            default "16";
            description "The statistical sampling rate for packet sampling from this source.
                        Set to N to sample 1/Nth of the packets in the monitored flows.An
                        agent should choose its own algorithm to introduce variance into the
                        sampling so that exactly every Nth packet is not counted. A sampling
                        rateof 1 counts all packets. A sampling rate of 0 disables
                        sampling.The agent is permitted to have minimum and maximum allowable
                        values for the sampling rate. A minimum rate lets the agent designer
                        set an upper bound on the overhead associated with sampling, and a
                        maximum rate may be the result of hardware restrictions (such as
                        counter size). In addition not all values between the maximum and
                        minimum may be realizable as the sampling rate (again because of
                        implementation considerations).When the sampling rate is set the agent
                        is free to adjust the value so that it lies between the maximum and
                        minimum values and has the closest achievable value.When read, the
                        agent must return the actual sampling rate it will be using (after the
                        adjustments previously described). The sampling algorithm must
                        converge so that over time the number of packets sampled approaches
                        1/Nth of the total number of packets in the monitored flows.";
        } // END of max-header-size definition.

    } // END of sflow-global-sampling-config definition.
    grouping sflow-global-sampling-top {
        description
            "sflow-global-sampling-top";
        container samplings {
            description
                "sflow global configuration for sampling";

            list sampling {
            // when " ipi-sflow:sampling/sflow/global/samplings/sampling/config/rate + ipi-sflow:sampling/sflow/global/samplings/sampling/config/max-header-size ";
                key "sampling-direction";
                description
                    "sflow global configuration for sampling on given direction";
                leaf sampling-direction  {
                    type  leafref {
                        path  "../config/sampling-direction";
                    }
                    description "sflow sampling direction";
                } // END of sampling-direction definition.

                container config {
                    description
                        "Configuration of sflow global configuration for sampling on given
                                direction";
                    uses sflow-global-sampling-config;
                } // END of config-container definition.
                container state {
                    config false;
                    description
                        "Operational state data of sflow global sampling on given direction";
                    uses sflow-global-sampling-config;
                } // END of state-container definition.
            } // End of sampling-list
        } // END of samplings-container definition.
    } // END of sflow-global-sampling-top definition.
    grouping sflow-global-polling-interval-config {
        description
            "sflow-global-polling-interval-config";
        leaf polling-interval  {
            type  uint8 {
                 range "5..60"  {
                    description "5..60: Supported range 5 - 60";
                 }
            }
            description "Configure global polling-interval for packet sampling. The sflow
                        polling-interval configuration on interface overrides the global
                        configuration.";
        } // END of polling-interval definition.

    } // END of sflow-global-polling-interval-config definition.
    grouping sflow-global-update-port-pvid-config {
        description
            "sflow-global-update-port-pvid-config";
        leaf update-port-pvid  {
            type  empty;
            description "Configure enable update-port-pvid for sflow enabled access ports to
                        include vlan in the sampled packets.";
        } // END of update-port-pvid definition.

    } // END of sflow-global-update-port-pvid-config definition.
    grouping sflow-global-configuration-top {
        description
            "sflow-global-configuration-top";
        container global {
            when " /ipi-sflow:sampling/ipi-sflow:sflow/ipi-sflow:config/ipi-sflow:enabled ";
            description
                "sFlow global configuration data";
            container config {
                description
                    "Configuration data for global configuration";
                uses sflow-global-polling-interval-config;
                uses sflow-global-update-port-pvid-config;
            } // END of config-container definition.
            container state {
                config false;
                description
                    "Operational state data for global configuration";
                uses sflow-global-polling-interval-config;
                uses sflow-global-update-port-pvid-config;
            } // END of state-container definition.
            uses sflow-global-sampling-top;
        } // END of global-container definition.
    } // END of sflow-global-configuration-top definition.
    grouping sflow-config {
        description
            "sflow-config";
        leaf enabled  {
            type  empty;
            mandatory true;
            description "Use this attribute to enable or disable Sampled Flow (sFlow) feature
                        globally.";
        } // END of enabled definition.

        leaf source-address  {
            // when " ipi-sflow:sampling/sflow/config/enabled ";
            type  inet:ipv4-address;
            description "The IP address associated with this agent. In the case of a
                        multi-homed agent, this should be the loopback address of the agent.
                        The sFlowAgent address must provide SNMP connectivity to the agent.
                        The address should be an invariant that does not change as interfaces
                        are reconfigured, enabled, disabled,added or removed. A manager should
                        be able to use the sFlowAgentAddress as a unique key that will
                        identify this agent over extended periods of time so that a history
                        can be maintained.";
        } // END of source-address definition.

        leaf cpu-rate-limit  {
            if-feature feature-list:HAVE_BROADCOM;
            if-feature feature-list:NOT_HAVE_DUNE;
            type  uint32 {
                 range "2000..100000"  {
                    description "2000..100000: Supported range 2000 - 100000";
                 }
            }
            units "packets/s";
            description "CPU rate in packets per second";
        } // END of cpu-rate-limit definition.

    } // END of sflow-config definition.
    grouping sflow-state {
        description
            "sflow-state";
        leaf sflow-version  {
            type  string {
                length "1..1965";
                pattern "[^?' =,>|]+";
            }
            description "Uniquely identifies the version and implementation of this MIB.The MIB
                        Version willchange with each revision of the SFLOW MIB.Management
                        entities must check the MIB Version and not attempt to manage agents
                        with MIB Versions greater than that for which they were designed.";
        } // END of sflow-version definition.

        leaf datagram-version  {
            type  uint8;
            description "The version of sFlow datagrams that should be sent.When set to a value
                        not support by the agent, the agent should adjust the value to the
                        highest supported value less than the requested value, or return an
                        SNMP bad value error if no such value exists.";
        } // END of datagram-version definition.

    } // END of sflow-state definition.
    grouping sflow-top {
        description
            "sflow-top";
        container sflow {
            description
                "Container that stores all info about sflow";
            container config {
                presence "Enabling sampling Flow (sFlow) feature globally";
                description
                    "sFlow configuration parameters";
                uses sflow-config;
            } // END of config-container definition.
            container state {
                config false;
                description
                    "sFlow state data";
                uses sflow-config;
                uses sflow-state;
            } // END of state-container definition.
            uses sflow-collectors-top;
            uses sflow-logging-top;
            uses sflow-debug-top;
            uses sflow-global-configuration-top;
        } // END of sflow-container definition.
    } // END of sflow-top definition.

    grouping  sampling-grouping {
    description
        "Container for all data related to samplings";
    container sampling {
        if-feature feature-list:HAVE_SFLOW;
        description
            "Container for all data related to samplings";
        uses sflow-top;
    } // END of sampling-container definition.
    } // END of sampling-grouping definition.

    uses sampling-grouping;

    rpc sflow-clear-access-list-log-cache {
        if-feature feature-list:HAVE_SFLOW;
        if-feature feature-list:HAVE_CUSTOM1_ACL_OR_HAVE_COPP_FILTER;
        description "";
    }

    rpc sflow-terminal-debug-on {
        if-feature feature-list:HAVE_SFLOW;
        description "Enable sFlow debug categories";
        input  {
            leaf terminal-debug-options  {
                type ipi-sflow-types:sflow_debug_t;
                mandatory true;
                description "Bitmap representing sFlow debug categories";
            }
        }
    }

    rpc sflow-terminal-debug-off {
        if-feature feature-list:HAVE_SFLOW;
        description "Disable sFlow debug categories";
        input  {
            leaf terminal-debug-options  {
                type ipi-sflow-types:sflow_debug_t;
                mandatory true;
                description "Bitmap representing sFlow debug categories";
            }
        }
    }

    notification sflow-receiver-timeout-alarm-message {
        if-feature feature-list:HAVE_SFLOW;

        description "Notify alarm message.";

        leaf severity {
            type cml-data-types:cml_notif_severity_t;
            description "Notification severity level (value: MINOR)";
        }

        leaf eventClass {
            type cml-data-types:cml_notif_class_t;
            description "Notification event class (value: MESSAGE)";
        }

        leaf message {
            type string;
            description " alarm message notification";
        }
    }

}
