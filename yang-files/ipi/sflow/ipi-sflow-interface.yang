/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-sflow-interface.yang
*
*/

module ipi-sflow-interface {

    yang-version 1.1;

    namespace   "http://www.ipinfusion.com/yang/ocnos/ipi-sflow-interface";

    prefix "ipi-sflow-interface";

    import ipi-sflow {
        prefix ipi-sflow;
        revision-date 2025-12-01;
    }

    import ipi-sflow-types {
        prefix ipi-sflow-types;
        revision-date 2025-03-06;
    }

    import ipi-interface {
        prefix ipi-interface;
        revision-date 2026-03-10;
    }

    import ietf-yang-types {
        prefix yang;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module provides user with the possibility to configure sflow
                interface parameters";


    revision "2025-08-11" {
        description "Add CLI to clear history of Dynamic-load-balance events.";
        reference " 0.8.2.";
    }

    revision "2025-07-28" {
        description "Fix CLI description for 'no sflow collector-id' command";
        reference " 0.8.1.";
    }

    revision "2025-06-10" {
        description "Modify sample sending behavior to send all samples to all collectors. Add interface configuration to disable collector-ids";
        reference " 0.8.0.";
    }

    revision "2025-05-17" {
        description "Change sampling configuration verification";
        reference " 0.7.4.";
    }

    revision "2025-04-28" {
        description "Add dependency object on interface to control sampling configuration be applied before sflow enable configuration";
        reference " 0.7.3.";
    }

    revision "2025-04-07" {
        description "Modify sampling direction CLI submenu level prompt";
        reference " 0.7.2.";
    }

    revision "2025-03-14" {
        description "Add verification to avoid sflow sampling object without meaningful configuration";
        reference " 0.7.1.";
    }

    revision "2025-03-06" {
        description "Change sflow sampling CLI format";
        reference " 0.7.0.";
    }

    revision "2025-01-09" {
        description "Removed sampling when tag for sflow enable command";
        reference " 0.6.2.";
    }

    revision "2024-12-20" {
        description "Sflow configs should be removed from interface if intra domain link is configured";
        reference " 0.6.1.";
    }

    revision "2024-12-04" {
        description "Updating the import of types in sflow-ipfix";
        reference " 0.6.0.";
    }

    revision "2024-06-20" {
        description "Added support to configure global sampling-rate and polling-interval";
        reference " 0.5.0.";
    }

    revision "2024-01-10" {
        description "Added collector ID attribute";
        reference " 0.4.0.";
    }

    revision "2022-12-01" {
        description "Updated when expressions";
        reference " 0.3.2.";
    }

    revision "2022-08-10" {
        description "Debug hierarchy change";
        reference " 0.3.1.";
    }

    revision "2022-07-30" {
        description "Updated when expressions in yang";
        reference " 0.3.0.";
    }

    revision "2022-06-01" {
        description "Updated the yang file with feature";
        reference " 0.2.0.";
    }

    revision "2021-07-30" {
        description "sFlow restructured";
        reference "Initial Version";
    }

    grouping sflow-interface-sampling-state {
        description
            "sflow-interface-sampling-state";
        leaf sampling-status  {
            type  ipi-sflow-types:sflow_egress_ingress_t;
            description "This leaf indicates the current state of the sampling direction.";
        } // END of sampling-status definition.

        leaf sampled-packet-count  {
            type  yang:counter32;
            description "This leaf is a counter of the sampled packets.";
        } // END of sampled-packet-count definition.

    } // END of sflow-interface-sampling-state definition.
    grouping sflow-interface-sampling-config {
        description
            "sflow-interface-sampling-config";
        leaf sampling-direction  {
            type  ipi-sflow-types:sflow_sampling_direction_t;
            description "sflow sampling direction";
        } // END of sampling-direction definition.

        leaf rate  {
            // when " ipi-sflow-interface:interfaces/interface/samplings/sampling/config/max-header-size ";
            type  uint32 {
                 range "1024..16777215"  {
                    description "1024..16777215: Supported range 1024 - 16777215";
                 }
            }
            default "16777215";
            description "The statistical sampling rate for packet sampling from this source.
                        Set to N to sample 1/Nth of the packets in the monitored flows.An
                        agent should choose its own algorithm to introduce variance into the
                        sampling so that exactly every Nth packet is not counted. A sampling
                        rateof 1 counts all packets. A sampling rate of 0 disables
                        sampling.The agent is permitted to have minimum and maximum allowable
                        values for the sampling rate. A minimum rate lets the agent designer
                        set an upper bound on the overhead associated with sampling, and a
                        maximum rate may be the result of hardware restrictions (such as
                        counter size). In addition not all values between the maximum and
                        minimum may be realizable as the sampling rate (again because of
                        implementation considerations).When the sampling rate is set the agent
                        is free to adjust the value so that it lies between the maximum and
                        minimum values and has the closest achievable value.When read, the
                        agent must return the actual sampling rate it will be using (after the
                        adjustments previously described). The sampling algorithm must
                        converge so that over time the number of packets sampled approaches
                        1/Nth of the total number of packets in the monitored flows.";
        } // END of rate definition.

        leaf max-header-size  {
            // when " ipi-sflow-interface:interfaces/interface/samplings/sampling/config/rate ";
            type  uint16 {
                 range "16..256"  {
                    description "16..256: Supported range 16 - 256";
                 }
            }
            default "16";
            description "The statistical sampling rate for packet sampling from this source.
                        Set to N to sample 1/Nth of the packets in the monitored flows.An
                        agent should choose its own algorithm to introduce variance into the
                        sampling so that exactly every Nth packet is not counted. A sampling
                        rateof 1 counts all packets. A sampling rate of 0 disables
                        sampling.The agent is permitted to have minimum and maximum allowable
                        values for the sampling rate. A minimum rate lets the agent designer
                        set an upper bound on the overhead associated with sampling, and a
                        maximum rate may be the result of hardware restrictions (such as
                        counter size). In addition not all values between the maximum and
                        minimum may be realizable as the sampling rate (again because of
                        implementation considerations).When the sampling rate is set the agent
                        is free to adjust the value so that it lies between the maximum and
                        minimum values and has the closest achievable value.When read, the
                        agent must return the actual sampling rate it will be using (after the
                        adjustments previously described). The sampling algorithm must
                        converge so that over time the number of packets sampled approaches
                        1/Nth of the total number of packets in the monitored flows.";
        } // END of max-header-size definition.

        leaf disabled  {
            type  empty;
            description "This leaf is used to disable sampling on given direction, but it keeps
                        the sFlow feature running on interface.";
        } // END of disabled definition.

    } // END of sflow-interface-sampling-config definition.
    grouping sflow-interface-sampling-top {
        description
            "sflow-interface-sampling-top";
        container samplings {
            description
                "sflow sampling configuration on interface";

            list sampling {
                key "sampling-direction";
                description
                    "sflow sampling on given direction configuration on interface";
                leaf sampling-direction  {
                    type  leafref {
                        path  "../config/sampling-direction";
                    }
                    description "sflow sampling direction";
                } // END of sampling-direction definition.

                container config {
                    description
                        "Configuration data for interface sFlow sampling";
                    uses sflow-interface-sampling-config;
                } // END of config-container definition.
                container state {
                    config false;
                    description
                        "Operational state data for interface sFlow sampling";
                    uses sflow-interface-sampling-config;
                    uses sflow-interface-sampling-state;
                } // END of state-container definition.
            } // End of sampling-list
        } // END of samplings-container definition.
    } // END of sflow-interface-sampling-top definition.
    grouping sflow-interface-state {
        description
            "sflow-interface-state";
        leaf polling-count  {
            type  yang:counter32;
            description "Retrieved from SFLOWPoller";
        } // END of polling-count definition.

        leaf hw-sampling-rate-limit  {
            if-feature feature-list:HAVE_UT;
            if-feature feature-list:HAVE_MARVELL;
            type  uint32;
            description "hw configured sampling rate";
        } // END of hw-sampling-rate-limit definition.

        leaf sampled-packet-count  {
            if-feature feature-list:HAVE_UT;
            if-feature feature-list:HAVE_MARVELL;
            type  yang:counter32;
            description "packet sampled count in the hw";
        } // END of sampled-packet-count definition.

        leaf countdown-count  {
            if-feature feature-list:HAVE_UT;
            if-feature feature-list:HAVE_MARVELL;
            type  yang:counter32;
            description "packet count down information";
        } // END of countdown-count definition.

    } // END of sflow-interface-state definition.
    grouping sflow-interface-config {
        description
            "Grouping for sFlow configuration on interface";
        leaf name  {
            type  leafref {
                path  "/ipi-interface:interfaces/ipi-interface:interface/ipi-interface:name";
            }
            description "Interface name for which sFlow is being configured";
        } // END of name definition.

        leaf enabled  {
            type  empty;
            description "To enable or disable sampling on an interface after giving the sflow
                        sampling-rate command on the same interface, or it can use the global
                        configuration for sampling and polling-interval on this interface.";
        } // END of enabled definition.

        leaf polling-interval  {
            type  uint8 {
                 range "5..60"  {
                    description "5..60: Supported range 5 - 60";
                 }
            }
            description "The maximum number of seconds between successive samples of the
                        counters associated with this data source. A sampling interval of 0
                        disables counter sampling.The agent is permitted to have minimum and
                        maximum allowable values for the counter polling interval. A minimum
                        interval lets the agent designer set an upper bound on the overhead
                        associated with polling, anda maximum interval may be the result of
                        implementation restrictions (such as counter size).In addition notall
                        values between the maximum and minimum may be realizable as the
                        sampling interval (again because of implementation
                        considerations).When the sampling rate is set the agent is free to
                        adjust the value so that it lies between the maximum and minimum
                        values and has the closest achievable value.When read, the agent must
                        return the actual sampling interval it will be using (after the
                        adjustments previously described).The sampling algorithm must converge
                        so that over time the number of packets sampledapproaches 1/Nth of the
                        total number of packets in the monitored flows.";
        } // END of polling-interval definition.

        leaf-list disable-collector-id  {
            type  uint8 {
                 range "1..5"  {
                    description "1..5: Supported range 1 - 5";
                 }
            }
            description "Disable a collector id to the interface so that no sflow data from
                        this interface is sent to it.";
        } // END of disable-collector-id definition.

    } // END of sflow-interface-config definition.

    grouping  interfaces-grouping {
    description
        "Configuration data for interface sFlow";
    container interfaces {
        if-feature feature-list:HAVE_SFLOW;
        description
            "Configuration data for interface sFlow";

        list interface {
            key "name";
            description
                "Configuration data list for interface sFlow";
            leaf name  {
                type  leafref {
                    path  "../config/name";
                }
                description "Interface name for which sFlow is being configured";
            } // END of name definition.

            container config {
                description
                    "Configuration data for interface sFlow";
                uses sflow-interface-config;
            } // END of config-container definition.
            container state {
                config false;
                description
                    "Operational state data for interface sFlow";
                uses sflow-interface-config;
                uses sflow-interface-state;
            } // END of state-container definition.
            uses sflow-interface-sampling-top;
        } // End of interface-list
    } // END of interfaces-container definition.
    } // END of interfaces-grouping definition.

    augment /ipi-sflow:sampling/ipi-sflow:sflow {
    when " /ipi-sflow:sampling/ipi-sflow:sflow/ipi-sflow:config/ipi-sflow:enabled ";
        if-feature feature-list:HAVE_SFLOW;
        description
            "Configuration data for interface sFlow";
        uses interfaces-grouping;
    }


    rpc sflow-clear-statistics {
        if-feature feature-list:HAVE_SFLOW;
        description "Use to clear all sFlow statistics from a specific interface";
        input  {
            leaf interface  {
                type string;
                mandatory true;
                description "Interface name for which sFlow statistics will be cleaned";
            }
        }
    }

    rpc clear-dynamic-load-balance-monitor-events {
        if-feature feature-list:HAVE_SFLOW;
        description "Use to clear all dynamic-load-balance monitor events in sflow";
    }

}
