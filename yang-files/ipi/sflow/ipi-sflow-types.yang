/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-sflow-types.yang
*
*/

module ipi-sflow-types {

    yang-version 1.1;

    namespace   "http://www.ipinfusion.com/yang/ocnos/ipi-sflow-types";

    prefix "ipi-sflow-types";

    organization
        "IP Infusion Inc.";

    contact
        "Address: 3965 Freedom Circle, Suite 200, Santa Clara, CA 95054
         Phone: +1 408-400-1900
         E-mail: support@ipinfusion.com
         Web: http://www.ipinfusion.com/";

    description
        "sflow datatypes";


    revision "2025-03-06" {
        description "Change sflow sampling CLI format";
        reference " 0.6.0.";
    }

    revision "2024-12-04" {
        description "Add a new type for samples-per-message";
        reference " 0.5.0.";
    }

    revision "2022-08-10" {
        description "Debug hierarchy change";
        reference " 0.4.0.";
    }

    revision "2022-06-01" {
        description "Updated the yang file with feature";
        reference " 0.3.0.";
    }

    revision "2021-09-03" {
        description "Update descriptions of attribute";
        reference "Initial Version";
    }

    revision "2021-07-30" {
        description "Sflow restructured";
        reference "Initial Version";
    }



    typedef  sflow_debug_t {
        type bits {
            bit agent {
                position 0;
                description "debug sflow agent";
            }
            bit sampling {
                position 1;
                description "debug sflow sampling";
            }
            bit polling {
                position 2;
                description "debug sflow polling";
            }
        }
        description "type definition for SFLOW_DEBUG_T";
    }

    typedef  sflow_egress_ingress_t {
        type enumeration {
            enum disabled {
                value 0;
                description "Disable Egress/Ingress";
            }
            enum enabled {
                value 1;
                description "Enable Egress/Ingress";
            }
        }
        description "type definition for SFLOW_EGRESS_INGRESS_T";
    }

    typedef  sflow_samples_per_message_t {
        type enumeration {
            enum 1 {
                value 1;
                description "Value 1";
            }
            enum 8 {
                value 8;
                description "Value 8";
            }
        }
        description "type definition for SFLOW_SAMPLES_PER_MESSAGE_T";
    }

    typedef  sflow_sampling_direction_t {
        type enumeration {
            enum ingress {
                value 1;
                description "sflow sampling on ingress direction";
            }
            enum egress {
                value 2;
                description "sflow sampling on egress direction";
            }
        }
        description "type definition for SFLOW_SAMPLING_DIRECTION_T";
    }

}
