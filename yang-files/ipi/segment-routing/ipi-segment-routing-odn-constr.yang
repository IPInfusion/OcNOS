/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-segment-routing-odn-constr.yang
*
*/

submodule ipi-segment-routing-odn-constr {

    yang-version 1.1;

    belongs-to  ipi-segment-routing { prefix ipi-segment-routing; }

    import feature-list {
        prefix feature-list;
        revision-date 2026-09-15;
    }

    import ipi-sr-types {
        prefix ipi-sr-types;
        revision-date 2024-12-09;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Segment-routing ODN extended constraints configurations";


    revision "2024-12-05" {
        description "Changed EAG, SRLG, Segment-Rule and Disjoint-Path to hidden";
        reference " 0.1.2.";
    }

    revision "2024-06-25" {
        description "Unhide the SR-policy Algorithm parameter";
        reference " 0.1.1.";
    }

    revision "2024-04-20" {
        description "Added SRLG group(s) required in SR-Policy dynamic-CP constraints";
        reference " 0.1.0.";
    }

    grouping affinity-admin-group-properties-config {
        description
            "Configuration parameters for admin group";
        leaf affinity-type  {
            type  ipi-sr-types:sr_te_admin_group_type_t;
            description "Use this attribute to configure the type is include-any or include-all
                        or exclude-any";
        } // END of affinity-type definition.

        leaf admin-group-name  {
            type  string {
                length "1..1965";
                pattern "[^?' =,>|]+";
            }
            description "Affinity admin-group name";
        } // END of admin-group-name definition.

    } // END of affinity-admin-group-properties-config definition.
    grouping affinity-extended-admin-group-properties-config {
        description
            "Configuration parameters for extended-admin group";
        leaf extended-admin-affinity-type  {
            type  ipi-sr-types:sr_te_extended_admin_group_type_t;
            description "Use this attribute to configure the type is include-any or include-all
                        or exclude-any";
        } // END of extended-admin-affinity-type definition.

        leaf extended-admin-group-name  {
            type  string {
                length "1..1965";
                pattern "[^?' =,>|]+";
            }
            description "Affinity extended-admin-group name";
        } // END of extended-admin-group-name definition.

    } // END of affinity-extended-admin-group-properties-config definition.
    grouping odn-srlg-group-config {
        description
            "configuration parameters for srlg group";
        leaf srlg-affinity-type  {
            type  ipi-sr-types:sr_te_srlg_affinity_type_t;
            description "Use this attribute to configure the type is include-any or include-all
                        or exclude-any";
        } // END of srlg-affinity-type definition.

        leaf srlg-group-name  {
            type  string {
                length "1..1965";
                pattern "[^?' =,>|]+";
            }
            description "SRLG group name";
        } // END of srlg-group-name definition.

    } // END of odn-srlg-group-config definition.
    grouping odn-include-ip-constraints-config {
        description
            "Ip addresses to be included as constraints for the dynamic path";
        leaf address  {
            type  inet:ip-address;
            description "Hop address which needs to be included in the LSP";
        } // END of address definition.

        leaf type  {
            type  ipi-sr-types:srte_ip_constraint_hop_type_t;
            description "Type of the constraints whether it is node or loose or it is a link or
                        strict, It is highly recomeneded to use strict fro link constraint";
        } // END of type definition.

    } // END of odn-include-ip-constraints-config definition.
    grouping odn-ip-hop-address-filter-constraints-config {
        description
            "IP hop addresses to be included/excluded as constraints for the
                        dynamic path";
        leaf ihaf-affinity-type  {
            type  ipi-sr-types:srte_ip_constraint_hop_filter_type_t;
            description "Type of the constraints whether the hop with IP address to be included
                        or excluded";
        } // END of ihaf-affinity-type definition.

        leaf ihaf-address  {
            type  inet:ip-address;
            description "IP Hop address which needs to be included/excluded in the LSP path";
        } // END of ihaf-address definition.

    } // END of odn-ip-hop-address-filter-constraints-config definition.
    grouping odn-dyn-cp-segment-rule-config {
        description
            "Configuration to change to dynamic-CP segment-rule mode";
        leaf enable  {
            type  empty;
            mandatory true;
            description "Enable segment constraints for the dynamic candidate path";
        } // END of enable definition.

    } // END of odn-dyn-cp-segment-rule-config definition.
    grouping odn-dyn-cp-cons-segrule-parameters-config {
        description
            "grouping for the properties of SR-policy dynamic CP segment properties";
        leaf dataplane-type  {
            type  ipi-sr-types:sr_dyn_cp_dataplane_type_t;
            description "SR policy dynamic candidate path's data-plane type";
        } // END of dataplane-type definition.

        leaf sid-algorithm  {
            type  uint32 {
                 range "128..255"  {
                    description "128..255: Supported range 128 - 255";
                 }
            }
            description "Flexible Algorithm Number";
        } // END of sid-algorithm definition.

        leaf protection-type  {
            type  ipi-sr-types:sr_dyn_cp_protection_type_t;
            description "SR policy dynamic candidate path's protection type";
        } // END of protection-type definition.

    } // END of odn-dyn-cp-cons-segrule-parameters-config definition.
    grouping odn-dyn-cp-cons-disjoint-path-config {
        description
            "grouping for the properties of SR-policy dynamic CP path disjointness
                        constraints";
        leaf group-id  {
            type  uint32 {
                 range "1..65535"  {
                    description "1..65535: Supported range 1 - 65535";
                 }
            }
            description "Disjoint path group id";
        } // END of group-id definition.

        leaf disjoint-type  {
            type  ipi-sr-types:sr_dyn_cp_disjoint_path_type_t;
            description "SR policy dynamic candidate path's disjointness type";
        } // END of disjoint-type definition.

        leaf sub-id  {
            type  uint32 {
                 range "1..65535"  {
                    description "1..65535: Supported range 1 - 65535";
                 }
            }
            description "Disjoint path sub-group id";
        } // END of sub-id definition.

    } // END of odn-dyn-cp-cons-disjoint-path-config definition.
    grouping odn-affinity-admin-group-constraints-top {
        description
            "Top level SRLG constraints group";
        container affinity-admin-groups {
            // when " ipi-segment-routing-odn:on-demand-nexthops/on-demand-nexthop/candidate-paths/candidate-path/dynamic/constraints/config ";
            description
                "CP constraint admin-group";

            list affinity-admin-group {
                if-feature feature-list:HAVE_SR_POLICY;
                key "admin-group-name";
                description
                    "list of affinity admin group";
                leaf admin-group-name  {
                    type  leafref {
                        path  "../config/admin-group-name";
                    }
                    description "admin group name";
                } // END of admin-group-name definition.

                container config {
                    description
                        "configuration container for affinity admin group";
                    uses affinity-admin-group-properties-config;
                } // END of config-container definition.
                container state {
                    config false;
                    description
                        "state container for admin group";
                    uses affinity-admin-group-properties-config;
                } // END of state-container definition.
            } // End of affinity-admin-group-list
        } // END of affinity-admin-groups-container definition.
    } // END of odn-affinity-admin-group-constraints-top definition.
    grouping odn-affinity-extended-admin-group-constraints-top {
        description
            "Top level Extended Admin Group constraints group";
        container affinity-extended-admin-groups {
            // when " ipi-segment-routing-odn:on-demand-nexthops/on-demand-nexthop/candidate-paths/candidate-path/dynamic/constraints/config ";
            description
                "CP constraint extended-admin-group";

            list affinity-extended-admin-group {
                if-feature feature-list:HAVE_SR_POLICY;
                key "extended-admin-group-name";
                description
                    "list of affinity extended-admin group";
                leaf extended-admin-group-name  {
                    type  leafref {
                        path  "../config/extended-admin-group-name";
                    }
                    description "extended-admin group name";
                } // END of extended-admin-group-name definition.

                container config {
                    description
                        "configuration container for affinity extended-admin group";
                    uses affinity-extended-admin-group-properties-config;
                } // END of config-container definition.
                container state {
                    config false;
                    description
                        "state container for extended-admin group";
                    uses affinity-extended-admin-group-properties-config;
                } // END of state-container definition.
            } // End of affinity-extended-admin-group-list
        } // END of affinity-extended-admin-groups-container definition.
    } // END of odn-affinity-extended-admin-group-constraints-top definition.
    grouping odn-srlg-group-constraints-top {
        description
            "Top level SRLG constraints group";
        container srlg-groups {
            // when " ipi-segment-routing-odn:on-demand-nexthops/on-demand-nexthop/candidate-paths/candidate-path/dynamic/constraints/config ";
            if-feature feature-list:HAVE_SR_POLICY_OR_HAVE_PCEP_SRV6;
            description
                "CP constraint srlg-group";

            list srlg-group {
                if-feature feature-list:HAVE_SR_POLICY_OR_HAVE_PCEP_SRV6;
                key "srlg-group-name";
                description
                    "list of SRLG group";
                leaf srlg-group-name  {
                    type  leafref {
                        path  "../config/srlg-group-name";
                    }
                    description "SRLG group name";
                } // END of srlg-group-name definition.

                container config {
                    description
                        "configuration container for SRLG group";
                    uses odn-srlg-group-config;
                } // END of config-container definition.
                container state {
                    config false;
                    description
                        "state container for SRLG group";
                    uses odn-srlg-group-config;
                } // END of state-container definition.
            } // End of srlg-group-list
        } // END of srlg-groups-container definition.
    } // END of odn-srlg-group-constraints-top definition.
    grouping odn-ip-hop-constraints-top {
        description
            "Top level IP hop loose/strict constraints group";
        container ip {
            description
                "IP constraints to be used for dynamic candidate path";
            container include-hops {
                description
                    "include-hops container";

                list include-hop {
                    key "address";
                    description
                        "All the ip constriants should be  included for the path computation";
                    leaf address  {
                        type  leafref {
                            path  "../config/address";
                        }
                        description "Hop address which needs toincluded in the LSP";
                    } // END of address definition.

                    container config {
                        description
                            "include-hop config container";
                        uses odn-include-ip-constraints-config;
                    } // END of config-container definition.
                    container state {
                        config false;
                        description
                            "include-hop state container";
                        uses odn-include-ip-constraints-config;
                    } // END of state-container definition.
                } // End of include-hop-list
            } // END of include-hops-container definition.
        } // END of ip-container definition.
    } // END of odn-ip-hop-constraints-top definition.
    grouping odn-ip-hop-address-filter-constraints-top {
        description
            "Top level IP hop address include/exclude filter constraints group";
        container ip-address-filters {
            description
                "IP address filter include/exclude constraints to be used for dynamic
                        candidate path";

            list ip-address-filter {
                key "ihaf-address";
                description
                    "All the IP address include/exclude constraints that are required for
                                the path computation";
                leaf ihaf-address  {
                    type  leafref {
                        path  "../config/ihaf-address";
                    }
                    description "IP Hop address which needs to be included/excluded in the LSP path";
                } // END of ihaf-address definition.

                container config {
                    description
                        "IP address filtering config container";
                    uses odn-ip-hop-address-filter-constraints-config;
                } // END of config-container definition.
                container state {
                    config false;
                    description
                        "IP address filtering state container";
                    uses odn-ip-hop-address-filter-constraints-config;
                } // END of state-container definition.
            } // End of ip-address-filter-list
        } // END of ip-address-filters-container definition.
    } // END of odn-ip-hop-address-filter-constraints-top definition.
    grouping odn-dyn-cp-cons-segrule-property {
        description
            "grouping for the properties of SR-policy dynamic CP segment properties";
        container property {
            description
                "Segment constraints for candidate path which needs to be satisfied by
                        computation engine when calculating a segment-list for the dynamic-CP";
            container config {
                presence "yes";
                description
                    "constraint segment property config container";
                uses odn-dyn-cp-cons-segrule-parameters-config;
            } // END of config-container definition.
            container state {
                config false;
                description
                    "constraint segment property state container";
                uses odn-dyn-cp-cons-segrule-parameters-config;
            } // END of state-container definition.
        } // END of property-container definition.
    } // END of odn-dyn-cp-cons-segrule-property definition.
    grouping odn-dyn-cp-cons-segrule-top {
        description
            "grouping for SR-policy dynamic CP constraints segment-rule top-level";
        container segment-rule {
            // when " ipi-segment-routing-odn:on-demand-nexthops/on-demand-nexthop/candidate-paths/candidate-path/dynamic/constraints/segment-rule/config/enable ";
            description
                "Segment-rule constraints for candidate path which needs to be
                        satisfied by computation engine when calculating a segment-list for
                        the dynamic-CP";
            container config {
                presence "yes";
                description
                    "constraint segment-rule config container";
                uses odn-dyn-cp-segment-rule-config;
            } // END of config-container definition.
            container state {
                config false;
                description
                    "constraint segment-rule state container";
                uses odn-dyn-cp-segment-rule-config;
            } // END of state-container definition.
            uses odn-dyn-cp-cons-segrule-property;
        } // END of segment-rule-container definition.
    } // END of odn-dyn-cp-cons-segrule-top definition.
    grouping odn-dyn-cp-cons-disjoint-path-top {
        description
            "Top Level grouping for the SR-policy dynamic CP disjointness
                        properties";
        container disjoint-paths {
            // when " ipi-segment-routing-odn:on-demand-nexthops/on-demand-nexthop/candidate-paths/candidate-path/dynamic/constraints/disjoint-paths/disjoint-path/config/sub-id ";
            description
                "Disjointness constraints for dynamic candidate path, to be satisfied
                        during path calculation";

            list disjoint-path {
                key "group-id disjoint-type";
                description
                    "list of disjoint path";
                leaf group-id  {
                    type  leafref {
                        path  "../config/group-id";
                    }
                    description "Disjoint path group id";
                } // END of group-id definition.

                leaf disjoint-type  {
                    type  leafref {
                        path  "../config/disjoint-type";
                    }
                    description "SR policy dynamic candidate path's disjointness type";
                } // END of disjoint-type definition.

                container config {
                    presence "yes";
                    description
                        "constraint path-disjointness config container";
                    uses odn-dyn-cp-cons-disjoint-path-config;
                } // END of config-container definition.
                container state {
                    config false;
                    description
                        "constraint path-disjointness state container";
                    uses odn-dyn-cp-cons-disjoint-path-config;
                } // END of state-container definition.
            } // End of disjoint-path-list
        } // END of disjoint-paths-container definition.
    } // END of odn-dyn-cp-cons-disjoint-path-top definition.


}
