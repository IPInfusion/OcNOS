/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-srv6-flxalg.yang
*
*/

submodule ipi-srv6-flxalg {

    yang-version 1.1;

    belongs-to  ipi-segment-routing { prefix ipi-segment-routing; }

    import feature-list {
        prefix feature-list;
        revision-date 2026-09-15;
    }

    import ipi-sr-types {
        prefix ipi-sr-types;
        revision-date 2024-12-09;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Segment-routing configurations for SRv6 Segments with Flexible
                Algorithms";


    revision "2024-03-09" {
        description "Updated for dependency revisions";
        reference " 0.1.2.";
    }

    revision "2024-03-05" {
        description "Filled-in all empty help strings";
        reference " 0.1.1.";
    }

    revision "2023-09-29" {
        description "Initial release of SRv6 Segment Routing with Flexible Algorithm";
        reference " 0.1.0.";
    }

    grouping segment-type-9-properties-common-config {
        description
            "Common properties of segment which includes it's index value and it's
                        type.";
        leaf segment-index  {
            type  uint32 {
                 range "1..65545"  {
                    description "1..65545: Supported range 1 - 65545";
                 }
            }
            description "Index of the segment through which it can be modified or unconfigured";
        } // END of segment-index definition.

        leaf type  {
            type  ipi-sr-types:srte_segment_type_9_srv6_t;
            description "Type of the segment";
        } // END of type definition.

        leaf prefix  {
            type  inet:ipv6-address;
            description "IPv6 Prefix";
        } // END of prefix definition.

    } // END of segment-type-9-properties-common-config definition.
    grouping segment-type-10-properties-common-config {
        description
            "Common properties of segment which includes it's index value and it's
                        type.";
        leaf segment-index  {
            type  uint32 {
                 range "1..65545"  {
                    description "1..65545: Supported range 1 - 65545";
                 }
            }
            description "Index of the segment through which it can be modified or unconfigured";
        } // END of segment-index definition.

        leaf type  {
            type  ipi-sr-types:srte_segment_type_10_srv6_t;
            description "Type of the segment";
        } // END of type definition.

    } // END of segment-type-10-properties-common-config definition.
    grouping segment-type-11-properties-common-config {
        description
            "Common properties of segment which includes it's index value and it's
                        type.";
        leaf segment-index  {
            type  uint32 {
                 range "1..65545"  {
                    description "1..65545: Supported range 1 - 65545";
                 }
            }
            description "Index of the segment through which it can be modified or unconfigured";
        } // END of segment-index definition.

        leaf type  {
            type  ipi-sr-types:srte_segment_type_11_srv6_t;
            description "Type of the segment";
        } // END of type definition.

        leaf local-ipv6-address  {
            type  inet:ipv6-address;
            description "IPv6 Prefix for local endpoint";
        } // END of local-ipv6-address definition.

        leaf remote-ipv6-address  {
            type  inet:ipv6-address;
            description "IPv6 Prefix for remote endpoint";
        } // END of remote-ipv6-address definition.

    } // END of segment-type-11-properties-common-config definition.
    grouping segment-type-9-properties-specific-config {
        description
            "grouping for the properties of segment type 9";
        leaf algorithm-num  {
            type  ipi-sr-types:sr_algo_choice_t;
            description "SR-Algorithm Number";
        } // END of algorithm-num definition.

    } // END of segment-type-9-properties-specific-config definition.
    grouping segment-type-10-properties-specific-config {
        description
            "grouping for the properties of segment type 10";
        leaf local-ipv6-address  {
            if-feature feature-list:HAVE_SRV6;
            type  inet:ipv6-address;
            description "IPv6 Prefix for local endpoint";
        } // END of local-ipv6-address definition.

        leaf local-interface-id  {
            if-feature feature-list:HAVE_SRV6;
            type  uint32;
            description "Interface ID for local endpoint";
        } // END of local-interface-id definition.

        leaf remote-ipv6-address  {
            if-feature feature-list:HAVE_SRV6;
            type  inet:ipv6-address;
            description "IPv6 Prefix for remote endpoint";
        } // END of remote-ipv6-address definition.

        leaf remote-interface-id  {
            if-feature feature-list:HAVE_SRV6;
            type  uint32;
            description "Interface ID for remote endpoint";
        } // END of remote-interface-id definition.

        leaf algorithm-num  {
            type  ipi-sr-types:sr_algo_choice_t;
            description "SR-Algorithm Number";
        } // END of algorithm-num definition.

    } // END of segment-type-10-properties-specific-config definition.
    grouping segment-type-11-properties-specific-config {
        description
            "grouping for the properties of segment type 11";
        leaf algorithm-num  {
            type  ipi-sr-types:sr_algo_choice_t;
            description "SR-Algorithm Number";
        } // END of algorithm-num definition.

    } // END of segment-type-11-properties-specific-config definition.
    grouping segment-type-9-definitions {
        description
            "grouping for Segment-Type-9 Definitions";

        list segment-v6-type-9 {
            key "segment-index type prefix";
            description
                "Properties of a type-9 segment";
            leaf segment-index  {
                type  leafref {
                    path  "../config/segment-index";
                }
                description "Index of the segment through which it can be modified or unconfigured";
            } // END of segment-index definition.

            leaf type  {
                type  leafref {
                    path  "../config/type";
                }
                description "Type of the segment";
            } // END of type definition.

            leaf prefix  {
                type  leafref {
                    path  "../config/prefix";
                }
                description "IPv6 Prefix of the segment";
            } // END of prefix definition.

            container config {
                description
                    "Contains config parameters for configuring segment index and type";
                uses segment-type-9-properties-common-config;
            } // END of config-container definition.
            container state {
                config false;
                description
                    "Contains operational information about segment index and type";
                uses segment-type-9-properties-common-config;
            } // END of state-container definition.
            container segment-type-9 {
                description
                    "Segment declared by IPv6 Prefix and optional SR Algorithm";
                container config {
                    description
                        "Contains parameters to configure segment-type-9";
                    uses segment-type-9-properties-specific-config;
                } // END of config-container definition.
                container state {
                    config false;
                    description
                        "Contains operational information regarding segment-type-9";
                    uses segment-type-9-properties-specific-config;
                } // END of state-container definition.
            } // END of segment-type-9-container definition.
        } // End of segment-v6-type-9-list
    } // END of segment-type-9-definitions definition.
    grouping segment-type-10-definitions {
        description
            "grouping for Segment-Type-10 Definitions";

        list segment-v6-type-10 {
            key "segment-index type local-ipv6-address local-interface-id remote-ipv6-address remote-interface-id";
            description
                "Properties of a type-10 segment";
            leaf segment-index  {
                type  leafref {
                    path  "../config/segment-index";
                }
                description "Index of the segment through which it can be modified or unconfigured";
            } // END of segment-index definition.

            leaf type  {
                type  leafref {
                    path  "../config/type";
                }
                description "Type of the segment";
            } // END of type definition.

            leaf local-ipv6-address  {
                type  leafref {
                    path  "../config/local-ipv6-address";
                }
                description "Local end-point IPv6 address of the segment";
            } // END of local-ipv6-address definition.

            leaf local-interface-id  {
                type  leafref {
                    path  "../config/local-interface-id";
                }
                description "Local end-point Interface ID of the segment";
            } // END of local-interface-id definition.

            leaf remote-ipv6-address  {
                type  leafref {
                    path  "../config/remote-ipv6-address";
                }
                description "Local IPv6 address of the segment";
            } // END of remote-ipv6-address definition.

            leaf remote-interface-id  {
                type  leafref {
                    path  "../config/remote-interface-id";
                }
                description "Local end-point Interface ID of the segment";
            } // END of remote-interface-id definition.

            container config {
                description
                    "Contains config parameters for configuring segment index and type";
                uses segment-type-10-properties-common-config;
            } // END of config-container definition.
            container state {
                config false;
                description
                    "Contains operational information about segment index and type";
                uses segment-type-10-properties-common-config;
            } // END of state-container definition.
            container segment-type-10 {
                description
                    "Segment declared by IPv6 Address and Interface ID for local and remote
                            end-point pair with optional SR Algorithm";
                container config {
                    description
                        "Contains parameters to configure segment-type-10";
                    uses segment-type-10-properties-specific-config;
                } // END of config-container definition.
                container state {
                    config false;
                    description
                        "Contains operational information regarding segment-type-10";
                    uses segment-type-10-properties-specific-config;
                } // END of state-container definition.
            } // END of segment-type-10-container definition.
        } // End of segment-v6-type-10-list
    } // END of segment-type-10-definitions definition.
    grouping segment-type-11-definitions {
        description
            "grouping for Segment-Type-11 Definitions";

        list segment-v6-type-11 {
            key "segment-index type local-ipv6-address remote-ipv6-address";
            description
                "Properties of a type-11 segment";
            leaf segment-index  {
                type  leafref {
                    path  "../config/segment-index";
                }
                description "Index of the segment through which it can be modified or unconfigured";
            } // END of segment-index definition.

            leaf type  {
                type  leafref {
                    path  "../config/type";
                }
                description "Type of the segment";
            } // END of type definition.

            leaf local-ipv6-address  {
                type  leafref {
                    path  "../config/local-ipv6-address";
                }
                description "Local end-point IPv6 address of the segment";
            } // END of local-ipv6-address definition.

            leaf remote-ipv6-address  {
                type  leafref {
                    path  "../config/remote-ipv6-address";
                }
                description "Local IPv6 address of the segment";
            } // END of remote-ipv6-address definition.

            container config {
                description
                    "Contains config parameters for configuring segment index and type";
                uses segment-type-11-properties-common-config;
            } // END of config-container definition.
            container state {
                config false;
                description
                    "Contains operational information about segment index and type";
                uses segment-type-11-properties-common-config;
            } // END of state-container definition.
            container segment-type-11 {
                description
                    "Segment declared by IPv6 Address for local and remote end-point pair
                            with optional SR Algorithm";
                container config {
                    description
                        "Contains parameters to configure segment-type-11";
                    uses segment-type-11-properties-specific-config;
                } // END of config-container definition.
                container state {
                    config false;
                    description
                        "Contains operational information regarding segment-type-11";
                    uses segment-type-11-properties-specific-config;
                } // END of state-container definition.
            } // END of segment-type-11-container definition.
        } // End of segment-v6-type-11-list
    } // END of segment-type-11-definitions definition.


}
