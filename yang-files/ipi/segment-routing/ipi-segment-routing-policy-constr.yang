/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-segment-routing-policy-constr.yang
*
*/

submodule ipi-segment-routing-policy-constr {

    yang-version 1.1;

    belongs-to  ipi-segment-routing { prefix ipi-segment-routing; }

    import feature-list {
        prefix feature-list;
        revision-date 2026-09-15;
    }

    import ipi-sr-types {
        prefix ipi-sr-types;
        revision-date 2024-12-09;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Segment-routing Policy extended constraints configurations";


    revision "2024-12-05" {
        description "Changed SR-Policy dynamic-CP EAG, SRLG and IP-Gop-Filter constraints to hidden";
        reference " 0.1.1.";
    }

    revision "2024-04-20" {
        description "Added SRLG group(s) required in SR-Policy dynamic-CP constraints";
        reference " 0.1.0.";
    }

    grouping weighted-segment-list-config {
        description
            "config attributes for segment list";
        leaf list-name  {
            type  string {
                length "1..1965";
                pattern "[^?' =,>|]+";
            }
            description "Segment-list name";
        } // END of list-name definition.

    } // END of weighted-segment-list-config definition.
    grouping affinity-config {
        description
            "affinity constraints for the dynamic candidate path";
        leaf-list exclude-any  {
            type  string {
                length "1..1965";
                pattern "[^?' =,>|]+";
            }
            description "The link is excluded if it has any of these affinities.";
        } // END of exclude-any definition.

        leaf-list include-any  {
            type  string {
                length "1..1965";
                pattern "[^?' =,>|]+";
            }
            description "The link is accepted if it has any of these affinities.";
        } // END of include-any definition.

        leaf-list include-all  {
            type  string {
                length "1..1965";
                pattern "[^?' =,>|]+";
            }
            description "The link is accepted if it has all these affinities.";
        } // END of include-all definition.

    } // END of affinity-config definition.
    grouping admin-group-config {
        description
            "configuration parameters for admin group";
        leaf affinity-type  {
            type  ipi-sr-types:sr_te_admin_group_type_t;
            description "Use this attribute to configure the type is include-any or include-all
                        or exclude-any";
        } // END of affinity-type definition.

        leaf admin-group-name  {
            type  string {
                length "1..1965";
                pattern "[^?' =,>|]+";
            }
            description "Affinity admin-group name";
        } // END of admin-group-name definition.

    } // END of admin-group-config definition.
    grouping extended-admin-group-config {
        description
            "configuration parameters for extended-admin-group";
        leaf extended-admin-affinity-type  {
            type  ipi-sr-types:sr_te_extended_admin_group_type_t;
            description "Use this attribute to configure the type is include-any or include-all
                        or exclude-any";
        } // END of extended-admin-affinity-type definition.

        leaf extended-admin-group-name  {
            type  string {
                length "1..1965";
                pattern "[^?' =,>|]+";
            }
            description "Affinity extended-admin-group name";
        } // END of extended-admin-group-name definition.

    } // END of extended-admin-group-config definition.
    grouping srlg-group-config {
        description
            "configuration parameters for srlg group";
        leaf srlg-affinity-type  {
            type  ipi-sr-types:sr_te_srlg_affinity_type_t;
            description "Use this attribute to configure the type is include-any or include-all
                        or exclude-any";
        } // END of srlg-affinity-type definition.

        leaf srlg-group-name  {
            type  string {
                length "1..1965";
                pattern "[^?' =,>|]+";
            }
            description "SRLG group name";
        } // END of srlg-group-name definition.

    } // END of srlg-group-config definition.
    grouping include-ip-constraints-config {
        description
            "Ip addresses to be included as constraints for the dynamic path";
        leaf address  {
            type  inet:ip-address;
            description "Hop address which needs to be included in the LSP";
        } // END of address definition.

        leaf type  {
            type  ipi-sr-types:srte_ip_constraint_hop_type_t;
            description "Type of the constraints whether it is node or loose or it is a link or
                        strict, It is highly recomeneded to use strict fro link constraint";
        } // END of type definition.

    } // END of include-ip-constraints-config definition.
    grouping ip-hop-address-filter-constraints-config {
        description
            "IP hop addresses to be included/excluded as constraints for the
                        dynamic path";
        leaf ihaf-affinity-type  {
            type  ipi-sr-types:srte_ip_constraint_hop_filter_type_t;
            description "Type of the constraints whether the hop with IP address to be included
                        or excluded";
        } // END of ihaf-affinity-type definition.

        leaf ihaf-address  {
            type  inet:ip-address;
            description "IP Hop address which needs to be included/excluded in the LSP path";
        } // END of ihaf-address definition.

    } // END of ip-hop-address-filter-constraints-config definition.
    grouping admin-group-constraints-top {
        description
            "Top level Admin-group constraints group";
        container admin-groups {
            // when " ipi-segment-routing:segment-routing/traffic-engineering/policies/policy/candidate-paths/candidate-path/dynamic/constraints/config ";
            if-feature feature-list:HAVE_SR_POLICY_OR_HAVE_PCEP_SRV6;
            description
                "CP constraint admin-group";

            list admin-group {
                if-feature feature-list:HAVE_SR_POLICY_OR_HAVE_PCEP_SRV6;
                key "admin-group-name";
                description
                    "list of affinity admin group";
                leaf admin-group-name  {
                    type  leafref {
                        path  "../config/admin-group-name";
                    }
                    description "admin group name";
                } // END of admin-group-name definition.

                container config {
                    description
                        "configuration container for affinity admin group";
                    uses admin-group-config;
                } // END of config-container definition.
                container state {
                    config false;
                    description
                        "state container for admin group";
                    uses admin-group-config;
                } // END of state-container definition.
            } // End of admin-group-list
        } // END of admin-groups-container definition.
    } // END of admin-group-constraints-top definition.
    grouping extended-admin-group-constraints-top {
        description
            "Top level extended-admin-group constraints group";
        container extended-admin-groups {
            // when " ipi-segment-routing:segment-routing/traffic-engineering/policies/policy/candidate-paths/candidate-path/dynamic/constraints/config ";
            if-feature feature-list:HAVE_SR_POLICY_OR_HAVE_PCEP_SRV6;
            description
                "CP constraint extended-admin-group";

            list extended-admin-group {
                if-feature feature-list:HAVE_SR_POLICY_OR_HAVE_PCEP_SRV6;
                key "extended-admin-group-name";
                description
                    "list of affinity extended-admin-group";
                leaf extended-admin-group-name  {
                    type  leafref {
                        path  "../config/extended-admin-group-name";
                    }
                    description "Extended admin group name";
                } // END of extended-admin-group-name definition.

                container config {
                    description
                        "configuration container for affinity Extended-admin-group";
                    uses extended-admin-group-config;
                } // END of config-container definition.
                container state {
                    config false;
                    description
                        "state container for extended-admin-group";
                    uses extended-admin-group-config;
                } // END of state-container definition.
            } // End of extended-admin-group-list
        } // END of extended-admin-groups-container definition.
    } // END of extended-admin-group-constraints-top definition.
    grouping srlg-group-constraints-top {
        description
            "Top level SRLG constraints group";
        container srlg-groups {
            // when " ipi-segment-routing:segment-routing/traffic-engineering/policies/policy/candidate-paths/candidate-path/dynamic/constraints/config ";
            if-feature feature-list:HAVE_SR_POLICY_OR_HAVE_PCEP_SRV6;
            description
                "CP constraint srlg-group";

            list srlg-group {
                if-feature feature-list:HAVE_SR_POLICY_OR_HAVE_PCEP_SRV6;
                key "srlg-group-name";
                description
                    "list of SRLG group";
                leaf srlg-group-name  {
                    type  leafref {
                        path  "../config/srlg-group-name";
                    }
                    description "SRLG group name";
                } // END of srlg-group-name definition.

                container config {
                    description
                        "configuration container for SRLG group";
                    uses srlg-group-config;
                } // END of config-container definition.
                container state {
                    config false;
                    description
                        "state container for SRLG group";
                    uses srlg-group-config;
                } // END of state-container definition.
            } // End of srlg-group-list
        } // END of srlg-groups-container definition.
    } // END of srlg-group-constraints-top definition.
    grouping ip-hop-constraints-top {
        description
            "Top level IP hop loose/strict constraints group";
        container ip {
            description
                "IP loose/strict constraints to be used for dynamic candidate path";

            list include-hop {
                key "address";
                description
                    "All the IP constraints should be included for the path computation";
                leaf address  {
                    type  leafref {
                        path  "../config/address";
                    }
                    description "Hop address which needs to be included in the LSP path";
                } // END of address definition.

                container config {
                    description
                        "include-hop config container";
                    uses include-ip-constraints-config;
                } // END of config-container definition.
                container state {
                    config false;
                    description
                        "include-hop state container";
                    uses include-ip-constraints-config;
                } // END of state-container definition.
            } // End of include-hop-list
        } // END of ip-container definition.
    } // END of ip-hop-constraints-top definition.
    grouping ip-hop-address-filter-constraints-top {
        description
            "Top level IP hop address include/exclude filter constraints group";
        container ip-address-filters {
            description
                "IP address filter include/exclude constraints to be used for dynamic
                        candidate path";

            list ip-address-filter {
                key "ihaf-address";
                description
                    "All the IP address include/exclude constraints that are required for
                                the path computation";
                leaf ihaf-address  {
                    type  leafref {
                        path  "../config/ihaf-address";
                    }
                    description "IP Hop address which needs to be included/excluded in the LSP path";
                } // END of ihaf-address definition.

                container config {
                    description
                        "IP address filtering config container";
                    uses ip-hop-address-filter-constraints-config;
                } // END of config-container definition.
                container state {
                    config false;
                    description
                        "IP address filtering state container";
                    uses ip-hop-address-filter-constraints-config;
                } // END of state-container definition.
            } // End of ip-address-filter-list
        } // END of ip-address-filters-container definition.
    } // END of ip-hop-address-filter-constraints-top definition.


}
