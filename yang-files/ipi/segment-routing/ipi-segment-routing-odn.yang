/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-segment-routing-odn.yang
*
*/

submodule ipi-segment-routing-odn {

    yang-version 1.1;

    belongs-to  ipi-segment-routing { prefix ipi-segment-routing; }

    import feature-list {
        prefix feature-list;
        revision-date 2026-09-15;
    }

    import ipi-sr-types {
        prefix ipi-sr-types;
        revision-date 2024-12-09;
    }

    include ipi-segment-routing-odn-constr { revision-date 2024-12-05;}
    organization
        "IP Infusion Inc.";

    contact
        "Address: 3965 Freedom Circle, Suite 200, Santa Clara, CA 95054
         Phone: +1 408-400-1900
         E-mail: support@ipinfusion.com
         Web: http://www.ipinfusion.com/";

    description
        "Model for managing segment-routing on-demand nexthop configurations";


    revision "2025-12-05" {
        description "Added separate container for PCE configuration and created dependency between candidate-path and pce lsp-delegate configuration";
        reference " 0.5.3.";
    }

    revision "2025-09-04" {
        description "Removing CML validations for fallback command";
        reference " 0.5.2.";
    }

    revision "2025-08-25" {
        description "Added a new attribute hop-limit under constraints for SR ODN";
        reference " 0.5.1.";
    }

    revision "2025-08-19" {
        description "Added fallback support for flex-algo in SR-ODN template";
        reference " 0.5.0.";
    }

    revision "2025-01-08" {
        description "Added ospf-empty attribute to when tag of constraints";
        reference " 0.5.4.";
    }

    revision "2024-12-18" {
        description "Added exit command exit-odn-cp back in constraints mode";
        reference " 0.4.3.";
    }

    revision "2024-12-13" {
        description "Added exit command in policy-cp-constraints mode";
        reference " 0.4.2.";
    }

    revision "2024-12-05" {
        description "Hide new SR-ODN constraints, EAG, SRLG, IP-Address-Filter-EAG";
        reference " 0.4.1.";
    }

    revision "2024-10-04" {
        description "Added Flex-Algo in ODN template";
        reference " 0.4.0.";
    }

    revision "2024-04-25" {
        description "Included ODN SR-Policy constraints for Flex-Algo";
        reference " 0.3.2.";
    }

    revision "2023-09-12" {
        description "Change in hierarchy for attrs under on-demand-nexthop";
        reference " 0.3.1.";
    }

    revision "2023-06-08" {
        description "Validation added for constraints IP-Address";
        reference " 0.3.0.";
    }

    revision "2023-03-09" {
        description "Replaced odn to sr-odn at required places";
        reference " 0.2.3.";
    }

    revision "2023-02-24" {
        description "Separating ODN properties from key grouping";
        reference " 0.2.2.";
    }

    revision "2023-02-23" {
        description "Updated xpath w.r.t ospf-empty case for when tag";
        reference " 0.2.1.";
    }

    revision "2023-02-17" {
        description "Added ospf-empty case for when tag";
        reference " 0.2.0.";
    }

    revision "2023-01-18" {
        description "Added another attribute w.r.t ospf-empty";
        reference " 0.1.6.";
    }

    revision "2023-01-12" {
        description "Updated input for RDN attrs";
        reference " 0.1.5.";
    }

    revision "2023-01-06" {
        description "Adding CML_RUNTIME flag in ip-constraints state container";
        reference " 0.1.4.";
    }

    revision "2023-01-04" {
        description "Preventing bounds keyword in CLI generation";
        reference " 0.1.3.";
    }

    revision "2022-11-07" {
        description "Addressing datamodel review comments";
        reference " 0.1.2.";
    }

    revision "2022-11-04" {
        description "Removal of explicit CP support on SR-ODN";
        reference " 0.1.1.";
    }

    revision "2022-11-01" {
        description "Initial Version";
        reference " 0.1.0.";
    }

    grouping odn-key-config {
        description
            "SR-ODN key config grouping";
        leaf color  {
            type  uint32 {
                 range "1..4294967295"  {
                    description "1..4294967295: Supported range 1 - 4294967295";
                 }
            }
            description "Color associated with ODN";
        } // END of color definition.

    } // END of odn-key-config definition.
    grouping odn-properties-config {
        description
            "SR-ODN properties grouping";
        leaf flex-algo  {
            type  uint8 {
                 range "128..255"  {
                    description "128..255: Supported range 128 - 255";
                 }
            }
            description "Flex algo value associated with ODN instance";
        } // END of flex-algo definition.

        leaf cspf-retry-limit  {
            type  uint16 {
                 range "1..65535"  {
                    description "1..65535: Supported range 1 - 65535";
                 }
            }
            description "Limit on the number of times a dynamic candidate path will retry to
                        calculate segment-list";
        } // END of cspf-retry-limit definition.

        leaf cspf-retry-interval  {
            type  uint16 {
                 range "1..600"  {
                    description "1..600: Supported range 1 - 600";
                 }
            }
            units "seconds";
            description "Interval between two successive retries for calculating
                        segment list of a dynamic candidate path using CSPF";
        } // END of cspf-retry-interval definition.

        leaf binding-sid-label  {
            type  uint16 {
                 range "16..15999"  {
                    description "16..15999: Supported range 16 - 15999";
                 }
            }
            description "Configurable Value for static binding SID";
        } // END of binding-sid-label definition.

    } // END of odn-properties-config definition.
    grouping odn-fallback-properties-config {
        description
            "SR-ODN fallback properties grouping";
        leaf fallback-native-sr  {
            // when " ../flex-algo ";
            type  empty;
            description "To enable fallback mechanism for flex-algorithm with Native-SR";
        } // END of fallback-native-sr definition.

        leaf fallback-flex-algo  {
            // when " ../flex-algo ";
            type  uint8 {
                 range "128..255"  {
                    description "128..255: Supported range 128 - 255";
                 }
            }
            description "To enable fallback mechanism for flex-algorithm with secondary
                        flex-algo FTN";
        } // END of fallback-flex-algo definition.

    } // END of odn-fallback-properties-config definition.
    grouping odn-segment-list-config {
        description
            "Config Attributes for segment list";
        leaf list-name  {
            type  string {
                length "1..1965";
                pattern "[^?' =,>|]+";
            }
            description "Segment-list name";
        } // END of list-name definition.

    } // END of odn-segment-list-config definition.
    grouping odn-candidate-paths-properties-config {
        description
            "odn-candidate-paths-properties-config";
        leaf discriminator  {
            type  uint32 {
                 range "1..65535"  {
                    description "1..65535: Supported range 1 - 65535";
                 }
            }
            description "Candidate path distinguisher, it's taken as a unique
                        identifier for a Local candidate path";
        } // END of discriminator definition.

        leaf protocol-origin  {
            type  ipi-sr-types:srte_protocol_origin_type_type_t;
            default "local";
            description "Instantiation mechanism used to create the candidate  path";
        } // END of protocol-origin definition.

        leaf originator  {
            type  string {
                length "0..1965";
                pattern "[^?' =,>|]*";
            }
            description "Identifier (concatenation of ASN and node-address) of
                        the node that signalled/instantiated the candidate
                        path on headend";
        } // END of originator definition.

        leaf preference  {
            type  uint16 {
                 range "1..65535"  {
                    description "1..65535: Supported range 1 - 65535";
                 }
            }
            default "100";
            description "Candidate path preference";
        } // END of preference definition.

    } // END of odn-candidate-paths-properties-config definition.
    grouping odn-dynamic-path-properties-config {
        description
            "Dynamic path properties of the candidate path";
        leaf pcep  {
            if-feature feature-list:HAVE_PCEP_SR;
            type  empty;
            description "Dynamic candidate path properties of PCEP";
        } // END of pcep definition.

        leaf isis-instance-id  {
            type  string {
                length "0..1965";
                pattern "[^?' =,>|]*";
            }
            default "";
            description "Dynamic candidate path properties of ISIS";
        } // END of isis-instance-id definition.

        leaf ospf-process-id  {
            type  int32 {
                 range "0..65535"  {
                    description "0..65535: Supported range 0 - 65535";
                 }
            }
            description "Dynamic candidate path properties of OSPF with process-id";
        } // END of ospf-process-id definition.

        leaf ospf-empty  {
            type  empty;
            description "Dynamic candidate path properties of OSPF without process-id";
        } // END of ospf-empty definition.

    } // END of odn-dynamic-path-properties-config definition.
    grouping odn-constraints-config {
        description
            "Configuration to change to constraints mode";
        leaf enable  {
            type  empty;
            mandatory true;
            description "Enable constraints for the candidate path";
        } // END of enable definition.

        leaf hop-limit  {
            type  uint8 {
                 range "1..32"  {
                    description "1..32: Supported range 1 - 32";
                 }
            }
            description "Use this attribute to specify a limit of hops for candidate-path";
        } // END of hop-limit definition.

    } // END of odn-constraints-config definition.
    grouping odn-bounds-config {
        description
            "Various Bound Constraints for the Dynamic Candidate Path";
        leaf metric-type  {
            type  ipi-sr-types:srte_cp_metric_type_t;
            description "Metric type to be used for path computation for this dynamic cp";
        } // END of metric-type definition.

        leaf bound  {
            // when " ../metric-type ";
            type  uint32 {
                 range "1..4294967295"  {
                    description "1..4294967295: Supported range 1 - 4294967295";
                 }
            }
            description "Path is invalid if its metric exceeds this value,
                        If no value is specified";
        } // END of bound definition.

    } // END of odn-bounds-config definition.
    grouping odn-candidate-path-types-config {
        description
            "Candidate path type grouping";
        container dynamic {
            if-feature feature-list:HAVE_SR_POLICY;
            description
                "Candidate path with dynamic computed segment-list";
            container config {
                description
                    "Dynamic CP config container";
                uses odn-dynamic-path-properties-config;
            } // END of config-container definition.
            container state {
                config false;
                description
                    "Dynamic CP state container";
                uses odn-dynamic-path-properties-config;
            } // END of state-container definition.
            container constraints {
                // when " ipi-segment-routing-odn:on-demand-nexthops/on-demand-nexthop/candidate-paths/candidate-path/dynamic/constraints/config/enable ";
                description
                    "constraints for candidate path which needs to be satisfied by
                            computation engine when calculating the cp";
                container config {
                    presence "yes";
                    description
                        "constraint config container";
                    uses odn-constraints-config;
                } // END of config-container definition.
                container state {
                    config false;
                    description
                        "constraint state container";
                    uses odn-constraints-config;
                } // END of state-container definition.
                container bounds {
                    description
                        "Upper-bound constraints container";

                    list bound {
                        key "metric-type";
                        max-elements 1;
                        description
                            "Upper-bound constraints on the computed dynamic path";
                        leaf metric-type  {
                            type  leafref {
                                path  "../config/metric-type";
                            }
                            description "Metric type can be IGP or TE";
                        } // END of metric-type definition.

                        container config {
                            description
                                "Bounds config container";
                            uses odn-bounds-config;
                        } // END of config-container definition.
                        container state {
                            config false;
                            description
                                "Bounds State container";
                            uses odn-bounds-config;
                        } // END of state-container definition.
                    } // End of bound-list
                } // END of bounds-container definition.
                uses odn-affinity-admin-group-constraints-top;
                uses odn-affinity-extended-admin-group-constraints-top;
                uses odn-srlg-group-constraints-top;
                uses odn-ip-hop-constraints-top;
                uses odn-ip-hop-address-filter-constraints-top;
                uses odn-dyn-cp-cons-segrule-top;
                uses odn-dyn-cp-cons-disjoint-path-top;
            } // END of constraints-container definition.
        } // END of dynamic-container definition.
    } // END of odn-candidate-path-types-config definition.
    grouping pce-config {
        description
            "SR-ODN PCE Configuration";
        leaf pce-state-report  {
            if-feature feature-list:HAVE_PCEP_SR;
            type  empty;
            description "To only report all the configured candidate path of policy to PCE
                        controller";
        } // END of pce-state-report definition.

        leaf pce-entity-id  {
            if-feature feature-list:HAVE_PCEP_SR;
            type  uint8 {
                 range "1..255"  {
                    description "1..255: Supported range 1 - 255";
                 }
            }
            description "Entity Id of PCEP entity to which this policy should be
                        queried/reported/delegated";
        } // END of pce-entity-id definition.

        leaf pce-lsp-delegate  {
            if-feature feature-list:HAVE_PCEP_SR;
            type  empty;
            description "To delegate all the configured candidate path of policy to PCE
                        controller";
        } // END of pce-lsp-delegate definition.

    } // END of pce-config definition.

    grouping  on-demand-nexthops-grouping {
    description
        "Top level container for On-Demand Nexthops";
    container on-demand-nexthops {
        // when " ipi-segment-routing:segment-routing/traffic-engineering/config/enable ";
        if-feature feature-list:HAVE_SR_POLICY;
        description
            "Top level container for On-Demand Nexthops";

        list on-demand-nexthop {
            key "color";
            description
                "SR On Demand Nexthop";
            leaf color  {
                type  leafref {
                    path  "../config/color";
                }
                description "Color associated with ODN";
            } // END of color definition.

            container config {
                description
                    "On-demand-nexthop config container";
                uses odn-key-config;
                uses odn-properties-config;
                uses odn-fallback-properties-config;
            } // END of config-container definition.
            container state {
                config false;
                description
                    "On-demand-nexthop state container";
                uses odn-key-config;
                uses odn-properties-config;
                uses odn-fallback-properties-config;
            } // END of state-container definition.
            container candidate-paths {
                // when " !ipi-segment-routing-odn:on-demand-nexthops/on-demand-nexthop/config/flex-algo ";
                description
                    "On-demand-nexthop candidate path(s)";

                list candidate-path {
                    key "discriminator protocol-origin originator";
                    description
                        "On-demand-nexthop Candidate path(s) list entry";
                    leaf discriminator  {
                        type  leafref {
                            path  "../config/discriminator";
                        }
                        description "Candidate path distinguisher, it's taken as a unique
                                    identifier for a Local candidate path";
                    } // END of discriminator definition.

                    leaf protocol-origin  {
                        type  leafref {
                            path  "../config/protocol-origin";
                        }
                        description "Instantiation mechanism used to create the candidate  path";
                    } // END of protocol-origin definition.

                    leaf originator  {
                        type  leafref {
                            path  "../config/originator";
                        }
                        description "Identifier (concatenation of ASN and node-address) of
                                    the node that signalled/instantiated the candidate
                                    path on headend";
                    } // END of originator definition.

                    container config {
                        description
                            "On-demand-nexthop config container";
                        uses odn-candidate-paths-properties-config;
                    } // END of config-container definition.
                    container state {
                        config false;
                        description
                            "On-demand-nexthop candidate path state container";
                        uses odn-candidate-paths-properties-config;
                    } // END of state-container definition.
                    uses odn-candidate-path-types-config;
                } // End of candidate-path-list
            } // END of candidate-paths-container definition.
            container pce {
                if-feature feature-list:HAVE_PCEP_SR;
                description
                    "On-demand-nexthop PCE Configuration";
                container config {
                    description
                        "ODN PCE config container";
                    uses pce-config;
                } // END of config-container definition.
                container state {
                    config false;
                    description
                        "ODN PCE state container";
                    uses pce-config;
                } // END of state-container definition.
            } // END of pce-container definition.
        } // End of on-demand-nexthop-list
    } // END of on-demand-nexthops-container definition.
    } // END of on-demand-nexthops-grouping definition.


}
