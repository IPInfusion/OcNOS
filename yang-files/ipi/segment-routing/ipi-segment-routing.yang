/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-segment-routing.yang
*
*/

module ipi-segment-routing {

    yang-version 1.1;

    namespace   "http://www.ipinfusion.com/yang/ocnos/ipi-segment-routing";

    prefix "ipi-segment-routing";

    import cml-data-types {
        prefix cml-data-types;
        revision-date 2026-05-15;
    }

    import ipi-sr-types {
        prefix ipi-sr-types;
        revision-date 2024-12-09;
    }

    import ipi-interface {
        prefix ipi-interface;
        revision-date 2026-03-10;
    }

    import ietf-inet-types {
        prefix inet;
        revision-date 2013-07-15;
    }

    import feature-list {
        prefix feature-list;
        revision-date 2026-09-15;
    }

    include ipi-segment-routing-mpls-flxalg { revision-date 2025-05-30;}
    include ipi-segment-routing-odn { revision-date 2025-12-05;}
    include ipi-segment-routing-policy-constr { revision-date 2024-12-05;}
    include ipi-segment-routing-policy-flxalg { revision-date 2024-12-05;}
    include ipi-srv6-flxalg { revision-date 2024-03-09;}
    include ipi-segment-routing-odn-constr { revision-date 2024-12-05;}
    organization
        "IP Infusion Inc.";

    contact
        "Address: 3965 Freedom Circle, Suite 200, Santa Clara, CA 95054
         Phone: +1 408-400-1900
         E-mail: support@ipinfusion.com
         Web: http://www.ipinfusion.com/";

    description
        "Model for managing segment-routing global configurations and state
                which includes traffic-enireening for sr as well";


    revision "2025-12-05" {
        description "Added separate container for PCE configuration and created dependency between candidate-path and pce lsp-delegate configuration";
        reference " 0.14.3.";
    }

    revision "2025-09-04" {
        description "Removing CML validations for fallback command";
        reference " 0.14.2.";
    }

    revision "2025-08-25" {
        description "Added a new attribute hop-limit under constraints for SR Policy";
        reference " 0.14.1.";
    }

    revision "2025-08-19" {
        description "Added fallback support for flex-algo in SR-ODN template";
        reference " 0.14.0.";
    }

    revision "2025-05-30" {
        description "Removed delete sequence under config container in adjacency segment and changed suppress cli to suppress-set-cli under adj-sid-proto attribute";
        reference " 0.13.9.";
    }

    revision "2024-12-18" {
        description "Added exit command exit-pol-cp back in constraints mode";
        reference " 0.13.7.";
    }

    revision "2024-12-13" {
        description "Added exit command in policy-cp-constraints mode";
        reference " 0.13.6.";
    }

    revision "2024-12-09" {
        description "Modified existing adjacency-sid cli to handle per proto functionality";
        reference " 0.13.8.";
    }

    revision "2024-12-05" {
        description "Hide new SR-Policy constraints, EAG, SRLG, IP-Address-Filter-EAG";
        reference " 0.13.5.";
    }

    revision "2024-10-04" {
        description "Added Flex-algo support for ODN";
        reference " 0.13.4.";
    }

    revision "2024-10-01" {
        description "Removed inclusion of SR-MPLS-IPv6 Segment-ID XML file, since not supported now";
        reference " 0.13.3.";
    }

    revision "2024-09-23" {
        description "Updated the description for binding-sid notification";
        reference " 0.13.2.";
    }

    revision "2024-08-20" {
        description "Added implicit delete tag for srms-preference";
        reference " 0.13.1.";
    }

    revision "2024-08-10" {
        description "Commented out Flex-Algo Adjacency-SID for OcNOS-6.6";
        reference " 0.13.0.";
    }

    revision "2024-06-25" {
        description "Unhide the SR-policy Algorithm parameter";
        reference " 0.12.11.";
    }

    revision "2024-05-06" {
        description "Included ODN SR-Policy constraints and Adj-SID XML files for Flex-Algo";
        reference " 0.12.10.";
    }

    revision "2024-04-27" {
        description "Updated revision date since Jenkins builds failed";
        reference " 0.12.9.";
    }

    revision "2024-04-26" {
        description "Modify Segment Routing Policy Entropy configuration description    ";
        reference " 0.12.8.";
    }

    revision "2024-04-12" {
        description "Defined custom error code for Prefix-SID deletion";
        reference " 0.12.7.";
    }

    revision "2024-03-18" {
        description "Setting Policy Explicit Candidate Path Entropy ERLD Value";
        reference " 0.12.6.";
    }

    revision "2024-03-13" {
        description "Flex-Algo policy data-model updated";
        reference " 0.12.5.";
    }

    revision "2024-03-09" {
        description "Moved all Flexible Algorithm related callbacks into a seperate yaml files";
        reference " 0.12.4.";
    }

    revision "2024-03-05" {
        description "Filled-in all empty help strings in Flex-Algo specfic SR-policy data-models in included files";
        reference " 0.12.3.";
    }

    revision "2024-02-29" {
        description "Commented out SR-MPLS IPv6 commands and new MPLS/SRv6 Segments with Flexible-Algorithm";
        reference " 0.12.2.";
    }

    revision "2024-02-13" {
        description "Updated validate function for prefix sid delete";
        reference " 0.12.1.";
    }

    revision "2024-01-24" {
        description "Included MPLS and SRv6 Explicit Segments with Flexible Algorithm Data Model";
        reference " 0.12.0.";
    }

    revision "2023-12-29" {
        description "Added utils_function for srv6-prefix";
        reference " 0.11.7.";
    }

    revision "2023-10-31" {
        description "Changed datatype from CML_DATE_TIME to CML_TIME for up/down time ";
        reference " 0.11.6.";
    }

    revision "2023-10-04" {
        description "Added CML_RUNTIME tag for include-hop state container ";
        reference " 0.11.5.";
    }

    revision "2023-09-12" {
        description "Change in hierarchy for attrs under on-demand-nexthop";
        reference " 0.11.4.";
    }

    revision "2023-08-04" {
        description "Added desc for attr start/end for srlb-config and cliprependstr for adj-sid,prefix-sid";
        reference " 0.11.3.";
    }

    revision "2023-07-11" {
        description "Added enclosing container for bound and policy-key objectlist";
        reference " 0.11.2.";
    }

    revision "2023-06-13" {
        description "Added enclosing container for mapping-entry objectlist";
        reference " 0.11.1.";
    }

    revision "2023-06-08" {
        description "Validation added for constraints IP-Address";
        reference " 0.11.0.";
    }

    revision "2023-04-22" {
        description "Added implicit delete tag for srms preference empty contanier";
        reference " 0.10.6.";
    }

    revision "2023-04-14" {
        description "Changed the Data type of flags attribute ";
        reference " 0.10.5.";
    }

    revision "2023-03-09" {
        description "Changed include if-feature from odn to sr-odn";
        reference " 0.10.4.";
    }

    revision "2023-02-26" {
        description "Added When tag for no-debug-all command";
        reference " 0.10.3.";
    }

    revision "2023-02-24" {
        description "Separating ODN properties from key grouping";
        reference " 0.10.2.";
    }

    revision "2023-02-23" {
        description "Updated xpath w.r.t ospf-empty case for when tag";
        reference " 0.10.1.";
    }

    revision "2023-02-17" {
        description "Addition of ospf_empty case in when tag";
        reference " 0.10.0.";
    }

    revision "2023-01-20" {
        description "Addition of when tag for mapping-entry";
        reference " 0.9.7.";
    }

    revision "2023-01-18" {
        description "Added another attribute ospf-empty";
        reference " 0.9.6.";
    }

    revision "2023-01-12" {
        description "Updated input for RDN attrs";
        reference " 0.9.5.";
    }

    revision "2023-01-06" {
        description "In ODN, Adding CML_RUNTIME flag in ip-constraints state container";
        reference " 0.9.4.";
    }

    revision "2023-01-04" {
        description "Preventing bounds keyword in CLI generation for SR-ODN";
        reference " 0.9.3.";
    }

    revision "2022-12-13" {
        description "Addition of implicit delete tag for config container";
        reference " 0.9.3.";
    }

    revision "2022-11-07" {
        description "Addressing datamodel team review comments in SR-ODN Initial checkin";
        reference " 0.9.2.";
    }

    revision "2022-11-04" {
        description "Removal of explicit CP support on SR-ODN";
        reference " 0.9.1.";
    }

    revision "2022-11-01" {
        description "SR-ODN changes";
        reference " 0.9.0.";
    }

    revision "2022-09-19" {
        description "Updated attribute names(unique) for ADJ-SID configuration";
        reference " 0.8.4.";
    }

    revision "2022-08-18" {
        description "Adding SRLB configuration";
        reference " 0.8.3.";
    }

    revision "2022-08-10" {
        description "Debug hierarchy change";
        reference " 0.8.2.";
    }

    revision "2022-08-02" {
        description "Updation of SRGB starting range value";
        reference " 0.8.1.";
    }

    revision "2022-07-30" {
        description "Updated when expressions in yang";
        reference " 0.8.0.";
    }

    revision "2022-07-19" {
        description "Update if-feature for Notification";
        reference " 0.7.2.";
    }

    revision "2022-07-16" {
        description "Global yang model name is changed as Global TE yang model";
        reference " 0.7.2.";
    }

    revision "2022-06-21" {
        description "Changes in the yang model WRT to admin-groups";
        reference " 0.7.1.";
    }

    revision "2022-06-01" {
        description "Updated the yang file with feature";
        reference " 0.7.0.";
    }

    revision "2022-04-05" {
        description "Merging SRv6 and SR-MPLS";
        reference " 0.6.0.";
    }

    revision "2021-06-16" {
        description "Moved prefix-sid configs from ipi-if-extended module to here";
        reference " 0.4.2.";
    }

    revision "2021-04-09" {
        description "SR-Netconf-Unit-Testing-Issues";
        reference " 0.4.1.";
    }

    revision "2021-04-05" {
        description "Adding Xpath to api support";
        reference " 0.4.0.";
    }

    revision "2021-02-28" {
        description "Adding support for SR Policy runtime attributes";
        reference " 0.3.0.";
    }

    revision "2020-12-15" {
        description "Change to have data-types in lower case instead of camel case";
        reference " 0.2.0.";
    }

    revision "2020-05-26" {
        description "Initial version";
        reference " 0.1.0.";
    }

    grouping ipv4-mapping-entry-properties-config {
        description
            "ipv4 prefix mapping entry address";
        leaf start-address  {
            type  cml-data-types:cml_ipv4_prefix_t;
            description "ipv4 prefix mapping entry address";
        } // END of start-address definition.

    } // END of ipv4-mapping-entry-properties-config definition.
    grouping mapping-entry-common-properties-config {
        description
            "common attributes for mapping entries";
        leaf start-sid  {
            type  uint32 {
                 range "0..1048575"  {
                    description "0..1048575: Supported range 0 - 1048575";
                 }
            }
            description "Starting Segment Identifier";
        } // END of start-sid definition.

        leaf range  {
            type  uint32 {
                 range "1..65535"  {
                    description "1..65535: Supported range 1 - 65535";
                 }
            }
            description "Segment Identifier interval";
        } // END of range definition.

        leaf attached  {
            type  boolean;
            description "Attached";
        } // END of attached definition.

        leaf algorithm-num  {
            type  uint32 {
                 range "128..255"  {
                    description "128..255: Supported range 128 - 255";
                 }
            }
            description "Flexible algorithm";
        } // END of algorithm-num definition.

    } // END of mapping-entry-common-properties-config definition.
    grouping srgb-config {
        description
            "segment routing global block configuration";
        leaf start  {
            // when " ../end ";
            type  uint32 {
                 range "16..1048575"  {
                    description "16..1048575: Supported range 16 - 1048575";
                 }
            }
            mandatory true;
            description "SRGB starting range";
        } // END of start definition.

        leaf end  {
            // when " ../start ";
            type  uint32 {
                 range "16..1048575"  {
                    description "16..1048575: Supported range 16 - 1048575";
                 }
            }
            mandatory true;
            description "SRGB end range";
        } // END of end definition.

    } // END of srgb-config definition.
    grouping srlb-config {
        description
            "segment routing global block configuration";
        leaf start  {
            type  uint32 {
                 range "16..1048575"  {
                    description "16..1048575: Supported range 16 - 1048575";
                 }
            }
            mandatory true;
            description "Start range for srlb-config";
        } // END of start definition.

        leaf end  {
            type  uint32 {
                 range "16..1048575"  {
                    description "16..1048575: Supported range 16 - 1048575";
                 }
            }
            mandatory true;
            description "End range for srlb-config";
        } // END of end definition.

    } // END of srlb-config definition.
    grouping segment-routing-interface-config {
        description
            "Grouping for segment-route interface configurations";
        leaf name  {
            type  leafref {
                path  "/ipi-interface:interfaces/ipi-interface:interface/ipi-interface:name";
            }
            description "Reference to interface name";
        } // END of name definition.

    } // END of segment-routing-interface-config definition.
    grouping prefer-sr-config {
        description
            "preference configuration for segment routing label over LDP label";
        leaf enable-preference  {
            type  empty;
            description "preference for segment routing label over LDP";
        } // END of enable-preference definition.

    } // END of prefer-sr-config definition.
    grouping srms-preference-value-config {
        description
            "preference configuration for segment routing mapping server";
        leaf preference  {
            type  uint8 {
                 range "1..255"  {
                    description "1..255: Supported range 1 - 255";
                 }
            }
            description "preference for segment routing mapping server";
        } // END of preference definition.

    } // END of srms-preference-value-config definition.
    grouping prefix-sid-config {
        description
            "Prefix-sid configurations";
        leaf prefix  {
            type  cml-data-types:cml_ip_prefix_t;
            description "connected prefix for prefix-sid";
        } // END of prefix definition.

        uses prefix-sid-attributes-config;
    } // END of prefix-sid-config definition.
    grouping prefix-sid-attributes-config {
        description
            "Prefix-sid attributes";
        leaf start-sid  {
            type  uint32;
            description "Value associated with prefix. The value must be
                        interpreted in the context of value-type.";
        } // END of start-sid definition.

    } // END of prefix-sid-attributes-config definition.
    grouping sid-value-type-config {
        description
            "This grouping defines how SID value is expressed";
        leaf value-type  {
            type  ipi-sr-types:sr_sid_value_type_t;
            description "Defines how the SID value is expressed.";
        } // END of value-type definition.

    } // END of sid-value-type-config definition.
    grouping sr-config {
        description
            "config attribute for frr for SR";
        leaf enable  {
            type  empty;
            mandatory true;
            description "Enable segment routing";
        } // END of enable definition.

    } // END of sr-config definition.
    grouping te-config {
        description
            "config attribute for traffic-engineering for SR Policies";
        leaf enable  {
            type  empty;
            mandatory true;
            description "Enable SR traffic engineering";
        } // END of enable definition.

    } // END of te-config definition.
    grouping srv6-config {
        description
            "config attribute for SRv6 for SR Policies";
        leaf enable  {
            type  empty;
            mandatory true;
            description "Enable segment routing v6";
        } // END of enable definition.

    } // END of srv6-config definition.
    grouping srv6-locators-config {
        description
            "config attribute for SRv6 Locators";
        leaf enable  {
            type  empty;
            mandatory true;
            description "Enable segment routing v6 locator";
        } // END of enable definition.

    } // END of srv6-locators-config definition.
    grouping prefix-sid-map-ipv4-config {
        description
            "config attribute for prefix-sid-map-ipv4";
        leaf enable  {
            type  empty;
            mandatory true;
            description "To enable ipv4 mapping server configuration";
        } // END of enable definition.

    } // END of prefix-sid-map-ipv4-config definition.
    grouping frr-config {
        description
            "config attribute for frr for SR Policies";
        leaf fast-reroute-enable  {
            if-feature feature-list:HAVE_SR_POLICY;
            type  empty;
            description "Enable fast reroute for traffic engineering polices";
        } // END of fast-reroute-enable definition.

    } // END of frr-config definition.
    grouping segment-properties-common-config {
        description
            "Common properties of segment which includes it's index value and it's
                        type.";
        leaf segment-index  {
            type  uint32 {
                 range "1..65535"  {
                    description "1..65535: Supported range 1 - 65535";
                 }
            }
            description "Index of the segment through which it can be modified or unconfigured";
        } // END of segment-index definition.

        leaf type  {
            type  ipi-sr-types:srte_segment_type_mpls_t;
            description "Type of the segment";
        } // END of type definition.

    } // END of segment-properties-common-config definition.
    grouping segment-v6-properties-common-config {
        description
            "Common properties of segment which includes it's index value and it's
                        type.";
        leaf segment-index  {
            type  uint32 {
                 range "1..65535"  {
                    description "1..65535: Supported range 1 - 65535";
                 }
            }
            description "Index of the segment through which it can be modified or unconfigured";
        } // END of segment-index definition.

        leaf type  {
            type  ipi-sr-types:srte_segment_type_2_t;
            description "Type of the segment";
        } // END of type definition.

    } // END of segment-v6-properties-common-config definition.
    grouping segment-type-1-properties-config {
        description
            "grouping for the properties of segment type 1";
        leaf sid-value  {
            type  uint32 {
                 range "0..1048575"  {
                    description "0..1048575: Supported range 0 - 1048575";
                 }
            }
            description "MPLS label value";
        } // END of sid-value definition.

    } // END of segment-type-1-properties-config definition.
    grouping segment-type-2-properties-config {
        description
            "grouping for the properties of segment type 2";
        leaf prefix  {
            type  inet:ipv6-address;
            description "SRV6 Prefix";
        } // END of prefix definition.

    } // END of segment-type-2-properties-config definition.
    grouping attributes-config {
        description
            "Grouping containing attributes applicable to all SR policies";
        container attributes {
            description
                "Attributes applicable to SR policies";
            uses segment-lists-config;
        } // END of attributes-container definition.
    } // END of attributes-config definition.
    grouping segment-list-config {
        description
            "config attributes for segment list";
        leaf list-name  {
            type  string {
                length "1..1965";
                pattern "[^?' =,>|]+";
            }
            description "Segment-list name";
        } // END of list-name definition.

    } // END of segment-list-config definition.
    grouping locators-list-config {
        description
            "config attributes for locator list";
        leaf locator-name  {
            type  string {
                length "1..1965";
                pattern "[^?' =,>|]+";
            }
            description "Locator name";
        } // END of locator-name definition.

        leaf prefix  {
            type  cml-data-types:cml_ipv6_prefix_t;
            description "Ipv6 Address for locator";
        } // END of prefix definition.

    } // END of locators-list-config definition.
    grouping locator-state {
        description
            "SRv6 Locator State";
        leaf uptime  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "Locator up time in seconds";
        } // END of uptime definition.

    } // END of locator-state definition.
    grouping locators-lists-config {
        description
            "Locators lists grouping";

        list locator {
        when " /ipi-segment-routing:segment-routing/ipi-segment-routing:srv6/ipi-segment-routing:locators/ipi-segment-routing:config/ipi-segment-routing:enable ";
            key "locator-name";
            description
                "Properties of a locator list";
            leaf locator-name  {
                type  leafref {
                    path  "../config/locator-name";
                }
                description "Locator name";
            } // END of locator-name definition.

            container config {
                description
                    "Config parameters for locator-list configuration";
                uses locators-list-config;
            } // END of config-container definition.
            container state {
                config false;
                description
                    "Operational state for locator-list configuration";
                uses locators-list-config;
                uses locator-state;
            } // END of state-container definition.
        } // End of locator-list
    } // END of locators-lists-config definition.
    grouping segment-lists-config {
        description
            "Segment lists grouping";
        container segment-lists {
            when " /ipi-segment-routing:segment-routing/ipi-segment-routing:traffic-engineering/ipi-segment-routing:config/ipi-segment-routing:enable ";
            if-feature feature-list:HAVE_SR_POLICY_OR_HAVE_SRV6;
            description
                "Segment-lists properties";

            list segment-list {
                key "list-name";
                description
                    "Properties of a segment list";
                leaf list-name  {
                    type  leafref {
                        path  "../config/list-name";
                    }
                    description "Segment-list name";
                } // END of list-name definition.

                container config {
                    description
                        "Config parameters for segment-list configuration";
                    uses segment-list-config;
                } // END of config-container definition.
                container state {
                    config false;
                    description
                        "Operational state for segment-list configuration";
                    uses segment-list-config;
                } // END of state-container definition.
                container segments {
                    description
                        "Segments for given segment list";

                    list segment {
                        key "segment-index type";
                        description
                            "Configure a segment at given index";
                        leaf segment-index  {
                            type  leafref {
                                path  "../config/segment-index";
                            }
                            description "Index of the segment through which it can be modified or unconfigured";
                        } // END of segment-index definition.

                        leaf type  {
                            type  leafref {
                                path  "../config/type";
                            }
                            description "Type of the segment";
                        } // END of type definition.

                        container config {
                            description
                                "Contains config parameters for configuring segment index and type";
                            uses segment-properties-common-config;
                        } // END of config-container definition.
                        container state {
                            config false;
                            description
                                "Contains operational information about segment index and type";
                            uses segment-properties-common-config;
                        } // END of state-container definition.
                        container segment-type-1 {
                            if-feature feature-list:HAVE_SR_MPLS;
                            description
                                "Segment declared by MPLS label";
                            container config {
                                description
                                    "Contains parameters to configure segment-type-1";
                                uses segment-type-1-properties-config;
                            } // END of config-container definition.
                            container state {
                                config false;
                                description
                                    "Contains operational information regarding segment-type-1";
                                uses segment-type-1-properties-config;
                            } // END of state-container definition.
                        } // END of segment-type-1-container definition.
                    } // End of segment-list

                    list segment-v6 {
                        key "segment-index type";
                        description
                            "Configure a segment at given index";
                        leaf segment-index  {
                            type  leafref {
                                path  "../config/segment-index";
                            }
                            description "Index of the segment through which it can be modified or unconfigured";
                        } // END of segment-index definition.

                        leaf type  {
                            type  leafref {
                                path  "../config/type";
                            }
                            description "Type of the segment";
                        } // END of type definition.

                        container config {
                            description
                                "Contains config parameters for configuring segment index and type";
                            uses segment-v6-properties-common-config;
                        } // END of config-container definition.
                        container state {
                            config false;
                            description
                                "Contains operational information about segment index and type";
                            uses segment-v6-properties-common-config;
                        } // END of state-container definition.
                        container segment-type-2 {
                            if-feature feature-list:HAVE_SRV6;
                            description
                                "Segment declared by SRv6 SID";
                            container config {
                                description
                                    "Contains parameters to configure segment-type-2";
                                uses segment-type-2-properties-config;
                            } // END of config-container definition.
                            container state {
                                config false;
                                description
                                    "Contains operational information regarding segment-type-2";
                                uses segment-type-2-properties-config;
                            } // END of state-container definition.
                        } // END of segment-type-2-container definition.
                    } // End of segment-v6-list
                } // END of segments-container definition.
            } // End of segment-list-list
        } // END of segment-lists-container definition.
    } // END of segment-lists-config definition.
    grouping policies-config {
        description
            "SR policy grouping";
        container policies {
            when " /ipi-segment-routing:segment-routing/ipi-segment-routing:traffic-engineering/ipi-segment-routing:config/ipi-segment-routing:enable ";
            if-feature feature-list:HAVE_SR_POLICY_OR_HAVE_SRV6;
            description
                "SR Policy container";

            list policy {
                key "name";
                description
                    "SR Policy properties";
                leaf name  {
                    type  leafref {
                        path  "../config/name";
                    }
                    description "User friendly name of the SR Policy";
                } // END of name definition.

                container policy-keys {
                    description
                        "SR Policy key container";

                    list policy-key {
                        key "color end-point";
                        description
                            "SR Policy key";
                        leaf color  {
                            type  leafref {
                                path  "../config/color";
                            }
                            description "Color associated with the policy";
                        } // END of color definition.

                        leaf end-point  {
                            type  leafref {
                                path  "../config/end-point";
                            }
                            description "Policy end point IP address";
                        } // END of end-point definition.

                        container config {
                            description
                                "SR policy config container";
                            uses policy-key-properties-config;
                        } // END of config-container definition.
                        container state {
                            config false;
                            description
                                "SR policy state container";
                            uses policy-key-properties-config;
                        } // END of state-container definition.
                    } // End of policy-key-list
                } // END of policy-keys-container definition.
                container config {
                    description
                        "SR policy config container";
                    uses policy-properties-config;
                } // END of config-container definition.
                container candidate-paths {
                    description
                        "SR policy candidate path(s)";

                    list candidate-path {
                        key "discriminator protocol-origin originator";
                        description
                            "SR policy Candidate path(s) list entry";
                        leaf discriminator  {
                            type  leafref {
                                path  "../config/discriminator";
                            }
                            description "Candidate path distinguisher, it's taken as a unique
                                        identifier for a Local candidate path";
                        } // END of discriminator definition.

                        leaf protocol-origin  {
                            type  leafref {
                                path  "../config/protocol-origin";
                            }
                            description "Instantiation mechanism used to create the candidate  path";
                        } // END of protocol-origin definition.

                        leaf originator  {
                            type  leafref {
                                path  "../config/originator";
                            }
                            description "Identifier (concatenation of ASN and node-address) of
                                        the node that signalled/instantiated the candidate
                                        path on headend";
                        } // END of originator definition.

                        container config {
                            description
                                "SR policy config container";
                            uses candidate-paths-properties-config;
                        } // END of config-container definition.
                        container state {
                            config false;
                            description
                                "SR policy candidate path table";
                            uses candidate-paths-properties-config;
                            uses candidate-paths-properties-state;
                        } // END of state-container definition.
                        container forwarding-paths {
                            config false;
                            description
                                "Top level container for SR Policy candidate forwarding paths";
                            container forwarding-path {
                                config false;
                                description
                                    "SR policy candidate path forwarding path";
                                container state {
                                    config false;
                                    description
                                        "SR policy forwarding path table";
                                    uses forwarding-path-state;
                                } // END of state-container definition.
                                container label-stack {
                                    config false;
                                    description
                                        "SR policy forwarding path label stack";
                                    container labels {
                                        config false;
                                        description
                                            "SR policy forwarding path labels";
                                        container state {
                                            config false;
                                            description
                                                "SR policy label stack table";
                                            uses label-stack-state;
                                        } // END of state-container definition.
                                    } // END of labels-container definition.
                                } // END of label-stack-container definition.
                            } // END of forwarding-path-container definition.
                        } // END of forwarding-paths-container definition.
                        uses candidate-path-types-config;
                    } // End of candidate-path-list
                } // END of candidate-paths-container definition.
                container state {
                    config false;
                    description
                        "SR policy state container";
                    container statistics {
                        if-feature feature-list:HAVE_SR_POLICY;
                        config false;
                        description
                            "Segment Routing Policy packet stats";
                        uses sr-policy-stats-state;
                    } // END of statistics-container definition.
                    uses policy-properties-config;
                    uses policy-properties-state;
                } // END of state-container definition.
                container pce {
                    if-feature feature-list:HAVE_PCEP_SR_OR_HAVE_PCEP_SRV6;
                    description
                        "SR Policy PCE Configuration";
                    container config {
                        description
                            "SR Policy PCE config container";
                        uses policy-pce-config;
                    } // END of config-container definition.
                    container state {
                        config false;
                        description
                            "SR Policy PCE state container";
                        uses policy-pce-config;
                    } // END of state-container definition.
                } // END of pce-container definition.
            } // End of policy-list
        } // END of policies-container definition.
    } // END of policies-config definition.
    grouping policy-key-properties-config {
        description
            "SR Policy configuration parameters grouping";
        leaf color  {
            type  uint32 {
                 range "1..4294967295"  {
                    description "1..4294967295: Supported range 1 - 4294967295";
                 }
            }
            description "Color associated with the policy";
        } // END of color definition.

        leaf end-point  {
            type  inet:ip-address;
            description "Policy end point IP address";
        } // END of end-point definition.

    } // END of policy-key-properties-config definition.
    grouping policy-properties-config {
        description
            "SR Policy configuration parameters grouping";
        leaf name  {
            type  string {
                length "1..1965";
                pattern "[^?' =,>|]+";
            }
            description "User friendly name of the SR Policy";
        } // END of name definition.

        leaf admin-state  {
            type  empty;
            description "SR policy administrative state, true for enabled, false for disabled";
        } // END of admin-state definition.

        leaf explicit-null  {
            if-feature feature-list:HAVE_SR_POLICY;
            type  ipi-sr-types:srte_explicite_null_type_t;
            description "To set explicit null behaviour for the policy";
        } // END of explicit-null definition.

        leaf cspf-retry-limit  {
            if-feature feature-list:HAVE_SR_POLICY;
            type  uint32 {
                 range "1..65535"  {
                    description "1..65535: Supported range 1 - 65535";
                 }
            }
            description "Limit on the number of times a dynamic candidate path will retry to
                        calculate segment-list";
        } // END of cspf-retry-limit definition.

        leaf cspf-retry-interval  {
            if-feature feature-list:HAVE_SR_POLICY;
            type  uint32 {
                 range "1..600"  {
                    description "1..600: Supported range 1 - 600";
                 }
            }
            description "Interval between two successive retries for calculating
                        segment list of a dynamic candidate path using CSPF";
        } // END of cspf-retry-interval definition.

        leaf entropy-erld  {
            if-feature feature-list:HAVE_SR_POLICY;
            type  uint8 {
                 range "3..255"  {
                    description "3..255: Supported range 3 - 255";
                 }
            }
            description "Setting ERLD to enable Entropy capability (only applicable for
                        explicit policy)";
        } // END of entropy-erld definition.

        uses bsid-properties-config;
    } // END of policy-properties-config definition.
    grouping policy-pce-config {
        description
            "SR Policy PCE Configuration";
        leaf pce-lsp-delegate  {
            if-feature feature-list:HAVE_PCEP_SR_OR_HAVE_PCEP_SRV6;
            type  empty;
            description "To delegate all the configured candidate path of policy to PCE
                        controller";
        } // END of pce-lsp-delegate definition.

        leaf pce-state-report  {
            if-feature feature-list:HAVE_PCEP_SR_OR_HAVE_PCEP_SRV6;
            type  empty;
            description "To only report all the configured candidate path of policy to PCE
                        controller";
        } // END of pce-state-report definition.

        leaf pce-entity-id  {
            if-feature feature-list:HAVE_PCEP_SR_OR_HAVE_PCEP_SRV6;
            type  uint32 {
                 range "1..255"  {
                    description "1..255: Supported range 1 - 255";
                 }
            }
            description "Entity Id of PCEP entity to which this policy should be
                        queried/reported/delegated";
        } // END of pce-entity-id definition.

    } // END of policy-pce-config definition.
    grouping bsid-properties-config {
        description
            "SR Policy BSID properties grouping";
        leaf bsid-value  {
            if-feature feature-list:HAVE_SR_POLICY;
            type  uint32 {
                 range "16..15999"  {
                    description "16..15999: Supported range 16 - 15999";
                 }
            }
            description "configurable value for static binding sid";
        } // END of bsid-value definition.

    } // END of bsid-properties-config definition.
    grouping policy-properties-state {
        description
            "SR Policy BSID properties grouping";
        leaf oper-state  {
            type  ipi-sr-types:srte_policy_oper_state_t;
            description "SR policy operational state";
        } // END of oper-state definition.

        leaf transition-count  {
            type  uint32;
            description "Indicates number of up/down transitions";
        } // END of transition-count definition.

        leaf up-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "Policy up time in seconds";
        } // END of up-time definition.

        leaf down-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "Policy down time in seconds";
        } // END of down-time definition.

        leaf bsid-alloc-mode  {
            type  string {
                length "1..1965";
                pattern "[^?' =,>|]+";
            }
            description "SR Policy Binding SID alloc mode";
        } // END of bsid-alloc-mode definition.

        leaf bsid-oper-state  {
            type  ipi-sr-types:sr_policy_bsid_oper_state;
            description "SR Policy Binding SID operational state";
        } // END of bsid-oper-state definition.

    } // END of policy-properties-state definition.
    grouping sr-policy-stats-state {
        description
            "Segment Routing Policy packet stats";
        leaf tx-bytes  {
            type  uint64;
            description "SR Policy statistics Tx Bytes";
        } // END of tx-bytes definition.

        leaf rx-bytes  {
            type  uint64;
            description "SR Policy statistics Rx Bytes";
        } // END of rx-bytes definition.

        leaf tx-packets  {
            type  uint64;
            description "SR Policy statistics Tx Packets";
        } // END of tx-packets definition.

        leaf rx-packets  {
            type  uint64;
            description "SR Policy statistics Rx Packets";
        } // END of rx-packets definition.

    } // END of sr-policy-stats-state definition.
    grouping candidate-paths-properties-config {
        description
            "SR Policy candidate path grouping";
        leaf discriminator  {
            type  uint32 {
                 range "1..65535"  {
                    description "1..65535: Supported range 1 - 65535";
                 }
            }
            description "Candidate path distinguisher, it's taken as a unique
                        identifier for a Local candidate path";
        } // END of discriminator definition.

        leaf protocol-origin  {
            type  ipi-sr-types:srte_protocol_origin_type_type_t;
            default "local";
            description "Instantiation mechanism used to create the candidate  path";
        } // END of protocol-origin definition.

        leaf originator  {
            type  string {
                length "0..1965";
                pattern "[^?' =,>|]*";
            }
            description "Identifier (concatenation of ASN and node-address) of
                        the node that signalled/instantiated the candidate
                        path on headend";
        } // END of originator definition.

        leaf preference  {
            type  uint32 {
                 range "1..65535"  {
                    description "1..65535: Supported range 1 - 65535";
                 }
            }
            default "100";
            description "Candidate path preference";
        } // END of preference definition.

    } // END of candidate-paths-properties-config definition.
    grouping candidate-paths-properties-state {
        description
            "SR Policy candidate path state attribute grouping";
        leaf is-valid  {
            type  boolean;
            description "Specifies the state of candidate path";
        } // END of is-valid definition.

        leaf non-selection-reason  {
            type  cml-data-types:cml_line_t {
                length "1..1965";
            }
            description "Specifies the inactive reason for candidate path";
        } // END of non-selection-reason definition.

        leaf is-best-candidate-path  {
            type  boolean;
            description "Specifies the whether it is best candidate path";
        } // END of is-best-candidate-path definition.

    } // END of candidate-paths-properties-state definition.
    grouping forwarding-path-state {
        description
            "Forwarding paths grouping";
        leaf path-id  {
            type  uint8;
            description "Specifies the forwarding path ID";
        } // END of path-id definition.

        leaf next-hop-address  {
            type  inet:ip-address;
            description "Specifies the IP address of next hop";
        } // END of next-hop-address definition.

        leaf outgoing-interface  {
            type  string {
                length "1..1965";
                pattern "[^?' =,>|]+";
            }
            description "Specifies the outgoing interface";
        } // END of outgoing-interface definition.

        leaf path-type  {
            type  string {
                length "1..1965";
                pattern "[^?' =,>|]+";
            }
            description "Specifies the path type";
        } // END of path-type definition.

    } // END of forwarding-path-state definition.
    grouping label-stack-state {
        description
            "Label stack grouping";
        leaf label  {
            type  string {
                length "1..1965";
                pattern "[^?' =,>|]+";
            }
            description "Specifies the label";
        } // END of label definition.

    } // END of label-stack-state definition.
    grouping candidate-path-types-config {
        description
            "Candidate path type grouping";
        container dynamic {
            if-feature feature-list:HAVE_SR_POLICY_OR_HAVE_PCEP_SRV6;
            description
                "Candidate path with dynamic computed segment-list";
            container config {
                description
                    "Dynamic CP config container";
                uses dynamic-path-properties-config;
            } // END of config-container definition.
            container state {
                config false;
                description
                    "Dynamic CP state container";
                uses dynamic-path-properties-config;
            } // END of state-container definition.
            container constraints {
                // when " ipi-segment-routing:segment-routing/traffic-engineering/policies/policy/candidate-paths/candidate-path/dynamic/constraints/config/enable ";
                description
                    "constraints for candidate path which needs to be satisfied by
                            computation engine when calculating a segment-list for the cp";
                container config {
                    presence "yes";
                    description
                        "constraint config container";
                    uses constraints-config;
                } // END of config-container definition.
                container state {
                    config false;
                    description
                        "constraint state container";
                    uses constraints-config;
                } // END of state-container definition.
                container bounds {
                    description
                        "Upper-bound constraints container";

                    list bound {
                        key "metric-type";
                        max-elements 1;
                        description
                            "Upper-bound constraints on the computed dynamic path";
                        leaf metric-type  {
                            type  leafref {
                                path  "../config/metric-type";
                            }
                            description "Metric type can be IGP or TE";
                        } // END of metric-type definition.

                        container config {
                            description
                                "Bounds config container";
                            uses bounds-config;
                        } // END of config-container definition.
                        container state {
                            config false;
                            description
                                "Bounds State container";
                            uses bounds-config;
                        } // END of state-container definition.
                    } // End of bound-list
                } // END of bounds-container definition.
                uses admin-group-constraints-top;
                uses extended-admin-group-constraints-top;
                uses srlg-group-constraints-top;
                uses ip-hop-constraints-top;
                uses ip-hop-address-filter-constraints-top;
                uses sr-dyn-cp-cons-segrule-top;
                uses sr-dyn-cp-cons-disjoint-path-top;
            } // END of constraints-container definition.
        } // END of dynamic-container definition.
        container explicit {
            description
                "Candidate path with explicitly defined set of segment-list";
            uses explicit-path-properties;
        } // END of explicit-container definition.
    } // END of candidate-path-types-config definition.
    grouping bounds-config {
        description
            "various bound constraints for the dynamic candidate path";
        leaf metric-type  {
            type  ipi-sr-types:srte_cp_metric_type_t;
            description "Metric type to be used for path computation for this dynamic cp";
        } // END of metric-type definition.

        leaf bound  {
            // when " ../metric-type ";
            type  uint32 {
                 range "1..4294967295"  {
                    description "1..4294967295: Supported range 1 - 4294967295";
                 }
            }
            description "Path is invalid if its metric exceeds this value,
                        If no value is specified";
        } // END of bound definition.

        leaf segment-bound  {
            type  uint32;
            description "Path is invalid if it has more segments than this value";
        } // END of segment-bound definition.

    } // END of bounds-config definition.
    grouping dynamic-path-properties-config {
        description
            "Dynamic path properties of the candidate path";
        leaf pcep  {
            if-feature feature-list:HAVE_PCEP_SR_OR_HAVE_PCEP_SRV6;
            type  empty;
            description "Dynamic candidate path properties of PCEP";
        } // END of pcep definition.

        leaf isis  {
            type  string {
                length "0..1965";
                pattern "[^?' =,>|]*";
            }
            default "";
            description "Dynamic candidate path properties of ISIS";
        } // END of isis definition.

        leaf ospf  {
            type  int32 {
                 range "0..65535"  {
                    description "0..65535: Supported range 0 - 65535";
                 }
            }
            description "Dynamic candidate path properties of OSPF with process-id";
        } // END of ospf definition.

        leaf ospf-empty  {
            type  empty;
            description "Dynamic candidate path properties of OSPF without process-id";
        } // END of ospf-empty definition.

    } // END of dynamic-path-properties-config definition.
    grouping explicit-path-properties {
        description
            "Dynamic path properties of the candidate path";
        container segment-lists {
            if-feature feature-list:HAVE_SR_POLICY_OR_HAVE_SRV6;
            description
                "Path segment list(s) properties";

            list segment-list {
                key "list-name";
                description
                    "SR policy candidate path segment lists";
                leaf list-name  {
                    type  leafref {
                        path  "../config/list-name";
                    }
                    description "Reference to segment-list name";
                } // END of list-name definition.

                container config {
                    description
                        "Configuration state for SR policy candidate path segment lists";
                    uses weighted-segment-list-config;
                } // END of config-container definition.
            } // End of segment-list-list
        } // END of segment-lists-container definition.
    } // END of explicit-path-properties definition.
    grouping constraints-config {
        description
            "Configuration to change to constraints mode";
        leaf enable  {
            type  empty;
            mandatory true;
            description "Enable constraints for the candidate path";
        } // END of enable definition.

        leaf hop-limit  {
            type  uint8 {
                 range "1..32"  {
                    description "1..32: Supported range 1 - 32";
                 }
            }
            description "Use this attribute to specify a limit of hops for candidate-path";
        } // END of hop-limit definition.

    } // END of constraints-config definition.
    grouping srv6-manager-state {
        description
            "SRv6 manager state attributes";
        leaf protocol-state  {
            type  ipi-sr-types:srv6_protocol_state_t;
            description "SRv6 Protocol State";
        } // END of protocol-state definition.

        leaf srv6-locator-name  {
            type  string {
                length "1..1965";
                pattern "[^?' =,>|]+";
            }
            description "SRv6 Locator Name";
        } // END of srv6-locator-name definition.

        leaf-list platform-capabilities-end-function  {
            type  string {
                length "1..1965";
                pattern "[^?' =,>|]+";
            }
            description "Platform Capabilities END Function";
        } // END of platform-capabilities-end-function definition.

        leaf-list platform-capabilities-ingress-function  {
            type  string {
                length "1..1965";
                pattern "[^?' =,>|]+";
            }
            description "platform-capabilities ingress function";
        } // END of platform-capabilities-ingress-function definition.

        leaf-list platform-capabilities-ingress-sr-policy  {
            type  string {
                length "1..1965";
                pattern "[^?' =,>|]+";
            }
            description "platform capabilities sr policy";
        } // END of platform-capabilities-ingress-sr-policy definition.

    } // END of srv6-manager-state definition.
    grouping srv6-services-state {
        description
            "SRv6 services state attributes";
        leaf fec-ipv4-prefix  {
            type  cml-data-types:cml_ipv4_prefix_t;
            description "SRv6 IPv4 FEC";
        } // END of fec-ipv4-prefix definition.

        leaf service-vrf-id  {
            type  uint32;
            description "SRv6 service VRF ID";
        } // END of service-vrf-id definition.

        leaf service-vrf-name  {
            type  string {
                length "1..1965";
                pattern "[^?' =,>|]+";
            }
            description "SRv6 service VRF Name";
        } // END of service-vrf-name definition.

        leaf service-type  {
            type  string {
                length "1..1965";
                pattern "[^?' =,>|]+";
            }
            description "SRv6 service Type";
        } // END of service-type definition.

        leaf flags  {
            type  string {
                length "1..1965";
            }
            description "SRv6 service flags. Possible values are - Installed and/or Uses
                        service-mapped tunnel";
        } // END of flags definition.

        leaf address-family  {
            type  uint32;
            description "SRv6 service address-family";
        } // END of address-family definition.

        leaf sid  {
            type  inet:ipv6-address;
            description "SRv6 service SID";
        } // END of sid definition.

        leaf nexthop-ipv6-prefix  {
            type  inet:ipv6-address;
            description "SRv6 service nexthop ipv6 address";
        } // END of nexthop-ipv6-prefix definition.

        leaf service-policy-name  {
            type  string {
                length "1..1965";
                pattern "[^?' =,>|]+";
            }
            description "SRv6 service Policy Name";
        } // END of service-policy-name definition.

    } // END of srv6-services-state definition.
    grouping srv6-transport-ftn-state {
        description
            "SRv6 transport FTN state attributes";
        leaf vrf-id  {
            type  uint32;
            description "SRv6 FTN VRF ID";
        } // END of vrf-id definition.

        leaf fec-prefix  {
            type  cml-data-types:cml_ipv4_addr_prefix_t;
            description "SRv6 Transport FTN Ipv4 FEC";
        } // END of fec-prefix definition.

        leaf vrf-name  {
            type  string {
                length "1..1965";
                pattern "[^?' =,>|]+";
            }
            description "SRv6 FTN VRF Name";
        } // END of vrf-name definition.

        leaf ftn-nexthop  {
            type  inet:ipv6-address;
            description "SRv6 Transport FTN Next hop ipv6 address";
        } // END of ftn-nexthop definition.

        leaf tunnel-policy  {
            type  string {
                length "1..1965";
                pattern "[^?' =,>|]+";
            }
            description "SRv6 Transport FTN Policy Name";
        } // END of tunnel-policy definition.

        leaf ftn-color  {
            type  uint32;
            description "SRv6 Transport FTN Policy color. Possible color values are
                        (1-4294967295)";
        } // END of ftn-color definition.

    } // END of srv6-transport-ftn-state definition.
    grouping srv6-transport-state {
        description
            "SRv6 transport state attributes";
        leaf fec  {
            type  inet:ipv6-address;
            description "SRv6 Transport entry Ipv6 FEC";
        } // END of fec definition.

        leaf policy-name  {
            type  string {
                length "1..1965";
                pattern "[^?' =,>|]+";
            }
            description "SRv6 Transport Entry Policy Name";
        } // END of policy-name definition.

        leaf policy-id  {
            type  uint32;
            description "SRv6 Transport Policy ID";
        } // END of policy-id definition.

        leaf transport-color  {
            type  uint32;
            description "SRv6 Policy color. Possible color values are (1-4294967295)";
        } // END of transport-color definition.

        leaf code  {
            type  string {
                length "1..1965";
                pattern "[^?' =,>|]+";
            }
            description "SRv6 transport code. Possible Values are SELECTED or INSTALLED";
        } // END of code definition.

        leaf is-primary  {
            type  boolean;
            description "SRv6 Transport entry Flag to denote, whether the entry in Primary or
                        Not";
        } // END of is-primary definition.

        leaf out-sid  {
            type  inet:ipv6-address;
            description "SRv6 transport outgoing segment identifier";
        } // END of out-sid definition.

        leaf out-interface  {
            type  string {
                length "1..1965";
                pattern "[^?' =,>|]+";
            }
            description "SRv6 transport outgoing interface name";
        } // END of out-interface definition.

        leaf nexthop  {
            type  inet:ipv6-address;
            description "SRv6 transport entry - nexthop Ipv6 address used for this FEC";
        } // END of nexthop definition.

    } // END of srv6-transport-state definition.
    grouping policy-debug-config {
        description
            "Configuration data related to debugging policy";
        leaf options  {
            type  ipi-sr-types:sr_te_debug_t;
            description "This attribute is used to enable/disable SR Policy debug logs";
        } // END of options definition.

    } // END of policy-debug-config definition.
    grouping policy-debug-state {
        description
            "Configuration data related to debugging policy";
        leaf terminal-debug-status  {
            type  ipi-sr-types:sr_te_debug_t;
            description "This attribute is used to enable/disable SR Policy debug logs";
        } // END of terminal-debug-status definition.

    } // END of policy-debug-state definition.
    grouping debug-policy-config {
        description
            "debug related attributes for sr policy";
        container debug {
            if-feature feature-list:HAVE_SR_POLICY_OR_HAVE_SRV6;
            description
                "enable/disable debug for sr-policy";
            container config {
                description
                    "Configuration data for debugging parameters";
                uses policy-debug-config;
            } // END of config-container definition.
            container state {
                config false;
                description
                    "Operational data for debugging parameters";
                uses policy-debug-config;
                uses policy-debug-state;
            } // END of state-container definition.
        } // END of debug-container definition.
    } // END of debug-policy-config definition.
    grouping srms-ipv4-prefix-sid-map-state {
        description
            "SRMS prefix-sid-map detail";
        leaf start-prefix  {
            type  cml-data-types:cml_ip_prefix_addr_t;
            description "SR MS prefix-sid-map Start Address";
        } // END of start-prefix definition.

        leaf algorithm-num  {
            type  uint8;
            description "SR Algorithm Number";
        } // END of algorithm-num definition.

        leaf start-sid-index  {
            type  uint16;
            description "Start SID Index";
        } // END of start-sid-index definition.

        leaf range  {
            type  uint16;
            description "range";
        } // END of range definition.

        leaf end-prefix  {
            type  cml-data-types:cml_ip_prefix_addr_t;
            description "SR MS prefix-sid-map End Address";
        } // END of end-prefix definition.

        leaf end-sid-index  {
            type  uint16;
            description "Last SID Index";
        } // END of end-sid-index definition.

        leaf attached  {
            type  empty;
            description "SR MS attachedd";
        } // END of attached definition.

        leaf preference  {
            type  uint8;
            description "SR map table entry SRMS pref";
        } // END of preference definition.

    } // END of srms-ipv4-prefix-sid-map-state definition.

    grouping  segment-routing-grouping {
    description
        "This defines a YANG data model for segment routing MPLS and TE
                configuration and operation. This document does not define the IGP
                extensions to support segment routing";
    container segment-routing {
        if-feature feature-list:HAVE_SRV6_OR_HAVE_SR_MPLS_OR_HAVE_SR_POLICY;
        description
            "This defines a YANG data model for segment routing MPLS and TE
                    configuration and operation. This document does not define the IGP
                    extensions to support segment routing";
        container config {
            presence "yes";
            description
                "segment-routing configuration container,         enables global
                        configuration of segment-routing and allows to configure
                        various SR related CLIs";
            uses sr-config;
            uses sr-te-flex-algo-config;
        } // END of config-container definition.
        container state {
            config false;
            description
                "segment-routing state container describes segment-routing state";
            uses sr-config;
            uses sr-te-flex-algo-config;
        } // END of state-container definition.
        container interfaces {
            if-feature feature-list:HAVE_SR_MPLS;
            description
                "Top level container for interfaces, including configuration and state
                        data";

            list interface {
                key "name";
                description
                    "This list defines global SR interface configuration and state
                                information.";
                leaf name  {
                    type  leafref {
                        path  "../config/name";
                    }
                    description "Reference to interface name";
                } // END of name definition.

                container config {
                    description
                        "Configuration data for segment-routing interface name";
                    uses segment-routing-interface-config;
                } // END of config-container definition.
                uses adjacency-segment-def-algo-top;
                uses prefix-segment-algorithm-top;
            } // End of interface-list
        } // END of interfaces-container definition.
        container sr-mpls {
            when " /ipi-segment-routing:segment-routing/ipi-segment-routing:config/ipi-segment-routing:enable ";
            if-feature feature-list:HAVE_SR_MPLS;
            description
                "SR MPLS data plane global configuration and operational state";
            container sr-prefer-over-ldp {
                description
                    "to prefer segment-routing labels over LDP labels";
                container config {
                    description
                        "config attribute for preferring sr-label over LDP";
                    uses prefer-sr-config;
                } // END of config-container definition.
                container state {
                    config false;
                    description
                        "State attribute to describe preference of sr-label over LDP";
                    uses prefer-sr-config;
                } // END of state-container definition.
            } // END of sr-prefer-over-ldp-container definition.
            container bindings {
                description
                    "prefix to sid bindings";
                container mapping-server {
                    description
                        "Configuration and state information of mapping-server entries.";
                    container config {
                        presence "yes";
                        description
                            "config parameters for mapping-server entries";
                        leaf enable  {
                            type  empty;
                            mandatory true;
                            description "To enable mapping server configuration";
                        } // END of enable definition.

                    } // END of config-container definition.
                    container state {
                        config false;
                        description
                            "Operational parameters for mapping-server entries";
                        leaf enable  {
                            type  empty;
                            mandatory true;
                            description "To enable mapping server configuration";
                        } // END of enable definition.

                    } // END of state-container definition.
                    container srms-preferenece {
                        when " /ipi-segment-routing:segment-routing/ipi-segment-routing:sr-mpls/ipi-segment-routing:bindings/ipi-segment-routing:mapping-server/ipi-segment-routing:config/ipi-segment-routing:enable ";
                        description
                            "The SRMS preference TLV is               used to advertise a
                                    preference associated with the node that acts               as an SR
                                    Mapping Server";
                        container config {
                            description
                                "container used to configure preference value associated with node that
                                        acts as an Mapping server";
                            uses srms-preference-value-config;
                        } // END of config-container definition.
                        container state {
                            config false;
                            description
                                "Operational parameters of SRMS preference TLV";
                            uses srms-preference-value-config;
                        } // END of state-container definition.
                    } // END of srms-preferenece-container definition.
                    container prefix-sid-map-ipv4 {
                        when " /ipi-segment-routing:segment-routing/ipi-segment-routing:sr-mpls/ipi-segment-routing:bindings/ipi-segment-routing:mapping-server/ipi-segment-routing:config/ipi-segment-routing:enable ";
                        description
                            "mapping-server entries.";
                        container config {
                            presence "yes";
                            description
                                "Config parameters to enable mapping server configuration";
                            leaf enable  {
                                type  empty;
                                mandatory true;
                                description "To enable ipv4 mapping server configuration";
                            } // END of enable definition.

                        } // END of config-container definition.
                        container state {
                            config false;
                            description
                                "Operational information of mapping server";
                            leaf enable  {
                                type  empty;
                                mandatory true;
                                description "To enable ipv4 mapping server configuration";
                            } // END of enable definition.

                        } // END of state-container definition.
                        container mapping-entries {
                            description
                                "Mapping entries container";

                            list mapping-entry {
                            when " /ipi-segment-routing:segment-routing/ipi-segment-routing:sr-mpls/ipi-segment-routing:bindings/ipi-segment-routing:mapping-server/ipi-segment-routing:prefix-sid-map-ipv4/ipi-segment-routing:config/ipi-segment-routing:enable ";
                                key "start-address start-sid";
                                description
                                    "This objectlist contains config and state parameters for mapping
                                                entries";
                                leaf start-address  {
                                    type  leafref {
                                        path  "../config/start-address";
                                    }
                                    description "connected prefix for prefix-sid";
                                } // END of start-address definition.

                                leaf start-sid  {
                                    type  leafref {
                                        path  "../config/start-sid";
                                    }
                                    description "Starting Segment Identifier";
                                } // END of start-sid definition.

                                container config {
                                    description
                                        "this container contains configuration parameters for mapping entries";
                                    uses ipv4-mapping-entry-properties-config;
                                    uses mapping-entry-common-properties-config;
                                } // END of config-container definition.
                                container state {
                                    config false;
                                    description
                                        "this container contains operational parameters for mapping entries";
                                    uses ipv4-mapping-entry-properties-config;
                                    uses mapping-entry-common-properties-config;
                                } // END of state-container definition.
                                container ipv4-table {
                                    config false;
                                    description
                                        "IPv4 SR Mapping Table Attributes";
                                    container state {
                                        config false;
                                        description
                                            "IPv4 SR Mapping-Server Table";
                                        uses srms-ipv4-prefix-sid-map-state;
                                    } // END of state-container definition.
                                } // END of ipv4-table-container definition.
                            } // End of mapping-entry-list
                        } // END of mapping-entries-container definition.
                    } // END of prefix-sid-map-ipv4-container definition.
                } // END of mapping-server-container definition.
            } // END of bindings-container definition.
            container global-block {
                if-feature feature-list:HAVE_SR_MPLS;
                description
                    "Segment routing Global block";
                container config {
                    presence "yes";
                    description
                        "Configurable parameters for SRGB";
                    uses srgb-config;
                } // END of config-container definition.
                container state {
                    config false;
                    description
                        "Operational parameters for SRGB";
                    uses srgb-config;
                } // END of state-container definition.
            } // END of global-block-container definition.
            container local-block {
                if-feature feature-list:HAVE_SR_MPLS;
                description
                    "Segment routing Local block";
                container config {
                    presence "yes";
                    description
                        "Configurable parameters for SRLB";
                    uses srlb-config;
                } // END of config-container definition.
                container state {
                    config false;
                    description
                        "Operational parameters for SRLB";
                    uses srlb-config;
                } // END of state-container definition.
            } // END of local-block-container definition.
        } // END of sr-mpls-container definition.
        container traffic-engineering {
            when " /ipi-segment-routing:segment-routing/ipi-segment-routing:config/ipi-segment-routing:enable ";
            if-feature feature-list:HAVE_SR_POLICY_OR_HAVE_SRV6;
            description
                "Traffic-engineering container for segment routing";
            container config {
                presence "yes";
                description
                    "Segment routing traffic engineering configuration and other CLIs
                            inside traffic enginnering";
                uses te-config;
                uses frr-config;
            } // END of config-container definition.
            container state {
                config false;
                description
                    "Segment routing traffic engineering runtime parameters";
                uses te-config;
                uses frr-config;
            } // END of state-container definition.
            uses attributes-config;
            uses policies-config;
            uses on-demand-nexthops-grouping;
        } // END of traffic-engineering-container definition.
        container srv6 {
            when " /ipi-segment-routing:segment-routing/ipi-segment-routing:config/ipi-segment-routing:enable ";
            if-feature feature-list:HAVE_SRV6;
            description
                "SRv6 container for segment routing";
            container config {
                presence "yes";
                description
                    "Segment routing SRv6 configuration and other CLIs inside srv6";
                uses srv6-config;
            } // END of config-container definition.
            container state {
                config false;
                description
                    "Segment routing V6 runtime parameters";
                uses srv6-config;
            } // END of state-container definition.
            container locators {
                when " /ipi-segment-routing:segment-routing/ipi-segment-routing:srv6/ipi-segment-routing:config/ipi-segment-routing:enable ";
                if-feature feature-list:HAVE_SRV6;
                description
                    "SRv6 container for segment routing";
                container config {
                    presence "yes";
                    description
                        "Segment routing SRv6 locators configuration and other CLIs inside srv6";
                    uses srv6-locators-config;
                } // END of config-container definition.
                container state {
                    config false;
                    description
                        "Segment routing V6 runtime parameters";
                    uses srv6-locators-config;
                } // END of state-container definition.
                uses locators-lists-config;
            } // END of locators-container definition.
            container services-entries {
                config false;
                description
                    "Global SRV6 services entries";

                list services-entry {
                    key "fec-ipv4-prefix service-vrf-id";
                    config false;
                    description
                        "SRv6 services entry";
                    leaf fec-ipv4-prefix  {
                        type  leafref {
                            path  "../state/fec-ipv4-prefix";
                        }
                        description "IPv4 prefix";
                    } // END of fec-ipv4-prefix definition.

                    leaf service-vrf-id  {
                        type  leafref {
                            path  "../state/service-vrf-id";
                        }
                        description "VRF ID";
                    } // END of service-vrf-id definition.

                    container state {
                        config false;
                        description
                            "State Container for SRv6 services entry";
                        uses srv6-services-state;
                    } // END of state-container definition.
                } // End of services-entry-list
            } // END of services-entries-container definition.
            container transport-entries {
                config false;
                description
                    "Global SRv6 transport entries";

                list transport-entry {
                    key "fec";
                    config false;
                    description
                        "SRv6 transport entry";
                    leaf fec  {
                        type  leafref {
                            path  "../state/fec";
                        }
                        description "IPv6 prefix";
                    } // END of fec definition.

                    container state {
                        config false;
                        description
                            "State container for SRv6 transport entry";
                        uses srv6-transport-state;
                    } // END of state-container definition.
                    container ftn-entries {
                        config false;
                        description
                            "SRv6 transport table FTN entries";

                        list ftn-entry {
                            key "vrf-id fec-prefix";
                            config false;
                            description
                                "FTN entries per SRv6 transport entry";
                            leaf vrf-id  {
                                type  leafref {
                                    path  "../state/vrf-id";
                                }
                                description "VRF ID for FTN Entry";
                            } // END of vrf-id definition.

                            leaf fec-prefix  {
                                type  leafref {
                                    path  "../state/fec-prefix";
                                }
                                description "FEC for FTN Entry";
                            } // END of fec-prefix definition.

                            container state {
                                config false;
                                description
                                    "State Container for FTN entries";
                                uses srv6-transport-ftn-state;
                            } // END of state-container definition.
                        } // End of ftn-entry-list
                    } // END of ftn-entries-container definition.
                } // End of transport-entry-list
            } // END of transport-entries-container definition.
            container manager-entries {
                if-feature feature-list:HAVE_SRV6;
                config false;
                description
                    "SRv6 Manager entries";
                container state {
                    config false;
                    description
                        "State Container for SRv6 manager entry";
                    uses srv6-manager-state;
                } // END of state-container definition.
            } // END of manager-entries-container definition.
        } // END of srv6-container definition.
        uses debug-policy-config;
    } // END of segment-routing-container definition.
    } // END of segment-routing-grouping definition.

    uses segment-routing-grouping;

    rpc sr-policy-terminal-debug-all-on {
        if-feature feature-list:HAVE_SR_POLICY_OR_HAVE_SRV6_OR_HAVE_SR_MPLS;
        description "Enable all debugging functions of sr-policy";
    }

    rpc sr-policy-terminal-debug-on {
        if-feature feature-list:HAVE_SR_POLICY_OR_HAVE_SRV6_OR_HAVE_SR_MPLS;
        description "Enable debugging functions of sr-policy";
        input  {
            leaf terminal-debug-options  {
                type ipi-sr-types:sr_te_debug_t;
                mandatory true;
                description "This attribute is used to enable/disable SR Policy debug logs";
            }
        }
    }

    rpc sr-policy-terminal-debug-off {
        if-feature feature-list:HAVE_SR_POLICY_OR_HAVE_SRV6_OR_HAVE_SR_MPLS;
        description "Disable debugging functions of SR Policy";
        input  {
            leaf terminal-debug-options  {
                type ipi-sr-types:sr_te_debug_t;
                mandatory true;
                description "This attribute is used to enable/disable SR Policy debug logs";
            }
        }
    }

    notification sr-policy-oper-state-down {
        if-feature feature-list:HAVE_SR_POLICY_OR_HAVE_SRV6_OR_HAVE_SR_MPLS;

        description "This notification is sent when SR policy oper-state goes down.";

        leaf severity {
            type cml-data-types:cml_notif_severity_t;
            description "Notification severity level (value: MAJOR)";
        }

        leaf eventClass {
            type cml-data-types:cml_notif_class_t;
            description "Notification event class (value: STATE)";
        }

        leaf name {
            type  string;
        description
            "User friendly name of the SR Policy";
        }

        leaf oper-state {
            type ipi-sr-types:srte_policy_oper_state_t;
        description
            "SR policy operational state";
        }
    }

    notification sr-policy-oper-state-up {
        if-feature feature-list:HAVE_SR_POLICY_OR_HAVE_SRV6_OR_HAVE_SR_MPLS;

        description "This notification is sent when SR policy oper-state goes up.";

        leaf severity {
            type cml-data-types:cml_notif_severity_t;
            description "Notification severity level (value: MAJOR)";
        }

        leaf eventClass {
            type cml-data-types:cml_notif_class_t;
            description "Notification event class (value: STATE)";
        }

        leaf name {
            type  string;
        description
            "User friendly name of the SR Policy";
        }

        leaf oper-state {
            type ipi-sr-types:srte_policy_oper_state_t;
        description
            "SR policy operational state";
        }
    }

    notification sr-policy-cp-active {
        if-feature feature-list:HAVE_SR_POLICY_OR_HAVE_SRV6_OR_HAVE_SR_MPLS;

        description "This notification is sent when SR policy candidate-path active.";

        leaf severity {
            type cml-data-types:cml_notif_severity_t;
            description "Notification severity level (value: MAJOR)";
        }

        leaf eventClass {
            type cml-data-types:cml_notif_class_t;
            description "Notification event class (value: STATE)";
        }

        leaf discriminator {
            type  uint32;
        description
            "Candidate path distinguisher, it's taken as a unique
                    identifier for a Local candidate path";
        }

        leaf protocol-origin {
            type ipi-sr-types:srte_protocol_origin_type_type_t;
        description
            "Instantiation mechanism used to create the candidate  path";
        }

        leaf originator {
            type  string;
        description
            "Identifier (concatenation of ASN and node-address) of
                    the node that signalled/instantiated the candidate
                    path on headend";
        }

        leaf name {
            type  string;
        description
            "User friendly name of the SR Policy";
        }

        leaf is-valid {
            type  boolean;
        description
            "Specifies the state of candidate path";
        }
    }

    notification sr-policy-cp-inactive {
        if-feature feature-list:HAVE_SR_POLICY_OR_HAVE_SRV6_OR_HAVE_SR_MPLS;

        description "This notification is sent when SR policy candidate-path in-active.";

        leaf severity {
            type cml-data-types:cml_notif_severity_t;
            description "Notification severity level (value: MAJOR)";
        }

        leaf eventClass {
            type cml-data-types:cml_notif_class_t;
            description "Notification event class (value: STATE)";
        }

        leaf discriminator {
            type  uint32;
        description
            "Candidate path distinguisher, it's taken as a unique
                    identifier for a Local candidate path";
        }

        leaf protocol-origin {
            type ipi-sr-types:srte_protocol_origin_type_type_t;
        description
            "Instantiation mechanism used to create the candidate  path";
        }

        leaf originator {
            type  string;
        description
            "Identifier (concatenation of ASN and node-address) of
                    the node that signalled/instantiated the candidate
                    path on headend";
        }

        leaf name {
            type  string;
        description
            "User friendly name of the SR Policy";
        }

        leaf is-valid {
            type  boolean;
        description
            "Specifies the state of candidate path";
        }
    }

    notification sr-policy-binding-sid-unavailable-event {
        if-feature feature-list:HAVE_SR_POLICY;
        if-feature feature-list:HAVE_SR_POLICY_OR_HAVE_SRV6_OR_HAVE_SR_MPLS;

        description "This notification is sent when the configured binding-sid value for SR policy is conflicting..";

        leaf severity {
            type cml-data-types:cml_notif_severity_t;
            description "Notification severity level (value: MAJOR)";
        }

        leaf eventClass {
            type cml-data-types:cml_notif_class_t;
            description "Notification event class (value: STATE)";
        }

        leaf name {
            type  string;
        description
            "User friendly name of the SR Policy";
        }

        leaf bsid-value {
            type  uint32;
        description
            "configurable value for static binding sid";
        }
    }

}
