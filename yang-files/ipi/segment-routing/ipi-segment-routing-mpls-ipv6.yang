/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-segment-routing-mpls-ipv6.yang
*
*/

submodule ipi-segment-routing-mpls-ipv6 {

    yang-version 1.1;

    belongs-to  ipi-segment-routing { prefix ipi-segment-routing; }

    import ipi-sr-types {
        prefix ipi-sr-types;
        revision-date 2024-03-09;
    }

    organization
        "IP Infusion Inc.";

    contact
        "Address: 3965 Freedom Circle, Suite 200, Santa Clara, CA 95054
         Phone: +1 408-400-1900
         E-mail: support@ipinfusion.com
         Web: http://www.ipinfusion.com/";

    description
        "Segment-routing configurations for MPLS Segments for IPv6 Dataplane";


    revision "2024-02-29" {
        description "Initial release of MPLS Segment Routing for IPv6 Dataplanem";
        reference " 0.1.0.";
    }

    grouping prefix-segment-algo-mpls-ipv6-config {
        description
            "Grouping for MPLS segment-route Prefix configurations for IPv6
                        Dataplane";
        leaf sid-absolute-ipv6  {
            type  uint32 {
                 range "16000..23999"  {
                    description "16000..23999: Supported range 16000 - 23999";
                 }
            }
            description "This attribute is used to configure Segment Route for IPv6 Prefix SID
                        absolute value";
        } // END of sid-absolute-ipv6 definition.

        leaf sid-index-ipv6  {
            type  uint32 {
                 range "0..7999"  {
                    description "0..7999: Supported range 0 - 7999";
                 }
            }
            description "This attribute is used to configure Segment Route for IPv6 Prefix SID
                        index-value";
        } // END of sid-index-ipv6 definition.

        leaf exp-null-ipv6  {
            type  ipi-sr-types:if_sr_prefix_flag_t;
            description "This attribute is used to set expNull for IPv6 Prefix SID";
        } // END of exp-null-ipv6 definition.

        leaf n-flag-clear-ipv6  {
            type  ipi-sr-types:if_sr_n_flag_clear_t;
            description "This attribute is used to set n-flag-clear for IPv6";
        } // END of n-flag-clear-ipv6 definition.

    } // END of prefix-segment-algo-mpls-ipv6-config definition.
    grouping prefix-segment-algo-mpls-ipv6-cmds {
        description
            "MPLS segment-route Prefix-SID/Algorithm commands for IPv6 dataplane.";
    } // END of prefix-segment-algo-mpls-ipv6-cmds definition.


}
