/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-sr-types.yang
*
*/

module ipi-sr-types {

    yang-version 1.1;

    namespace   "http://www.ipinfusion.com/yang/ocnos/ipi-sr-types";

    prefix "ipi-sr-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-sr-types";


    revision "2024-12-09" {
        description "Added data-types for adjacency sid feature";
        reference " 0.8.0.";
    }

    revision "2024-03-09" {
        description "Added debug options for Flexible Algorithm features";
        reference " 0.7.1.";
    }

    revision "2023-09-29" {
        description "Added data-types for Flexible Algorithm features";
        reference " 0.7.0.";
    }

    revision "2022-06-01" {
        description "Updated the yang file with feature";
        reference " 0.6.0.";
    }

    revision "2022-02-14" {
        description "SRv6 GET API Changes";
        reference " 0.5.0.";
    }

    revision "2021-09-03" {
        description "Update descriptions of attribute";
        reference " 0.4.1.";
    }

    revision "2021-02-28" {
        description "Adding support for SR Policy runtime attributes";
        reference " 0.4.0.";
    }

    revision "2020-12-15" {
        description "Change to have data-types in lower case instead of camel case";
        reference " 0.2.0.";
    }

    revision "2020-06-11" {
        description "Initial Version";
        reference " 0.1.0.";
    }



    typedef  sr_adj_proto_type {
        type enumeration {
            enum isis {
                value 1;
                description "isis";
            }
            enum ospf {
                value 2;
                description "ospf";
            }
        }
        description "type definition for SR_ADJ_PROTO_TYPE";
    }

    typedef  sr_sid_value_type_t {
        type enumeration {
            enum index {
                value 1;
                description "Prefix-SID index";
            }
            enum absolute {
                value 2;
                description "Prefix-SID absolute value";
            }
        }
        description "type definition for SR_SID_VALUE_TYPE_T";
    }

    typedef  srte_segment_type_2_t {
        type enumeration {
            enum segment-type-2 {
                value 2;
                description "Segment-descriptor type: SRv6 Prefix";
            }
        }
        description "type definition for SRTE_SEGMENT_TYPE_2_T";
    }

    typedef  srte_segment_type_mpls_t {
        type enumeration {
            enum segment-type-1 {
                value 1;
                description "Segment-descriptor type: SR-MPLS Label";
            }
        }
        description "type definition for SRTE_SEGMENT_TYPE_MPLS_T";
    }

    typedef  srte_segment_type_3_mpls_t {
        type enumeration {
            enum segment-type-3 {
                value 3;
                description "Segment-descriptor type: IPv4 Prefix with optional SR Algorithm";
            }
        }
        description "type definition for SRTE_SEGMENT_TYPE_3_MPLS_T";
    }

    typedef  srte_segment_type_4_mpls_t {
        type enumeration {
            enum segment-type-4 {
                value 4;
                description "Segment-descriptor type: IPv6 Global Prefix with optional SR Algorithm for SR-MPLS";
            }
        }
        description "type definition for SRTE_SEGMENT_TYPE_4_MPLS_T";
    }

    typedef  srte_segment_type_9_srv6_t {
        type enumeration {
            enum segment-type-9 {
                value 9;
                description "Segment-descriptor type: IPv6 Global Prefix with optional SR Algorithm for SRv6";
            }
        }
        description "type definition for SRTE_SEGMENT_TYPE_9_SRV6_T";
    }

    typedef  srte_segment_type_10_srv6_t {
        type enumeration {
            enum segment-type-10 {
                value 10;
                description "Segment-descriptor type: IPv6 Prefix and Interface ID for link endpoints as Local and Remote pair with optional SR Algorithm for SRv6";
            }
        }
        description "type definition for SRTE_SEGMENT_TYPE_10_SRV6_T";
    }

    typedef  srte_segment_type_11_srv6_t {
        type enumeration {
            enum segment-type-11 {
                value 11;
                description "Segment-descriptor type: IPv6 global addresses for link endpoints as Local and Remote pair with optional SR Algorithm for SRv6";
            }
        }
        description "type definition for SRTE_SEGMENT_TYPE_11_SRV6_T";
    }

    typedef  sr_strict_spf_algo_t {
        type enumeration {
            enum spf {
                value 0;
                description "Segment Routing Shortest Path Algorithm";
            }
            enum strict-spf {
                value 1;
                description "Segment Routing Strict Shortest Path Algorithm";
            }
        }
        description "datatype for SPF/Strict-SPF SR Algorithm";
    }

    typedef  sr_flex_algo_t {
        type uint32 {
             range 0..4294967295;
        }
        description "datatype for Flexible Algorithm Number";
    }

    typedef  sr_algo_choice_t {
        type union {
            type sr_strict_spf_algo_t {

            }
            type sr_flex_algo_t {

            }
        }
        description "datatype for segment routing algorithm number";
    }

    typedef  sr_adj_sid_index_t {
        type uint32 {
             range 0..4294967295;
        }
        description "datatype for SPF/Strict-SPF SR Algorithm";
    }

    typedef  sr_adj_sid_absolute_t {
        type uint32 {
             range 0..4294967295;
        }
        description "datatype for Flexible Algorithm Number";
    }

    typedef  sr_adj_sid_choice_t {
        type union {
            type sr_adj_sid_index_t {

            }
            type sr_adj_sid_absolute_t {

            }
        }
        description "datatype for segment routing adjacency SID number";
    }

    typedef  sr_adj_sid_type_t {
        type enumeration {
            enum index {
                value 0;
                description "Adjacency SID index type";
            }
            enum absolute {
                value 1;
                description "Adjacency SID absolute type";
            }
        }
        description "datatype for segment routing adjacency SID type";
    }

    typedef  srte_policy_oper_state_t {
        type enumeration {
            enum up {
                value 1;
                description "SR policy is operationally up";
            }
            enum down {
                value 2;
                description "SR policy is operationally down";
            }
        }
        description "type definition for SRTE_POLICY_OPER_STATE_T";
    }

    typedef  srte_protocol_origin_type_type_t {
        type enumeration {
            enum pcep {
                value 10;
                description "PCEP used as signalling mechanism for the candidate path";
            }
            enum bgp {
                value 20;
                description "BGP used as signalling mechanism for the candidate path";
            }
            enum local {
                value 30;
                description "CLI Yang model via Netconf etc used for candidate path instantiation";
            }
        }
        description "type definition for SRTE_PROTOCOL_ORIGIN_TYPE_TYPE_T";
    }

    typedef  srte_explicite_null_type_t {
        type enumeration {
            enum ipv4 {
                value 1;
                description "IPV4 explicit label";
            }
        }
        description "type definition for SRTE_EXPLICITE_NULL_TYPE_T";
    }

    typedef  srte_ip_constraint_hop_type_t {
        type enumeration {
            enum loose {
                value 0;
                description "Make this constraint loose";
            }
            enum strict {
                value 1;
                description "Make this constraint strict";
            }
        }
        description "type definition for SRTE_IP_CONSTRAINT_HOP_TYPE_T";
    }

    typedef  srte_ip_constraint_hop_filter_type_t {
        type enumeration {
            enum exclude-any {
                value 1;
                description "exclude-any";
            }
            enum include-any {
                value 2;
                description "include-any";
            }
            enum include-all {
                value 3;
                description "include-all";
            }
        }
        description "type definition for SRTE_IP_CONSTRAINT_HOP_FILTER_TYPE_T";
    }

    typedef  srte_cp_metric_type_t {
        type enumeration {
            enum igp {
                value 1;
                description "IGP-Metric";
            }
            enum te {
                value 2;
                description "TE-Metric";
            }
            enum latency {
                value 3;
                description "Latency-Metric";
            }
        }
        description "type definition for SRTE_CP_METRIC_TYPE_T";
    }

    typedef  sr_te_debug_t {
        type bits {
            bit policy {
                position 0;
                description "Policy related information";
            }
            bit cp {
                position 1;
                description "Candidate-Path related information";
            }
            bit pce {
                position 2;
                description "PCE related information";
            }
            bit mpls {
                position 3;
                description "SR-policy MPLS information";
            }
            bit flexalgo {
                position 4;
                description "SR-policy Flexible Algorithm information";
            }
        }
        description "type definition for SR_TE_DEBUG_T";
    }

    typedef  srv6_protocol_state_t {
        type enumeration {
            enum enabled {
                value 1;
                description "enabled";
            }
            enum disabled {
                value 2;
                description "disabled";
            }
        }
        description "type definition for SRV6_PROTOCOL_STATE_T";
    }

    typedef  sr_te_admin_group_type_t {
        type enumeration {
            enum exclude-any {
                value 1;
                description "exclude-any";
            }
            enum include-any {
                value 2;
                description "include-any";
            }
            enum include-all {
                value 3;
                description "include-all";
            }
        }
        description "type definition for SR_TE_ADMIN_GROUP_TYPE_T";
    }

    typedef  sr_te_extended_admin_group_type_t {
        type enumeration {
            enum exclude-any {
                value 1;
                description "exclude-any";
            }
            enum include-any {
                value 2;
                description "include-any";
            }
            enum include-all {
                value 3;
                description "include-all";
            }
        }
        description "type definition for SR_TE_EXTENDED_ADMIN_GROUP_TYPE_T";
    }

    typedef  sr_te_srlg_affinity_type_t {
        type enumeration {
            enum exclude-any {
                value 1;
                description "exclude-any";
            }
            enum include-any {
                value 2;
                description "include-any";
            }
            enum include-all {
                value 3;
                description "include-all";
            }
        }
        description "type definition for SR_TE_SRLG_AFFINITY_TYPE_T";
    }

    typedef  sr_policy_bsid_oper_state {
        type enumeration {
            enum pending {
                value 1;
                description "Oper-state Pending";
            }
            enum programmed {
                value 3;
                description "Oper-state Programmed";
            }
            enum conflict {
                value 4;
                description "Oper-state Conflict";
            }
        }
        description "type definition for SR_POLICY_BSID_OPER_STATE";
    }

    typedef  if_sr_prefix_flag_t {
        type enumeration {
            enum explicit-null {
                value 1;
                description "Set explicit-null";
            }
            enum no-php {
                value 2;
                description "Set no-PHP";
            }
        }
        description "datatype for segment routing prefix flag";
    }

    typedef  if_sr_n_flag_clear_t {
        type enumeration {
            enum n-flag-clear {
                value 1;
                description "Clear n-flag";
            }
        }
        description "datatype for segment routing N flag";
    }

    typedef  sr_dyn_cp_dataplane_type_t {
        type enumeration {
            enum mpls {
                value 1;
                description "MPLS Data-plane";
            }
            enum srv6 {
                value 2;
                description "SRv6 Data-plane";
            }
        }
        description "type definition for SR_DYN_CP_DATAPLANE_TYPE_T";
    }

    typedef  sr_dyn_cp_protection_type_t {
        type enumeration {
            enum protected-only {
                value 1;
                description "SID list must be encoded using protected segments";
            }
            enum protected-prefered {
                value 2;
                description "SID list encoding uses segments preferably protected";
            }
            enum unprotected-only {
                value 3;
                description "SID list must be encoded using unprotected segments";
            }
            enum unprotected-prefered {
                value 4;
                description "SID list encoding uses segments preferably unprotected";
            }
        }
        description "type definition for SR_DYN_CP_PROTECTION_TYPE_T";
    }

    typedef  sr_dyn_cp_disjoint_path_type_t {
        type enumeration {
            enum link {
                value 1;
                description "Computed path is Link-disjoint with the existing path";
            }
            enum node {
                value 2;
                description "Computed path is Node-disjoint with the existing path";
            }
            enum srlg {
                value 3;
                description "Computed path is SRLG-disjoint with the existing path";
            }
            enum srlg-node {
                value 4;
                description "Computed path is both Node and SRLG disjoint with the existing path";
            }
        }
        description "type definition for SR_DYN_CP_DISJOINT_PATH_TYPE_T";
    }

}
