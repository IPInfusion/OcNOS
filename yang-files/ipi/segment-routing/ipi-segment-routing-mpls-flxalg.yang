/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-segment-routing-mpls-flxalg.yang
*
*/

submodule ipi-segment-routing-mpls-flxalg {

    yang-version 1.1;

    belongs-to  ipi-segment-routing { prefix ipi-segment-routing; }

    import feature-list {
        prefix feature-list;
        revision-date 2026-09-15;
    }

    import ipi-sr-types {
        prefix ipi-sr-types;
        revision-date 2024-12-09;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Segment-routing configurations for MPLS Segments with Flexible
                Algorithms";


    revision "2025-05-30" {
        description "Removed delete sequence under config container in adjacency segment and changed suppress cli to suppress-set-cli under adj-sid-proto attribute";
        reference " 0.2.2.";
    }

    revision "2024-12-09" {
        description "Modified existing adjacency-sid cli to handle per proto functionality";
        reference " 0.2.1.";
    }

    revision "2024-08-10" {
        description "Commented out Flex-Algo Adjacency-SID for OcNOS-6.6";
        reference " 0.2.0.";
    }

    revision "2024-06-25" {
        description "Flexible Algorithm capability param added";
        reference " 0.1.4.";
    }

    revision "2024-05-06" {
        description "Added Adjacency Segment configuration containers for Flexible Algorithms";
        reference " 0.1.3.";
    }

    revision "2024-03-09" {
        description "Updated for dependency revisions change";
        reference " 0.1.2.";
    }

    revision "2024-03-05" {
        description "Filled-in all empty help strings";
        reference " 0.1.1.";
    }

    revision "2023-09-29" {
        description "Initial release of MPLS Segment Routing with Flexible Algorithm";
        reference " 0.1.0.";
    }

    grouping sr-te-flex-algo-config {
        description
            "Flexible Algorithm config for SR Policies";
        leaf flex-algo-enable  {
            type  empty;
            description "Enable flexible algorithm for segment routing polices";
        } // END of flex-algo-enable definition.

    } // END of sr-te-flex-algo-config definition.
    grouping adjacency-segment-def-algo-config {
        description
            "Grouping for MPLS segment-routing Adjacency configurations";
        leaf adj-sid-proto  {
            type  ipi-sr-types:sr_adj_proto_type;
            description "This attribute is used to handle adjacency sid per proto configuration";
        } // END of adj-sid-proto definition.

        leaf adj-sid-absolute  {
            type  uint32 {
                 range "16..1048575"  {
                    description "16..1048575: Supported range 16 - 1048575";
                 }
            }
            description "This attribute is used to configure Segment Route adjacency SID
                        absolute value";
        } // END of adj-sid-absolute definition.

        leaf adj-sid-index  {
            type  uint32 {
                 range "0..1048575"  {
                    description "0..1048575: Supported range 0 - 1048575";
                 }
            }
            description "This attribute is used to configure Segment Route adjacency SID
                        index-value";
        } // END of adj-sid-index definition.

    } // END of adjacency-segment-def-algo-config definition.
    grouping adjacency-segment-flex-algo-config {
        description
            "Grouping for MPLS segment-route adjacency configurations";
        leaf algorithm-num  {
            type  ipi-sr-types:sr_algo_choice_t;
            description "SR-Algorithm number";
        } // END of algorithm-num definition.

        leaf adj-sid-multi  {
            type  ipi-sr-types:sr_adj_sid_choice_t;
            description "This attribute is used to configure Segment Route Adjacency SID value";
        } // END of adj-sid-multi definition.

        leaf adj-sid-type  {
            type  ipi-sr-types:sr_adj_sid_type_t;
            description "This attribute is used to display Segment Route Adjacency SID type";
        } // END of adj-sid-type definition.

    } // END of adjacency-segment-flex-algo-config definition.
    grouping prefix-segment-algorithm-config {
        description
            "Grouping for MPLS segment-route Prefix configurations";
        leaf algorithm-num  {
            type  ipi-sr-types:sr_algo_choice_t;
            description "SR-Algorithm number";
        } // END of algorithm-num definition.

        leaf sid-absolute  {
            type  uint32 {
                 range "16..1048575"  {
                    description "16..1048575: Supported range 16 - 1048575";
                 }
            }
            description "This attribute is used to configure Segment Route Prefix SID absolute
                        value";
        } // END of sid-absolute definition.

        leaf sid-index  {
            type  uint32 {
                 range "0..1048575"  {
                    description "0..1048575: Supported range 0 - 1048575";
                 }
            }
            description "This attribute is used to configure Segment Route Prefix SID
                        index-value";
        } // END of sid-index definition.

        leaf exp-null  {
            type  ipi-sr-types:if_sr_prefix_flag_t;
            description "This attribute describes except Null";
        } // END of exp-null definition.

        leaf n-flag-clear  {
            type  ipi-sr-types:if_sr_n_flag_clear_t;
            description "This attribute is used to set n-flag-clear";
        } // END of n-flag-clear definition.

    } // END of prefix-segment-algorithm-config definition.
    grouping adjacency-segment-def-algo-top {
        description
            "Grouping for MPLS segment-route adjacency configurations";
        container adjacency-segments {
            if-feature feature-list:HAVE_SR_MPLS;
            description
                "MPLS segment-route adjacency";

            list adjacency-segment {
            // when " ipi-interface:interfaces/interface/config/enable-switchport != '1' ";
                key "adj-sid-proto";
                description
                    "MPLS segment-route adjacency sid proto";
                leaf adj-sid-proto  {
                    type  leafref {
                        path  "../config/adj-sid-proto";
                    }
                    description "This attribute is used to configure Segment Route adjacency SID
                                absolute value";
                } // END of adj-sid-proto definition.

                container config {
                    description
                        "Configuration data for segment-route adjacency module";
                    uses adjacency-segment-def-algo-config;
                } // END of config-container definition.
                container state {
                    config false;
                    description
                        "Operational state data for segment-route prefix module";
                    uses adjacency-segment-def-algo-config;
                } // END of state-container definition.
            } // End of adjacency-segment-list
        } // END of adjacency-segments-container definition.
    } // END of adjacency-segment-def-algo-top definition.
    grouping adjacency-segment-flex-algo-top {
        description
            "Grouping for MPLS segment-route adjacency configurations";
        container adjacency-segment-flex-algos {
            if-feature feature-list:HAVE_SR_MPLS;
            description
                "MPLS segment-route Adjacency-SID/Algorithm list";

            list adjacency-segment-flex-algo {
            // when " ipi-interface:interfaces/interface/config/enable-switchport != '1' ";
                key "algorithm-num adj-sid-multi";
                description
                    "MPLS segment-route Adjacency-SID/Algorithm pair";
                leaf algorithm-num  {
                    type  leafref {
                        path  "../config/algorithm-num";
                    }
                    description "SR-Algorithm number";
                } // END of algorithm-num definition.

                leaf adj-sid-multi  {
                    type  leafref {
                        path  "../config/adj-sid-multi";
                    }
                    description "SR Adjacency SID value";
                } // END of adj-sid-multi definition.

                container config {
                    // when " ../config/adj-sid-multi ";
                    description
                        "Configuration data for segment-route adjacency module";
                    uses adjacency-segment-flex-algo-config;
                } // END of config-container definition.
                container state {
                    config false;
                    description
                        "Operational state data for segment-route adjacency module";
                    uses adjacency-segment-flex-algo-config;
                } // END of state-container definition.
            } // End of adjacency-segment-flex-algo-list
        } // END of adjacency-segment-flex-algos-container definition.
    } // END of adjacency-segment-flex-algo-top definition.
    grouping prefix-segment-algorithm-top {
        description
            "Grouping for MPLS segment-route Prefix-SID/Algorithm configurations";
        container prefix-segment-algorithms {
            if-feature feature-list:HAVE_SR_MPLS;
            description
                "MPLS segment-route Prefix-SID/Algorithm list";

            list prefix-segment-algorithm {
            // when " ipi-interface:interfaces/interface/config/enable-switchport != '1' ";
                key "algorithm-num";
                description
                    "MPLS segment-route Prefix-SID/Algorithm pair";
                leaf algorithm-num  {
                    type  leafref {
                        path  "../config/algorithm-num";
                    }
                    description "SR-Algorithm number";
                } // END of algorithm-num definition.

                container config {
                    // when " ../config/sid-index or ../config/sid-absolute ";
                    description
                        "Configuration data for segment-route prefix module";
                    uses prefix-segment-algorithm-config;
                } // END of config-container definition.
                container state {
                    config false;
                    description
                        "Operational state data for segment-route prefix module";
                    uses prefix-segment-algorithm-config;
                } // END of state-container definition.
            } // End of prefix-segment-algorithm-list
        } // END of prefix-segment-algorithms-container definition.
    } // END of prefix-segment-algorithm-top definition.
    grouping segment-type-3-properties-common-config {
        description
            "Common properties of segment which includes it's index value and it's
                        type.";
        leaf segment-index  {
            type  uint32 {
                 range "1..65535"  {
                    description "1..65535: Supported range 1 - 65535";
                 }
            }
            description "Index of the segment through which it can be modified or unconfigured";
        } // END of segment-index definition.

        leaf type  {
            type  ipi-sr-types:srte_segment_type_3_mpls_t;
            description "Type of the segment";
        } // END of type definition.

        leaf prefix  {
            type  inet:ipv4-address;
            description "IPv4 Prefix";
        } // END of prefix definition.

    } // END of segment-type-3-properties-common-config definition.
    grouping segment-type-4-properties-common-config {
        description
            "Common properties of segment which includes it's index value and it's
                        type.";
        leaf segment-index  {
            type  uint32 {
                 range "1..65545"  {
                    description "1..65545: Supported range 1 - 65545";
                 }
            }
            description "Index of the segment through which it can be modified or unconfigured";
        } // END of segment-index definition.

        leaf type  {
            type  ipi-sr-types:srte_segment_type_4_mpls_t;
            description "Type of the segment";
        } // END of type definition.

        leaf prefix  {
            type  inet:ipv6-address;
            description "IPv6 Prefix";
        } // END of prefix definition.

    } // END of segment-type-4-properties-common-config definition.
    grouping segment-type-3-properties-specific-config {
        description
            "grouping for the properties of segment type 3";
        leaf algorithm-num  {
            type  ipi-sr-types:sr_algo_choice_t;
            description "SR-Algorithm Number";
        } // END of algorithm-num definition.

    } // END of segment-type-3-properties-specific-config definition.
    grouping segment-type-4-properties-specific-config {
        description
            "grouping for the properties of segment type 4";
        leaf algorithm-num  {
            type  ipi-sr-types:sr_algo_choice_t;
            description "SR-Algorithm Number";
        } // END of algorithm-num definition.

    } // END of segment-type-4-properties-specific-config definition.
    grouping segment-type-3-definitions {
        description
            "grouping for the Segment-Type-3 Definitions";

        list segment-mpls-type-3 {
            key "segment-index type prefix";
            description
                "Properties of a type-3 segment";
            leaf segment-index  {
                type  leafref {
                    path  "../config/segment-index";
                }
                description "Index of the segment through which it can be modified or unconfigured";
            } // END of segment-index definition.

            leaf type  {
                type  leafref {
                    path  "../config/type";
                }
                description "Type of the segment";
            } // END of type definition.

            leaf prefix  {
                type  leafref {
                    path  "../config/prefix";
                }
                description "IPv4 Prefix of the segment";
            } // END of prefix definition.

            container config {
                description
                    "Contains config parameters for configuring segment index and type";
                uses segment-type-3-properties-common-config;
            } // END of config-container definition.
            container state {
                config false;
                description
                    "Contains operational information about segment index and type";
                uses segment-type-3-properties-common-config;
            } // END of state-container definition.
            container segment-type-3 {
                description
                    "Segment declared by IPv4 Prefix and optional SR Algorithm";
                container config {
                    description
                        "Contains parameters to configure segment-type-3";
                    uses segment-type-3-properties-specific-config;
                } // END of config-container definition.
                container state {
                    config false;
                    description
                        "Contains operational information regarding segment-type-3";
                    uses segment-type-3-properties-specific-config;
                } // END of state-container definition.
            } // END of segment-type-3-container definition.
        } // End of segment-mpls-type-3-list
    } // END of segment-type-3-definitions definition.
    grouping segment-type-4-definitions {
        description
            "grouping for the Segment-Type-4 Definitions";

        list segment-mpls-type-4 {
            key "segment-index type prefix";
            description
                "Properties of a type-4 segment";
            leaf segment-index  {
                type  leafref {
                    path  "../config/segment-index";
                }
                description "Index of the segment through which it can be modified or unconfigured";
            } // END of segment-index definition.

            leaf type  {
                type  leafref {
                    path  "../config/type";
                }
                description "Type of the segment";
            } // END of type definition.

            leaf prefix  {
                type  leafref {
                    path  "../config/prefix";
                }
                description "IPv6 Prefix of the segment";
            } // END of prefix definition.

            container config {
                description
                    "Contains config parameters for configuring segment index and type";
                uses segment-type-4-properties-common-config;
            } // END of config-container definition.
            container state {
                config false;
                description
                    "Contains operational information about segment index and type";
                uses segment-type-4-properties-common-config;
            } // END of state-container definition.
            container segment-type-4 {
                description
                    "Segment declared by IPv4 Prefix and optional SR Algorithm";
                container config {
                    description
                        "Contains parameters to configure segment-type-4";
                    uses segment-type-4-properties-specific-config;
                } // END of config-container definition.
                container state {
                    config false;
                    description
                        "Contains operational information regarding segment-type-4";
                    uses segment-type-4-properties-specific-config;
                } // END of state-container definition.
            } // END of segment-type-4-container definition.
        } // End of segment-mpls-type-4-list
    } // END of segment-type-4-definitions definition.


}
