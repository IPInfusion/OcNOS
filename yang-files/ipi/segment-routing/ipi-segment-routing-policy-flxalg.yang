/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-segment-routing-policy-flxalg.yang
*
*/

submodule ipi-segment-routing-policy-flxalg {

    yang-version 1.1;

    belongs-to  ipi-segment-routing { prefix ipi-segment-routing; }

    import ipi-sr-types {
        prefix ipi-sr-types;
        revision-date 2024-12-09;
    }

    organization
        "IP Infusion Inc.";

    contact
        "Address: 3965 Freedom Circle, Suite 200, Santa Clara, CA 95054
         Phone: +1 408-400-1900
         E-mail: support@ipinfusion.com
         Web: http://www.ipinfusion.com/";

    description
        "Segment-routing Policy configurations for Flexible Algorithms";


    revision "2024-12-05" {
        description "Changed SR-policy Algorithm parameter to hidden";
        reference " 0.1.7.";
    }

    revision "2024-06-25" {
        description "Unhide the SR-policy Algorithm parameter";
        reference " 0.1.6.";
    }

    revision "2024-04-03" {
        description "Updated history since Jenkins Build failed";
        reference " 0.1.5.";
    }

    revision "2024-03-13" {
        description "Added Flexible Algorithm global config Enable/Disable";
        reference " 0.1.4.";
    }

    revision "2024-03-09" {
        description "Corrected CLI SEGRULE mode name";
        reference " 0.1.3.";
    }

    revision "2024-03-05" {
        description "Filled-in all empty help strings";
        reference " 0.1.2.";
    }

    revision "2024-02-29" {
        description "Changed all Segement-Rule and Protection-Group CLI commands to hidden";
        reference " 0.1.1.";
    }

    revision "2023-09-29" {
        description "Initial release of Segment Routing Policy with Flexible Algorithm";
        reference " 0.1.0.";
    }

    grouping sr-dyn-cp-segment-rule-config {
        description
            "Configuration to change to dynamic-CP segment-rule mode";
        leaf enable  {
            type  empty;
            mandatory true;
            description "Enable segment constraints for the dynamic candidate path";
        } // END of enable definition.

    } // END of sr-dyn-cp-segment-rule-config definition.
    grouping sr-dyn-cp-cons-segrule-parameters-config {
        description
            "grouping for the properties of SR-policy dynamic CP segment properties";
        leaf dataplane-type  {
            type  ipi-sr-types:sr_dyn_cp_dataplane_type_t;
            description "SR policy dynamic candidate path's data-plane type";
        } // END of dataplane-type definition.

        leaf sid-algorithm  {
            type  uint32 {
                 range "128..255"  {
                    description "128..255: Supported range 128 - 255";
                 }
            }
            description "Flexible Algorithm Number";
        } // END of sid-algorithm definition.

        leaf protection-type  {
            type  ipi-sr-types:sr_dyn_cp_protection_type_t;
            description "SR policy dynamic candidate path's protection type";
        } // END of protection-type definition.

    } // END of sr-dyn-cp-cons-segrule-parameters-config definition.
    grouping sr-dyn-cp-cons-disjoint-path-config {
        description
            "grouping for the properties of SR-policy dynamic CP path disjointness
                        constraints";
        leaf group-id  {
            type  uint32 {
                 range "1..65535"  {
                    description "1..65535: Supported range 1 - 65535";
                 }
            }
            description "Disjoint path group id";
        } // END of group-id definition.

        leaf disjoint-type  {
            type  ipi-sr-types:sr_dyn_cp_disjoint_path_type_t;
            description "SR policy dynamic candidate path's disjointness type";
        } // END of disjoint-type definition.

        leaf sub-id  {
            type  uint32 {
                 range "1..65535"  {
                    description "1..65535: Supported range 1 - 65535";
                 }
            }
            description "Disjoint path sub-group id";
        } // END of sub-id definition.

    } // END of sr-dyn-cp-cons-disjoint-path-config definition.
    grouping sr-dyn-cp-cons-segrule-property {
        description
            "grouping for the properties of SR-policy dynamic CP segment properties";
        container property {
            description
                "Segment constraints for candidate path which needs to be satisfied by
                        computation engine when calculating a segment-list for the dynamic-CP";
            container config {
                presence "yes";
                description
                    "constraint segment property config container";
                uses sr-dyn-cp-cons-segrule-parameters-config;
            } // END of config-container definition.
            container state {
                config false;
                description
                    "constraint segment property state container";
                uses sr-dyn-cp-cons-segrule-parameters-config;
            } // END of state-container definition.
        } // END of property-container definition.
    } // END of sr-dyn-cp-cons-segrule-property definition.
    grouping sr-dyn-cp-cons-segrule-top {
        description
            "grouping for SR-policy dynamic CP constraints segment-rule top-level";
        container segment-rule {
            // when " ipi-segment-routing:segment-routing/traffic-engineering/policies/policy/candidate-paths/candidate-path/dynamic/constraints/segment-rule/config/enable ";
            description
                "Segment-rule constraints for candidate path which needs to be
                        satisfied by computation engine when calculating a segment-list for
                        the dynamic-CP";
            container config {
                presence "yes";
                description
                    "constraint segment-rule config container";
                uses sr-dyn-cp-segment-rule-config;
            } // END of config-container definition.
            container state {
                config false;
                description
                    "constraint segment-rule state container";
                uses sr-dyn-cp-segment-rule-config;
            } // END of state-container definition.
            uses sr-dyn-cp-cons-segrule-property;
        } // END of segment-rule-container definition.
    } // END of sr-dyn-cp-cons-segrule-top definition.
    grouping sr-dyn-cp-cons-disjoint-path-top {
        description
            "Top Level grouping for the SR-policy dynamic CP disjointness
                        properties";
        container disjoint-paths {
            // when " ipi-segment-routing:segment-routing/traffic-engineering/policies/policy/candidate-paths/candidate-path/dynamic/constraints/disjoint-paths/disjoint-path/config/sub-id ";
            description
                "Disjointness constraints for dynamic candidate path, to be satisfied
                        during path calculation";

            list disjoint-path {
                key "group-id disjoint-type";
                description
                    "list of disjoint path";
                leaf group-id  {
                    type  leafref {
                        path  "../config/group-id";
                    }
                    description "Disjoint path group id";
                } // END of group-id definition.

                leaf disjoint-type  {
                    type  leafref {
                        path  "../config/disjoint-type";
                    }
                    description "SR policy dynamic candidate path's disjointness type";
                } // END of disjoint-type definition.

                container config {
                    presence "yes";
                    description
                        "constraint path-disjointness config container";
                    uses sr-dyn-cp-cons-disjoint-path-config;
                } // END of config-container definition.
                container state {
                    config false;
                    description
                        "constraint path-disjointness state container";
                    uses sr-dyn-cp-cons-disjoint-path-config;
                } // END of state-container definition.
            } // End of disjoint-path-list
        } // END of disjoint-paths-container definition.
    } // END of sr-dyn-cp-cons-disjoint-path-top definition.


}
