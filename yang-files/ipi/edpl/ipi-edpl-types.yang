/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-edpl-types.yang
*
*/

module ipi-edpl-types {

    yang-version 1.1;

    namespace   "http://www.ipinfusion.com/yang/ocnos/ipi-edpl-types";

    prefix "ipi-edpl-types";

    organization
        "IP Infusion Inc.";

    contact
        "Address: 3965 Freedom Circle, Suite 200, Santa Clara, CA 95054
         Phone: +1 408-400-1900
         E-mail: support@ipinfusion.com
         Web: http://www.ipinfusion.com/";

    description
        "Service Authentication Test";


    revision "2025-10-10" {
        description "Removed EDPL_MAC_ADDR_T and EDPL_IP_ADDR_T";
        reference " 0.1.1.";
    }

    revision "2025-06-09" {
        description "Initial version";
        reference " 0.1.0.";
    }



    typedef  edpl_direction_t {
        type enumeration {
            enum upstream {
                value 1;
                description "Configure upstream";
            }
            enum downstream {
                value 2;
                description "Configure downstream";
            }
        }
        description "type definition for EDPL_DIRECTION_T";
    }

    typedef  edpl_addr_family_t {
        type enumeration {
            enum l2 {
                value 1;
                description "Configure L2";
            }
            enum ipv4 {
                value 2;
                description "Configure IPV4";
            }
            enum ipv6 {
                value 3;
                description "Configure IPV6";
            }
        }
        description "type definition for EDPL_ADDR_FAMILY_T";
    }

    typedef  edpl_test_action_t {
        type enumeration {
            enum start {
                value 1;
                description "Start EDPL test";
            }
            enum stop {
                value 2;
                description "Stop EDPL test";
            }
        }
        description "type definition for EDPL_TEST_ACTION_T";
    }

}
