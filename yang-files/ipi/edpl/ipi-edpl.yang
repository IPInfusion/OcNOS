/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-edpl.yang
*
*/

module ipi-edpl {

    yang-version 1.1;

    namespace   "http://www.ipinfusion.com/yang/ocnos/ipi-edpl";

    prefix "ipi-edpl";

    import cml-data-types {
        prefix cml-data-types;
        revision-date 2026-05-15;
    }

    import ietf-inet-types {
        prefix inet;
        revision-date 2013-07-15;
    }

    import ipi-edpl-types {
        prefix ipi-edpl-types;
        revision-date 2025-10-10;
    }

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Ethernet dataplane Loopback";


    revision "2025-10-27" {
        description "Corrected the pattern for ethertype attribute";
        reference " 0.1.3.";
    }

    revision "2025-10-10" {
        description "Removed added datatypes for mac,ip and used the existing ones";
        reference " 0.1.2.";
    }

    revision "2025-09-25" {
        description "Changed max vlan-id to 4095 in EDPL profile";
        reference " 0.1.1.";
    }

    revision "2025-07-14" {
        description "Initial Version";
        reference " 0.1.0.";
    }

    grouping edpl-test-execution-top {
        description
            "Top level grouping for EDPL test execution";
        container execution {
            description
                "Container for EDPL test execution";
            container state {
                config false;
                description
                    "Operational state data for EDPL test execution";
                uses edpl-execution-state;
            } // END of state-container definition.
        } // END of execution-container definition.
    } // END of edpl-test-execution-top definition.
    grouping edpl-execution-state {
        description
            "Grouping for EDPL test execution data";
        leaf test-direction  {
            type  ipi-edpl-types:edpl_direction_t;
            description "This attribute specifies the direction as upstream or downstream";
        } // END of test-direction definition.

        leaf address-family  {
            type  ipi-edpl-types:edpl_addr_family_t;
            description "This attribute specifies the family type as l2/ipv4/ipv6";
        } // END of address-family definition.

        leaf logical-if-name  {
            type  string {
                length "1..1965";
            }
            description "This attributes specifies the logical interface name for the test";
        } // END of logical-if-name definition.

        leaf src-if-name  {
            type  string {
                length "1..1965";
            }
            description "This attributes specifies the source interface name for the test";
        } // END of src-if-name definition.

        leaf dst-mac  {
            type  string {
                length "1..1965";
            }
            description "This attributes specifies the destination MAC address for the test";
        } // END of dst-mac definition.

        leaf vlan  {
            type  uint16;
            description "This attributes specifies the vlan for the test";
        } // END of vlan definition.

        leaf ethtype  {
            type  string {
                length "1..1965";
            }
            description "This attributes specifies the ethertype for the test";
        } // END of ethtype definition.

        leaf src-ip  {
            type  string {
                length "1..1965";
            }
            description "This attribute specifies the source ip Filters for EDPL test";
        } // END of src-ip definition.

        leaf dst-ip  {
            type  string {
                length "1..1965";
            }
            description "This attribute specifies the Destination ip Filters for EDPL test";
        } // END of dst-ip definition.

        leaf src-udp-port  {
            type  uint16;
            description "This attribute specifies the source UDP port Filters for EDPL test";
        } // END of src-udp-port definition.

        leaf dst-udp-port  {
            type  uint16;
            description "This attribute specifies the Destination UDP port  Filters for EDPL
                        test";
        } // END of dst-udp-port definition.

        leaf action-ip-swap  {
            type  string {
                length "1..1965";
            }
            description "This attribute specifies the action as ip swap for  EDPL test";
        } // END of action-ip-swap definition.

        leaf action-udp-tcp-port-swap  {
            type  string {
                length "1..1965";
            }
            description "This attribute specifies the action as UDP TCP port swap for  EDPL
                        test";
        } // END of action-udp-tcp-port-swap definition.

        leaf start-time  {
            type  string {
                length "1..1965";
            }
            description "Specifies the start time for EDPL";
        } // END of start-time definition.

        leaf end-time  {
            type  string {
                length "1..1965";
            }
            description "Specifies the End time for EDPL";
        } // END of end-time definition.

        leaf perpetual-time  {
            type  empty;
            description "Specifies the continuous run for EDPL";
        } // END of perpetual-time definition.

    } // END of edpl-execution-state definition.
    grouping edpl-test-timer-top {
        description
            "Top level grouping for EDPL test timer configuration data";
        container timer {
            description
                "container for Test timer";
            container config {
                presence "yes";
                description
                    "test profile structure for config parameters";
                uses edpl-test-timer-config;
            } // END of config-container definition.
            container state {
                config false;
                description
                    "synce Operational state data";
                uses edpl-test-timer-config;
            } // END of state-container definition.
        } // END of timer-container definition.
    } // END of edpl-test-timer-top definition.
    grouping edpl-test-config {
        description
            "Grouping for EDPL test configuration data";
        leaf name  {
            type  string {
                length "1..32";
                pattern "[^?' =,>|]+";
            }
            description "EDPL test name";
        } // END of name definition.

        leaf profile  {
            type  leafref {
                path  "/edpl/profiles/profile/config/name";
            }
            description "Specify the EDPL profile filter name";
        } // END of profile definition.

        leaf source-port  {
            type  leafref {
                path  "/ipi-interface:interfaces/ipi-interface:interface/ipi-interface:name";
            }
            description "Specify the source port name";
        } // END of source-port definition.

        leaf l2-port  {
            // when " ../source-port ";
            type  leafref {
                path  "/ipi-interface:interfaces/ipi-interface:interface/ipi-interface:name";
            }
            description "Specify the L2 port name";
        } // END of l2-port definition.

    } // END of edpl-test-config definition.
    grouping edpl-test-timer-config {
        description
            "Grouping for EDPL test Timer Configuration data";
        leaf duration  {
            type  empty;
            mandatory true;
            description "Used to set the test duration";
        } // END of duration definition.

        leaf hours  {
            // when " ../duration ";
            type  uint8 {
                 range "1..60"  {
                    description "1..60: Supported range 1 - 60";
                 }
            }
            description "Set the test time in terms of hours";
        } // END of hours definition.

        leaf minutes  {
            // when " ../duration ";
            type  uint8 {
                 range "1..60"  {
                    description "1..60: Supported range 1 - 60";
                 }
            }
            description "Set the test time in terms of minutes";
        } // END of minutes definition.

        leaf seconds  {
            // when " ../duration ";
            type  uint8 {
                 range "1..60"  {
                    description "1..60: Supported range 1 - 60";
                 }
            }
            description "Set the test time in terms of seconds";
        } // END of seconds definition.

    } // END of edpl-test-timer-config definition.
    grouping edpl-test-top {
        description
            "Top level grouping for EDPL test";
        container tests {
            description
                "Container for EDPL test configuration";

            list test {
                key "name";
                description
                    "List of EDPL test configuration";
                leaf name  {
                    type  leafref {
                        path  "../config/name";
                    }
                    description "Specifies EDPL test name";
                } // END of name definition.

                container config {
                    description
                        "Configuration data for EDPL test";
                    uses edpl-test-config;
                } // END of config-container definition.
                container state {
                    config false;
                    description
                        "Operational data for EDPL test";
                    uses edpl-test-config;
                } // END of state-container definition.
                uses edpl-test-timer-top;
                uses edpl-test-execution-top;
            } // End of test-list
        } // END of tests-container definition.
    } // END of edpl-test-top definition.
    grouping edpl-profile-config {
        description
            "Grouping for EDPL Profile Configuration data";
        leaf name  {
            type  string {
                length "1..1965";
                pattern "[^?' =,>|]+";
            }
            description "EDPL profile name";
        } // END of name definition.

        leaf direction  {
            type  ipi-edpl-types:edpl_direction_t;
            description "Used to map the direction as upstream/downstream";
        } // END of direction definition.

        leaf dst-mac  {
            type  cml-data-types:cml_mac_addr_t {
                length "1..1965";
            }
            description "Specify the destination MAC address";
        } // END of dst-mac definition.

        leaf vlan-id  {
            type  uint16 {
                 range "0..4095"  {
                    description "0..4095: Supported range 0 - 4095";
                 }
            }
            description "Specify the VLAN Identifier";
        } // END of vlan-id definition.

        leaf ip-swap  {
            type  empty;
            description "Enable ip swap";
        } // END of ip-swap definition.

        leaf udp-tcp-port-swap  {
            type  empty;
            description "Enable UDP/TCP port swap";
        } // END of udp-tcp-port-swap definition.

        leaf source-udp-port  {
            type  uint16;
            description "Specify the source udp port";
        } // END of source-udp-port definition.

        leaf destination-udp-port  {
            type  uint16;
            description "Specify the destination udp port";
        } // END of destination-udp-port definition.

        leaf ethertype  {
            type  string {
                length "5..6";
                pattern "0x([1-9a-f][0-9a-f]{3}|[6-9a-f][0-9a-f]{2})";
            }
            description "Use this attribute to classify traffic based on the EtherType value";
        } // END of ethertype definition.

        leaf address-family  {
            type  ipi-edpl-types:edpl_addr_family_t;
            description "Use this attribute to specify address-family";
        } // END of address-family definition.

        leaf src-ip  {
            type  inet:ip-address;
            description "Specify the source ip address";
        } // END of src-ip definition.

        leaf dst-ip  {
            type  inet:ip-address;
            description "Specify the destination ip address";
        } // END of dst-ip definition.

    } // END of edpl-profile-config definition.
    grouping edpl-profile-top {
        description
            "Top Level Grouping for EDPL profile top grouping";
        container profiles {
            description
                "Container for EDPL profile";

            list profile {
                key "name";
                description
                    "List of EDPL profile";
                leaf name  {
                    type  leafref {
                        path  "../config/name";
                    }
                    description "EDPL profile name";
                } // END of name definition.

                container config {
                    description
                        "Configuration data for EDPL profile";
                    uses edpl-profile-config;
                } // END of config-container definition.
                container state {
                    config false;
                    description
                        "Operational data for EDPL profile";
                    uses edpl-profile-config;
                } // END of state-container definition.
            } // End of profile-list
        } // END of profiles-container definition.
    } // END of edpl-profile-top definition.

    grouping  edpl-grouping {
    description
        "Container for EDPL (Ethernt Data Plane Loopback)";
    container edpl {
        if-feature feature-list:HAVE_ONMD;
        if-feature feature-list:HAVE_EDPL;
        description
            "Container for EDPL (Ethernt Data Plane Loopback)";
        uses edpl-profile-top;
        uses edpl-test-top;
    } // END of edpl-container definition.
    } // END of edpl-grouping definition.

    uses edpl-grouping;

    rpc edpl-test-execute {
        if-feature feature-list:HAVE_ONMD;
        if-feature feature-list:HAVE_EDPL;
        description "Execute edpl test";
        input  {
            leaf edpl-action  {
                type ipi-edpl-types:edpl_test_action_t;
                mandatory true;
                description "Specify the EDPL test action";
            }
            leaf test-name  {
                type string {
                    length "1..32";
                }
                mandatory true;
                description "This attribute specify the EDPL test name";
            }
        }
    }

}
