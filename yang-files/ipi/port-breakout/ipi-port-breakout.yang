/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-port-breakout.yang
*
*/

module ipi-port-breakout {

    yang-version 1.1;

    namespace   "http://www.ipinfusion.com/yang/ocnos/ipi-port-breakout";

    prefix "ipi-port-breakout";

    import ipi-port-breakout-types {
        prefix ipi-port-breakout-types;
        revision-date 2024-10-14;
    }

    import feature-list {
        prefix feature-list;
        revision-date 2026-09-15;
    }

    include ipi-port-breakout-interface { revision-date 2024-01-31;}
    organization
        "IP Infusion Inc.";

    contact
        "Address: 3965 Freedom Circle, Suite 200, Santa Clara, CA 95054
         Phone: +1 408-400-1900
         E-mail: support@ipinfusion.com
         Web: http://www.ipinfusion.com/";

    description
        "Datamodel for Layer-2 Port Breakout";


    revision "2025-12-12" {
        description "Added is-bitmap-check-enable flag to fix the value assigned to the serdes attribute when it is not provided.";
        reference " 0.5.1.";
    }

    revision "2025-01-31" {
        description "Fixed DB sync issue for Ethernet-800G interface names";
        reference " 0.4.18.";
    }

    revision "2024-12-18" {
        description "Removed 1X200g serdes 25G from Tomahawk5 device";
        reference " 0.4.17.";
    }

    revision "2024-10-21" {
        description "Added port breakout support to Tomahawk5 device";
        reference " 0.4.16.";
    }

    revision "2024-10-14" {
        description "Added port breakout support to Tomahawk5 device";
        reference " 0.4.15.";
    }

    revision "2024-10-10" {
        description "Added port breakout support to Tomahawk5 device";
        reference " 0.4.14.";
    }

    revision "2024-06-26" {
        description "Added custom db trigger for port breakout config create";
        reference " 0.4.13.";
    }

    revision "2024-06-21" {
        description "Added custom db trigger for port breakout config delete";
        reference " 0.4.12.";
    }

    revision "2024-02-26" {
        description "Removed MPLS dependencey and made port breakout config as generic";
        reference " 0.4.11.";
    }

    revision "2024-02-21" {
        description "Added 1X40g port breakout support";
        reference " 0.4.10.";
    }

    revision "2024-02-19" {
        description "Removed 8X50G/8X25G/8X10G port breakout modes from TH4 platform";
        reference " 0.4.9.";
    }

    revision "2024-01-31" {
        description "Updated dependent object xpath as per new hierarchy of vlan-reservation for breakout";
        reference " 0.4.8.";
    }

    revision "2023-11-30" {
        description "Added Changes to switch from one breakout mode to another breakout mode ";
        reference " 0.4.7.";
    }

    revision "2023-10-05" {
        description "Added flags for serdes in port breakout ";
        reference " 0.4.6.";
    }

    revision "2023-09-20" {
        description "Maverick2 port breakout support";
        reference " 0.4.5.";
    }

    revision "2023-07-26" {
        description "Combined breakout and breakout-ifname containers";
        reference " 0.4.4.";
    }

    revision "2023-07-12" {
        description "Restructred port breakout data model";
        reference " 0.4.3.";
    }

    revision "2023-06-22" {
        description "Added changes in xgs port breakout";
        reference " 0.4.2.";
    }

    revision "2023-05-29" {
        description "Restructuredport breakout support for non dune boards";
        reference " 0.4.1.";
    }

    revision "2023-05-17" {
        description "400g port breakout support for TH3 board";
        reference " 0.4.0.";
    }

    revision "2023-04-12" {
        description "Added dependency for port breakout config";
        reference " 0.3.9.";
    }

    revision "2023-03-23" {
        description "400g port breakout support for dnx";
        reference " 0.3.8.";
    }

    revision "2023-03-15" {
        description "Added skip-yang flag in when condition for breakout_dune objectlist";
        reference " 0.3.7.";
    }

    revision "2023-03-01" {
        description "Blocked interface level port breakout for Q2";
        reference " 0.3.6.";
    }

    revision "2023-01-24" {
        description "updated port breakout support with ifname for dnx";
        reference " 0.3.5.";
    }

    revision "2023-01-19" {
        description "Blocked port breakout support for dnx";
        reference " 0.3.4.";
    }

    revision "2022-11-24" {
        description "Added port breakout support for dnx";
        reference " 0.3.2.";
    }

    revision "2022-07-26" {
        description "Added vlan reservation as dependent object for breakout objectlist with flags";
        reference " 0.3.1.";
    }

    revision "2022-07-21" {
        description "Added vlan reservation as dependent object for breakout";
        reference " 0.3.0.";
    }

    revision "2022-06-01" {
        description "Updated the yang file with feature";
        reference " 0.2.0.";
    }

    revision "2022-01-13" {
        description "Added if-not-feature HAVE_DUNE for the dependentObject tag";
        reference " 0.3.3.";
    }

    revision "2021-11-29" {
        description "Restructured port-breakout module in accordance with OpenConfig style";
        reference " 0.1.0.";
    }

    revision "2018-09-17" {
        description "Initial Version";
        reference "Initial Version";
    }

    grouping port-breakout-breakout-state {
        description
            "Grouping for port-breakout operational state data";
        leaf block  {
            type  uint8;
            description "Use this attribute to get port-breakout block operational state data";
        } // END of block definition.

    } // END of port-breakout-breakout-state definition.
    grouping port-breakout-breakout-config {
        description
            "Grouping for port-breakout configuration data";
        leaf interface  {
            type  string {
                length "1..1965";
                pattern "[^?' =,>|]+";
            }
            description "use this attribute to configure the port breakout with Interface
                        name/portnumber";
        } // END of interface definition.

        leaf mode  {
            type  ipi-port-breakout-types:port_breakout_mode_t;
            mandatory true;
            description "Use this attribute to set port breakout mode";
        } // END of mode definition.

        leaf serdes  {
            type  ipi-port-breakout-types:port_breakout_serdes_type_t;
            description "Use this attribute to set the serdes";
        } // END of serdes definition.

    } // END of port-breakout-breakout-config definition.
    grouping port-breakout-breakout-top {
        description
            "Grouping for port-breakout entries";
        container breakouts {
            description
                "Container for port-breakout list configuration";

            list breakout {
                key "interface";
                description
                    "List of port breakout";
                leaf interface  {
                    type  leafref {
                        path  "../config/interface";
                    }
                    description "Name of the interface to breakout";
                } // END of interface definition.

                container config {
                    description
                        "Configuration data for port-breakout entry";
                    uses port-breakout-breakout-config;
                } // END of config-container definition.
                container state {
                    config false;
                    description
                        "Operational state data for port-breakout entry";
                    uses port-breakout-breakout-config;
                    uses port-breakout-breakout-state;
                } // END of state-container definition.
            } // End of breakout-list
        } // END of breakouts-container definition.
    } // END of port-breakout-breakout-top definition.
    grouping port-breakout-group-speed-state {
        description
            "Grouping for port-breakout group speed operational state data";
        leaf-list ports  {
            type  uint8;
            description "Use this attribute to get the list of ports within the group speed";
        } // END of ports definition.

    } // END of port-breakout-group-speed-state definition.
    grouping port-breakout-group-speed-config {
        description
            "Grouping for port-breakout group speed configuration data";
        leaf port-group  {
            type  uint8;
            description "Use this attribute to set the port group associated with this instance";
        } // END of port-group definition.

        leaf speed  {
            type  ipi-port-breakout-types:port_breakout_group_speed_t;
            mandatory true;
            description "Use this attribute to set the port group speed";
        } // END of speed definition.

    } // END of port-breakout-group-speed-config definition.
    grouping port-breakout-group-speed-top {
        description
            "Grouping for Port Breakout group speed";
        container groups-speed {
            description
                "Container for Port Breakout group speed list configuration";

            list group-speed {
            // when " ipi-port-breakout:port-breakout/groups-speed/group-speed/config/speed ";
                if-feature feature-list:NOT_HAVE_DUNE;
                key "port-group";
                description
                    "List of group speed";
                leaf port-group  {
                    type  leafref {
                        path  "../config/port-group";
                    }
                    description "Use this attribute to set the port group associated with this instance";
                } // END of port-group definition.

                container config {
                    description
                        "Configuration data for group speed entry";
                    uses port-breakout-group-speed-config;
                } // END of config-container definition.
                container state {
                    config false;
                    description
                        "Operational state data for group speed entry";
                    uses port-breakout-group-speed-config;
                    uses port-breakout-group-speed-state;
                } // END of state-container definition.
            } // End of group-speed-list
        } // END of groups-speed-container definition.
    } // END of port-breakout-group-speed-top definition.

    grouping  port-breakout-grouping {
    description
        "Port-breakout data model";
    container port-breakout {
        if-feature feature-list:HAVE_FLEXPORT;
        description
            "Port-breakout data model";
        uses port-breakout-breakout-top;
        uses port-breakout-group-speed-top;
        uses port-breakout-interface-top;
    } // END of port-breakout-container definition.
    } // END of port-breakout-grouping definition.

    uses port-breakout-grouping;

}
