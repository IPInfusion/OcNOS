/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-port-breakout-types.yang
*
*/

module ipi-port-breakout-types {

    yang-version 1.1;

    namespace   "http://www.ipinfusion.com/yang/ocnos/ipi-port-breakout-types";

    prefix "ipi-port-breakout-types";

    organization
        "IP Infusion Inc.";

    contact
        "Address: 3965 Freedom Circle, Suite 200, Santa Clara, CA 95054
         Phone: +1 408-400-1900
         E-mail: support@ipinfusion.com
         Web: http://www.ipinfusion.com/";

    description
        "Datamodel for Layer-2 Port Breakout types";


    revision "2024-10-14" {
        description "Added port breakout support to Tomahawk5 device";
        reference " 0.9.2.";
    }

    revision "2024-10-10" {
        description "Added port breakout support to Tomahawk5 device";
        reference " 0.9.1.";
    }

    revision "2024-02-21" {
        description "Added 1X40g port breakout support";
        reference " 0.9.0.";
    }

    revision "2023-07-26" {
        description "Combined breakout and breakout-ifname containers";
        reference " 0.8.0.";
    }

    revision "2023-07-12" {
        description "Restructred port breakout data model";
        reference " 0.7.0.";
    }

    revision "2023-05-17" {
        description "400g port breakout support for TH3";
        reference " 0.6.0.";
    }

    revision "2023-03-23" {
        description "400g port breakout support for dnx";
        reference " 0.5.0.";
    }

    revision "2023-01-18" {
        description "Updated the port breakout with ifname for dnx";
        reference " 0.4.0.";
    }

    revision "2022-11-24" {
        description "Updated the port breakout type for dnx";
        reference " 0.3.0.";
    }

    revision "2022-06-01" {
        description "Updated the yang file with feature";
        reference " 0.2.0.";
    }

    revision "2021-11-29" {
        description "Restructured port-breakout module in accordance with OpenConfig style";
        reference " 0.1.0.";
    }



    typedef  port_breakout_mode_t {
        type enumeration {
            enum 4X10g {
                value 1;
                description "split to 4X10g";
            }
            enum 4X25g {
                value 2;
                description "split to 4X25g";
            }
            enum 2X50g {
                value 3;
                description "split to 2X50g";
            }
            enum 4X100g {
                value 8;
                description "split to 4X100g";
            }
            enum 8X50g {
                value 9;
                description "split to 8X50g";
            }
            enum 8X25g {
                value 10;
                description "split to 8X25g";
            }
            enum 8X10g {
                value 11;
                description "split to 8X10g";
            }
            enum 2X200g {
                value 12;
                description "split to 2X200g";
            }
            enum 3X100g {
                value 14;
                description "split to 3X100g";
            }
            enum 2X100g {
                value 15;
                description "split to 2X100g(default serdes is 50G)";
            }
            enum 1X100g {
                value 16;
                description "split to 1X100g(default serdes is 50G)";
            }
            enum 1X200g {
                value 17;
                description "split to 1X200g";
            }
            enum 4X50g {
                value 18;
                description "split to 4X50g";
            }
            enum 1X40g {
                value 19;
                description "split to 1X40g";
            }
            enum 3X200g {
                value 20;
                description "split to 3X200g";
            }
            enum 4X200g {
                value 21;
                description "split to 4X200g";
            }
            enum 1X400g {
                value 22;
                description "split to 1X400g";
            }
            enum 2X400g {
                value 23;
                description "split to 2X400g";
            }
            enum 8X100g {
                value 24;
                description "split to 8X100g";
            }
            enum 7X100g {
                value 25;
                description "split to 7X100g";
            }
            enum 6X100g {
                value 26;
                description "split to 6X100g";
            }
            enum 5X100g {
                value 27;
                description "split to 5X100g";
            }
        }
        description "type definition for PORT_BREAKOUT_MODE_T";
    }

    typedef  port_breakout_serdes_type_t {
        type enumeration {
            enum 25g {
                value 1;
                description "serdes 25g";
            }
            enum 50g {
                value 2;
                description "serdes 50g";
            }
            enum 100g {
                value 3;
                description "serdes 100g";
            }
        }
        description "type definition for PORT_BREAKOUT_SERDES_TYPE_T";
    }

    typedef  port_breakout_group_speed_t {
        type enumeration {
            enum 10g {
                value 0;
                description "10 gigabits";
            }
        }
        description "type definition for PORT_BREAKOUT_GROUP_SPEED_T";
    }

    typedef  port_breakout_if_mode_t {
        type enumeration {
            enum 4X10g {
                value 1;
                description "split to 4X10g";
            }
            enum 4X25g {
                value 2;
                description "split to 4X25g";
            }
            enum 2X50g {
                value 3;
                description "split to 2X50g";
            }
        }
        description "type definition for PORT_BREAKOUT_IF_MODE_T";
    }

}
