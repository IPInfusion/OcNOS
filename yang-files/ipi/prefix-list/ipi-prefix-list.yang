/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-prefix-list.yang
*
*/

module ipi-prefix-list {

    yang-version 1.1;

    namespace   "http://www.ipinfusion.com/yang/ocnos/ipi-prefix-list";

    prefix "ipi-prefix-list";

    import cml-data-types {
        prefix cml-data-types;
        revision-date 2026-05-15;
    }

    import ipi-prefix-list-types {
        prefix ipi-prefix-list-types;
        revision-date 2022-07-31;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-prefix-list";


    revision "2025-04-15" {
        description "Add indexing for prefix-list";
        reference " 0.7.1.";
    }

    revision "2024-10-29" {
        description "Added attribute 'exact-prefix-length-match' for ipv6 prefix-list";
        reference " 0.7.0.";
    }

    revision "2024-04-22" {
        description "Added clear-prefix-list for ip and ipv6 command to reset the hit count to zero";
        reference " 0.6.0.";
    }

    revision "2024-04-07" {
        description "Changed logic of generating sequence id for prefix-list";
        reference " 0.5.4.";
    }

    revision "2022-10-10" {
        description "Changed logic of generating sequence id for prefix-list";
        reference " 0.5.3.";
    }

    revision "2022-10-07" {
        description "Added util api to validate ipv6 address";
        reference " 0.5.2.";
    }

    revision "2022-07-31" {
        description "Stop using inet:ipv4-prefix and inet:ipv6-prefix due to Cisco NSO iterop";
        reference " 0.5.1.";
    }

    revision "2022-07-28" {
        description "Updated smi-server-modules with restructured RIPng module name";
        reference " 0.5.0.";
    }

    revision "2022-07-26" {
        description "Corrected RIP datamodel as per Open Config style";
        reference " 0.4.0.";
    }

    revision "2022-06-01" {
        description "Updated the yang file with feature";
        reference " 0.3.0.";
    }

    revision "2020-12-15" {
        description "Change to have data-types in lower case instead of camel case";
        reference " 0.2.0.";
    }

    revision "2020-06-24" {
        description "Initial Version";
        reference " 0.1.0.";
    }

    grouping prefix-list-common {
        description
            "Configuration data for prefix-lists";
        leaf prefix-list-name  {
            type  string {
                length "1..1965";
                pattern "[a-zA-Z0-9][^?' =,>|]*";
            }
            description "Name of the prefix list";
        } // END of prefix-list-name definition.

        leaf prefix-list-type  {
            type  ipi-prefix-list-types:prefix_list_type_t;
            description "prefix-list type";
        } // END of prefix-list-type definition.

        leaf description  {
            type  cml-data-types:cml_line_t {
                length "1..80";
            }
            description "Up to 80 characters describing this prefix-list";
        } // END of description definition.

    } // END of prefix-list-common definition.
    grouping sequence-entry {
        description
            "Configuration data for prefix-list sequence";
        leaf sequence-id  {
            type  uint32 {
                 range "1..4294967295"  {
                    description "1..4294967295: Supported range 1 - 4294967295";
                 }
            }
            description "Sequence number of the prefix list";
        } // END of sequence-id definition.

    } // END of sequence-entry definition.
    grouping ipv4-prefix-list-seq {
        description
            "Configuration data for prefix-list sequence";
        leaf action  {
            type  ipi-prefix-list-types:prefix_list_action_t;
            description "Router starts to match prefixes from the top of the prefix list, and
                        stops whenever a match or deny occurs. To promote efficiency, use the
                        seq parameter and place common matches or denials towards the top of
                        the list. The sequence values are generated in the sequence of 5. The
                        parameters ge and le specify the range of the prefix length to be
                        matched";
        } // END of action definition.

        leaf minimum-prefix-length-match  {
            when " /ipi-prefix-list:prefixes/ipi-prefix-list:prefix/ipi-prefix-list:prefix-entries/ipi-prefix-list:prefix-entry/ipi-prefix-list:ipv4/ipi-prefix-list:entry/ipi-prefix-list:prefix-addr != 'any' ";
            type  uint8 {
                 range "0..32"  {
                    description "0..32: Supported range 0 - 32";
                 }
            }
            description "Minimum prefix length match";
        } // END of minimum-prefix-length-match definition.

        leaf maximum-prefix-length-match  {
            when " /ipi-prefix-list:prefixes/ipi-prefix-list:prefix/ipi-prefix-list:prefix-entries/ipi-prefix-list:prefix-entry/ipi-prefix-list:ipv4/ipi-prefix-list:entry/ipi-prefix-list:prefix-addr != 'any' ";
            type  uint8 {
                 range "0..32"  {
                    description "0..32: Supported range 0 - 32";
                 }
            }
            description "Maximum prefix length match";
        } // END of maximum-prefix-length-match definition.

        leaf prefix-addr  {
            type  ipi-prefix-list-types:prefix_list_ipv4_network_t;
            description "Either IP address mask and length of the prefix list mask or Take all
                        packets of any length. This parameter is the same as using 0.0.0.0/0
                        le 32 for A.B.C.D/M.";
        } // END of prefix-addr definition.

        leaf exact-prefix-length-match  {
            when " /ipi-prefix-list:prefixes/ipi-prefix-list:prefix/ipi-prefix-list:prefix-entries/ipi-prefix-list:prefix-entry/ipi-prefix-list:ipv4/ipi-prefix-list:entry/ipi-prefix-list:prefix-addr != 'any' ";
            type  uint8 {
                 range "0..32"  {
                    description "0..32: Supported range 0 - 32";
                 }
            }
            description "Exact prefix length match";
        } // END of exact-prefix-length-match definition.

    } // END of ipv4-prefix-list-seq definition.
    grouping ipv6-prefix-list-seq {
        description
            "Configuration data for prefix-list sequence";
        leaf ipv6-prefix-addr  {
            type  ipi-prefix-list-types:prefix_list_ipv6_network_t;
            description "Either IPv6 address mask and length of the prefix list mask or This is
                        the same as specifying ::/0 for X:X::X:X/M";
        } // END of ipv6-prefix-addr definition.

        leaf action  {
            type  ipi-prefix-list-types:prefix_list_action_t;
            description "Router starts to match prefixes from the top of the prefix list, and
                        stops whenever a match or deny occurs. To promote efficiency, use the
                        seq parameter and place common matches or denials towards the top of
                        the list. The sequence values are generated in the sequence of 5. The
                        parameters ge and le specify the range of the prefix length to be
                        matched";
        } // END of action definition.

        leaf minimum-prefix-length-match  {
            // when " ipi-prefix-list:prefixes/prefix/prefix-entries/prefix-entry/ipv6/entry/config/ipv6-prefix-addr != 'any' ";
            type  uint8 {
                 range "0..128"  {
                    description "0..128: Supported range 0 - 128";
                 }
            }
            description "Minimum prefix length match";
        } // END of minimum-prefix-length-match definition.

        leaf maximum-prefix-length-match  {
            // when " ipi-prefix-list:prefixes/prefix/prefix-entries/prefix-entry/ipv6/entry/config/ipv6-prefix-addr != 'any' ";
            type  uint8 {
                 range "0..128"  {
                    description "0..128: Supported range 0 - 128";
                 }
            }
            description "Maximum prefix length match";
        } // END of maximum-prefix-length-match definition.

        leaf exact-prefix-length-match  {
            // when " ipi-prefix-list:prefixes/prefix/prefix-entries/prefix-entry/ipv6/entry/config/ipv6-prefix-addr != 'any' ";
            type  uint8 {
                 range "0..128"  {
                    description "0..128: Supported range 0 - 128";
                 }
            }
            description "Exact prefix length match";
        } // END of exact-prefix-length-match definition.

    } // END of ipv6-prefix-list-seq definition.
    grouping prefix-list-sequence {
        description
            "Configuration data for prefix-list sequence";
        container prefix-entries {
            description
                "List of sequences";

            list prefix-entry {
                key "sequence-id";
                description
                    "List of sequences";
                leaf sequence-id  {
                    type  leafref {
                        path  "../config/sequence-id";
                    }
                    description "Sequence number of the prefix list";
                } // END of sequence-id definition.

                container config {
                    description
                        "Configuration data for ipv4 prefix-list sequence";
                    uses sequence-entry;
                } // END of config-container definition.
                container state {
                    config false;
                    description
                        "Operational state data";
                    uses sequence-entry;
                } // END of state-container definition.
                uses ipv4-prefix-list-network;
                uses ipv6-prefix-list-network;
            } // End of prefix-entry-list
        } // END of prefix-entries-container definition.
    } // END of prefix-list-sequence definition.
    grouping ipv4-prefix-list-network {
        description
            "prefix-list network information";
        container ipv4 {
            description
                "prefix-list network information";

            list entry {
                key "action prefix-addr";
                description
                    "prefix-list network information";
                leaf action  {
                    type  leafref {
                        path  "../config/action";
                    }
                    description "Router starts to match prefixes from the top of the prefix list, and
                                stops whenever a match or deny occurs. To promote efficiency, use the
                                seq parameter and place common matches or denials towards the top of
                                the list. The sequence values are generated in the sequence of 5. The
                                parameters ge and le specify the range of the prefix length to be
                                matched";
                } // END of action definition.

                leaf prefix-addr  {
                    type  leafref {
                        path  "../config/prefix-addr";
                    }
                    description "Either IP address mask and length of the prefix list mask or Take all
                                packets of any length. This parameter is the same as using 0.0.0.0/0
                                le 32 for A.B.C.D/M.";
                } // END of prefix-addr definition.

                container config {
                    description
                        "Configuration data for ipv4 prefix-list sequence";
                    uses ipv4-prefix-list-seq;
                } // END of config-container definition.
                container state {
                    config false;
                    description
                        "Operational state data";
                    uses ipv4-prefix-list-seq;
                } // END of state-container definition.
            } // End of entry-list
        } // END of ipv4-container definition.
    } // END of ipv4-prefix-list-network definition.
    grouping ipv6-prefix-list-network {
        description
            "prefix-list network information";
        container ipv6 {
            if-feature feature-list:HAVE_IPV6;
            description
                "prefix-list network information";

            list entry {
                if-feature feature-list:HAVE_IPV6;
                key "action ipv6-prefix-addr";
                description
                    "prefix-list network information";
                leaf action  {
                    type  leafref {
                        path  "../config/action";
                    }
                    description "Router starts to match prefixes from the top of the prefix list, and
                                stops whenever a match or deny occurs. To promote efficiency, use the
                                seq parameter and place common matches or denials towards the top of
                                the list. The sequence values are generated in the sequence of 5. The
                                parameters ge and le specify the range of the prefix length to be
                                matched";
                } // END of action definition.

                leaf ipv6-prefix-addr  {
                    type  leafref {
                        path  "../config/ipv6-prefix-addr";
                    }
                    description "Either IPv6 address mask and length of the prefix list mask or This is
                                the same as specifying ::/0 for X:X::X:X/M";
                } // END of ipv6-prefix-addr definition.

                container config {
                    if-feature feature-list:HAVE_IPV6;
                    description
                        "Configuration data for ipv4 prefix-list sequence";
                    uses ipv6-prefix-list-seq;
                } // END of config-container definition.
                container state {
                    if-feature feature-list:HAVE_IPV6;
                    config false;
                    description
                        "Operational state data";
                    uses ipv6-prefix-list-seq;
                } // END of state-container definition.
            } // End of entry-list
        } // END of ipv6-container definition.
    } // END of ipv6-prefix-list-network definition.
    grouping plist-global {
        description
            "Global data for prefix-list configurations";
        leaf disable-ipv4-sequence-display  {
            type  empty;
            description "Use this attribute to configure prefix list sequence number.Include
                        and exclude sequence numbers in nonvolatile generation (NVGEN).";
        } // END of disable-ipv4-sequence-display definition.

        leaf disable-ipv6-sequence-display  {
            if-feature feature-list:HAVE_IPV6;
            type  empty;
            description "Use this attribute to configure prefix list sequence number.Include
                        and exclude sequence numbers in nonvolatile generation (NVGEN).";
        } // END of disable-ipv6-sequence-display definition.

    } // END of plist-global definition.
    grouping prefix-list-top {
        description
            "Top level grouping for ipv4 prefix-list";

        list prefix {
            key "prefix-list-name prefix-list-type";
            description
                "IPV4 prefix-list configurations";
            leaf prefix-list-name  {
                type  leafref {
                    path  "../config/prefix-list-name";
                }
                description "prefix-list name";
            } // END of prefix-list-name definition.

            leaf prefix-list-type  {
                type  leafref {
                    path  "../config/prefix-list-type";
                }
                description "prefix-list type";
            } // END of prefix-list-type definition.

            container config {
                description
                    "Configuration data for prefix list";
                uses prefix-list-common;
            } // END of config-container definition.
            container state {
                config false;
                description
                    "Operational state data";
                uses prefix-list-common;
            } // END of state-container definition.
            uses prefix-list-sequence;
        } // End of prefix-list
    } // END of prefix-list-top definition.

    grouping  prefixes-grouping {
    description
        "Prefix-list information";
    container prefixes {
        description
            "Prefix-list information";
        uses prefix-list-top;
    } // END of prefixes-container definition.
    } // END of prefixes-grouping definition.

    uses prefixes-grouping;

    rpc clear-prefix-list-all {
        description "Use clear-prefix-list-all command to reset the hit count to zero in
                    the prefix-list entries for an IPv4 interface.";
    }

    rpc clear-prefix-list-ipv6-all {
        description "Use clear-prefix-list-all command to reset the hit count to zero in
                    the prefix-list entries for an IPv6 interface.";
    }

    rpc clear-ipv4-prefix-list {
        description "Use clear-ipv4-plist-by-prefix command to reset the hit count to zero
                    in the prefix-list entries for an mentioned prefix.";
        input  {
            leaf prefix-list-name  {
                type string;
                mandatory true;
                description "Name of the ipv4 prefix-list reset the hit count to zero";
            }
            leaf prefix  {
                type cml-data-types:cml_ipv4_addr_prefix_t;
                description "prefix of the ipv4 prefix-list reset the hit count to zero";
            }
        }
    }

    rpc clear-ipv6-prefix-list {
        if-feature feature-list:HAVE_IPV6;
        description "Use clear-ipv6-plist-by-prefix command to reset the hit count to zero
                    in the prefix-list entries for an mentioned prefix.";
        input  {
            leaf prefix-list-name  {
                type string;
                mandatory true;
                description "Name of the ipv6 prefix-list reset the hit count to zero";
            }
            leaf prefix  {
                type cml-data-types:cml_ipv6_prefix_t;
                description "prefix of the ipv6 prefix-list reset the hit count to zero";
            }
        }
    }

}
