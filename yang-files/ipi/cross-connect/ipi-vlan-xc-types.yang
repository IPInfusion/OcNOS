/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-vlan-xc-types.yang
*
*/

module ipi-vlan-xc-types {

    yang-version 1.1;

    namespace   "http://www.ipinfusion.com/yang/ocnos/ipi-vlan-xc-types";

    prefix "ipi-vlan-xc-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-vlan-xc-types";


    revision "2022-06-01" {
        description "Updated the yang file with feature";
        reference " 0.2.0.";
    }

    revision "2021-03-23" {
        description "Initial Version";
        reference " 0.1.0.";
    }



    typedef  vlan_xc_admin_status_t {
        type enumeration {
            enum down {
                value 0;
                description "Set the admin role as Down";
            }
            enum up {
                value 1;
                description "Set the admin role as UP";
            }
        }
        description "type definition for VLAN_XC_ADMIN_STATUS_T";
    }

    typedef  vlan_xc_oper_status_t {
        type enumeration {
            enum down {
                value 0;
                description "Set the oper role as Down";
            }
            enum up {
                value 1;
                description "Set the oper role as UP";
            }
        }
        description "type definition for VLAN_XC_OPER_STATUS_T";
    }

}
