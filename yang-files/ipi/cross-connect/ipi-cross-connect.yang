/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-cross-connect.yang
*
*/

module ipi-cross-connect {

    yang-version 1.1;

    namespace   "http://www.ipinfusion.com/yang/ocnos/ipi-cross-connect";

    prefix "ipi-cross-connect";

    import cml-data-types {
        prefix cml-data-types;
        revision-date 2026-05-15;
    }

    import ipi-cross-connect-types {
        prefix ipi-cross-connect-types;
        revision-date 2025-10-09;
    }

    import ipi-network-instance {
        prefix ipi-network-instance;
        revision-date 2026-08-12;
    }

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Cross-Connect configurations";


    revision "2025-10-09" {
        description "Removed blocking for crossconect for XGs platforms";
        reference " 0.2.8.";
    }

    revision "2025-09-17" {
        description "Blocking Bridge-domain and cross-connect for all XGS (DC) platforms";
        reference " 0.2.7.";
    }

    revision "2025-04-17" {
        description "Added when directive for cross-connection g8031-eps. Removed implicit_delete from cross-connect-interface config";
        reference " 0.2.6.";
    }

    revision "2025-02-06" {
        description "Added 'CML_UNIQUE' support for endpoint-if";
        reference " 0.2.5.";
    }

    revision "2025-02-03" {
        description "Added 'CML_UNIQUE' support for endpoint-if-bkp";
        reference " 0.2.4.";
    }

    revision "2024-08-22" {
        description "Changed MAX value for evc-name";
        reference " 0.2.3.";
    }

    revision "2023-11-24" {
        description "Added new attributes for cross-connection backup";
        reference " 0.2.2.";
    }

    revision "2023-10-20" {
        description "When tag validation under attribute endpoint-if";
        reference " 0.2.1.";
    }

    revision "2023-08-17" {
        description "Reverted: Reverted: Create the cross-connect interface as an object-list with endpoint-if as attribute";
        reference " 0.1.7.";
    }

    revision "2023-08-16" {
        description "Reverted: Create the cross-connect interface as an object-list with endpoint-if as attribute";
        reference " 0.1.6.";
    }

    revision "2023-08-11" {
        description "Create the cross-connect interface as an object-list with endpoint-if as attribute";
        reference " 0.1.5.";
    }

    revision "2023-06-15" {
        description "Added a when tag in endpoint-if with subinterface encapsulation";
        reference " 0.1.4.";
    }

    revision "2023-01-12" {
        description "Removed endpoint notification and added leaf-ref";
        reference " 0.1.3.";
    }

    revision "2022-06-01" {
        description "Updated the yang file with feature";
        reference " 0.1.2.";
    }

    revision "2022-01-17" {
        description "Add attribute xc-name to cross-connect config container.";
        reference " 0.1.1.";
    }

    revision "2021-11-10" {
        description "It was moved from interfaces extended datamodel to network-instances datamodel.";
        reference " 0.1.0.";
    }

    grouping cross-connect-interface-config {
        description
            "Grouping for Cross-Connect interface configuration";
        leaf endpoint-if  {
            type  leafref {
                path  "/ipi-interface:interfaces/ipi-interface:interface/ipi-interface:name";
            }
            description "This attribute specifies the endpoint for cross-connect";
        } // END of endpoint-if definition.

        leaf endpoint-if-bkp  {
            if-feature feature-list:HAVE_DUNE;
            type  string {
                length "1..33";
                pattern "[^?' =,>|]+";
            }
            description "This attribute specifies the backup endpoint for cross-connect";
        } // END of endpoint-if-bkp definition.

        leaf evc-name  {
            if-feature feature-list:HAVE_DUNE;
            type  string {
                length "1..100";
                pattern "[^?' =,>|]+";
            }
            description "Ethernet virtual connection ID";
        } // END of evc-name definition.

    } // END of cross-connect-interface-config definition.
    grouping cross-connect-interface-top {
        description
            "Grouping for Cross-Connect interface";
        container cross-connect-interfaces {
            description
                "Container for Cross-Connect interfaces";

            list cross-connect-interface {
                if-feature feature-list:NOT_HAVE_CUSTOM1_SUBINTERFACE;
                key "endpoint-if";
                unique "config/endpoint-if-bkp";
                description
                    "List of Cross-Connect interfaces";
                leaf endpoint-if  {
                    type  leafref {
                        path  "../config/endpoint-if";
                    }
                    description "This attribute specifies the endpoint for cross-connect";
                } // END of endpoint-if definition.

                container config {
                    description
                        "Configuration data for Cross-Connect interface";
                    uses cross-connect-interface-config;
                } // END of config-container definition.
                container state {
                    config false;
                    description
                        "Operational state data for Cross-Connect interface";
                    uses cross-connect-interface-config;
                } // END of state-container definition.
            } // End of cross-connect-interface-list
        } // END of cross-connect-interfaces-container definition.
    } // END of cross-connect-interface-top definition.
    grouping cross-connect-config {
        description
            "Grouping for Cross-Connect configurations";
        leaf xc-name  {
            type  leafref {
                path  "/ipi-network-instance:network-instances/ipi-network-instance:network-instance/ipi-network-instance:instance-name";
            }
            description "This attribute specifies the entry name for cross-connect";
        } // END of xc-name definition.

        leaf description  {
            type  cml-data-types:cml_line_t {
                length "1..1965";
            }
            description "This attribute specifies the description for cross-connect";
        } // END of description definition.

        leaf admin-disable  {
            type  empty;
            description "This attribute is used to temporarily shutdown the cross-connect";
        } // END of admin-disable definition.

    } // END of cross-connect-config definition.
    grouping cross-connect-state {
        description
            "Grouping for Cross-Connect operational data";
        leaf operational-state  {
            type  ipi-cross-connect-types:xc_oper_status_t;
            description "This attribute shows the current status of cross-connect.";
        } // END of operational-state definition.

    } // END of cross-connect-state definition.

    grouping  cross-connect-grouping {
    description
        "Global container for cross connect between subinterfaces";
    container cross-connect {
        if-feature feature-list:HAVE_SUBINTERFACE;
        description
            "Global container for cross connect between subinterfaces";
        container config {
            description
                "Global configuration for Cross-Connect";
            uses cross-connect-config;
        } // END of config-container definition.
        container state {
            config false;
            description
                "State data for cross-connect";
            uses cross-connect-config;
            uses cross-connect-state;
        } // END of state-container definition.
        uses cross-connect-interface-top;
    } // END of cross-connect-container definition.
    } // END of cross-connect-grouping definition.

    augment /ipi-network-instance:network-instances/ipi-network-instance:network-instance {
        description
            "Global container for cross connect between subinterfaces";
        uses cross-connect-grouping;
    }


}
