/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-flexe.yang
*
*/

module ipi-flexe {

    yang-version 1.1;

    namespace   "http://www.ipinfusion.com/yang/ocnos/ipi-flexe";

    prefix "ipi-flexe";

    import ipi-flexe-types {
        prefix ipi-flexe-types;
        revision-date 2023-10-24;
    }

    import feature-list {
        prefix feature-list;
        revision-date 2026-09-15;
    }

    include ipi-flexe-client { revision-date 2023-10-24;}
    include ipi-flexe-group { revision-date 2023-10-24;}
    organization
        "IP Infusion Inc.";

    contact
        "Address: 3965 Freedom Circle, Suite 200, Santa Clara, CA 95054
         Phone: +1 408-400-1900
         E-mail: support@ipinfusion.com
         Web: http://www.ipinfusion.com/";

    description
        "FlexEthernet(FlexE) configuration";


    revision "2023-10-24" {
        description "Initial Version";
        reference " 0.1.0.";
    }

    grouping flexe-global-config {
        description
            "Grouping for FlexE global configuration data";
        leaf flexe-mode  {
            type  empty;
            description "Use this attribute to enable or disable the FlexE";
        } // END of flexe-mode definition.

        leaf slot-granularity  {
            type  ipi-flexe-types:flexe_slot_granularity_t;
            default "5G";
            description "Use this attribute to set the slot granularity for 1G,1.5G and 5G";
        } // END of slot-granularity definition.

        leaf bandwidth-notation  {
            type  empty;
            description "Use this attribute to set the bandwidth notation for FlexE";
        } // END of bandwidth-notation definition.

    } // END of flexe-global-config definition.
    grouping flexe-global-top {
        description
            "Top level grouping for FlexE Global";
        container global {
            description
                "FlexE Global Structure";
            container config {
                description
                    "FlexE Global configuration data";
                uses flexe-global-config;
            } // END of config-container definition.
            container state {
                config false;
                description
                    "Operational State data";
                uses flexe-global-config;
            } // END of state-container definition.
        } // END of global-container definition.
    } // END of flexe-global-top definition.

    grouping  flexe-grouping {
    description
        "FlexE Main container";
    container flexe {
        if-feature feature-list:HAVE_FLEXE;
        description
            "FlexE Main container";
        uses flexe-global-top;
        uses flexe-groups-grouping;
        uses interfaces-grouping;
    } // END of flexe-container definition.
    } // END of flexe-grouping definition.

    uses flexe-grouping;

}
