/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-flexe-client.yang
*
*/

submodule ipi-flexe-client {

    yang-version 1.1;

    belongs-to  ipi-flexe { prefix ipi-flexe; }

    import feature-list {
        prefix feature-list;
        revision-date 2026-09-15;
    }

    import ipi-interface {
        prefix ipi-interface;
        revision-date 2026-03-10;
    }

    import cml-data-types {
        prefix cml-data-types;
        revision-date 2026-05-15;
    }

    include ipi-flexe-group { revision-date 2023-10-24;}
    organization
        "IP Infusion Inc.";

    contact
        "Address: 3965 Freedom Circle, Suite 200, Santa Clara, CA 95054
         Phone: +1 408-400-1900
         E-mail: support@ipinfusion.com
         Web: http://www.ipinfusion.com/";

    description
        "FlexE client configurations";


    revision "2023-10-24" {
        description "Initial Version";
        reference " 0.1.0.";
    }

    grouping flexe-client-binding-config {
        description
            "FlexE client binding attributes";
        leaf flexe-group-id  {
            type  leafref {
                path  "/ipi-flexe:flexe/ipi-flexe:flexe-groups/ipi-flexe:flexe-group/ipi-flexe:group-id";
            }
            mandatory true;
            description "Use this attribute to set the group id for FlexE client";
        } // END of flexe-group-id definition.

        leaf client-id  {
            type  uint32 {
                 range "1..79"  {
                    description "1..79: Supported range 1 - 79";
                 }
            }
            mandatory true;
            description "Use this attribute to set the client id for the FlexE client";
        } // END of client-id definition.

    } // END of flexe-client-binding-config definition.
    grouping flexe-client-binding-top {
        description
            "Grouping for FlexE client binding";
        container binding {
            description
                "Container for FlexE client binding";
            container config {
                presence "yes";
                description
                    "Configuration data for FlexE client binding";
                uses flexe-client-binding-config;
            } // END of config-container definition.
            container state {
                config false;
                description
                    "Operational data for FlexE client binding";
                uses flexe-client-binding-config;
            } // END of state-container definition.
        } // END of binding-container definition.
    } // END of flexe-client-binding-top definition.
    grouping flexe-client-bandwidth-map-config {
        description
            "FlexE client bandwidth map attributes";
        leaf interface  {
            type  leafref {
                path  "/ipi-interface:interfaces/ipi-interface:interface/ipi-interface:name";
            }
            description "Use this attribute to set the bandwidth map port for the FlexE client";
        } // END of interface definition.

        leaf bandwidth  {
            type  string {
                length "1..1965";
                pattern "[^?' =,>|]+";
            }
            mandatory true;
            description "Use this attribute to set the bandwidth";
        } // END of bandwidth definition.

    } // END of flexe-client-bandwidth-map-config definition.
    grouping flexe-client-bandwidth-map-top {
        description
            "FlexE client bandwidth map configuration";
        container bandwidth-maps {
            description
                "Container for FlexE client bandwidth map";

            list bandwidth-map {
                key "interface";
                description
                    "FlexE client badwidth map entry";
                leaf interface  {
                    type  leafref {
                        path  "../config/interface";
                    }
                    description "Use this attribute to set the bandwidth map port for the FlexE client";
                } // END of interface definition.

                container config {
                    description
                        "Configuration data for FlexE client bandwidth map";
                    uses flexe-client-bandwidth-map-config;
                } // END of config-container definition.
                container state {
                    config false;
                    description
                        "Operational data for FlexE client bandwidth map";
                    uses flexe-client-bandwidth-map-config;
                } // END of state-container definition.
            } // End of bandwidth-map-list
        } // END of bandwidth-maps-container definition.
    } // END of flexe-client-bandwidth-map-top definition.
    grouping flexe-slot-map-config {
        description
            "FlexE client slot map attributes";
        leaf interface  {
            type  leafref {
                path  "/ipi-interface:interfaces/ipi-interface:interface/ipi-interface:name";
            }
            description "Use this attribute to configure slot-map port for the FlexE client";
        } // END of interface definition.

        leaf slot-id  {
            type  cml-data-types:cml_range_t;
            mandatory true;
            description "Use this attribute to set the slot id";
        } // END of slot-id definition.

    } // END of flexe-slot-map-config definition.
    grouping flexe-client-slot-map-top {
        description
            "Grouping for FlexE client slot map configuration";
        container flexe-slot-maps {
            description
                "Container for FlexE slot map configuration";

            list flexe-slot-map {
                key "interface";
                description
                    "FlexE slot map entry";
                leaf interface  {
                    type  leafref {
                        path  "../config/interface";
                    }
                    description "Use this attribute to configure slot-map port for the FlexE client";
                } // END of interface definition.

                container config {
                    description
                        "config container";
                    uses flexe-slot-map-config;
                } // END of config-container definition.
                container state {
                    config false;
                    description
                        "Operational state data for dot1q and dot1ad encapsulation";
                    uses flexe-slot-map-config;
                } // END of state-container definition.
            } // End of flexe-slot-map-list
        } // END of flexe-slot-maps-container definition.
    } // END of flexe-client-slot-map-top definition.
    grouping flexe-client-config {
        description
            "FlexE client attributes";
        leaf l1-switch-mode  {
            type  empty;
            description "Use This attribute to set the L1 switch mode on the interface";
        } // END of l1-switch-mode definition.

    } // END of flexe-client-config definition.
    grouping flexe-client-top {
        description
            "Grouping for client interface interface FlexE mode";
        container flexe-client {
            description
                "Configuration data for FlexE interface";
            container config {
                description
                    "Configuration data for FlexE client interface";
                uses flexe-client-config;
            } // END of config-container definition.
            container state {
                config false;
                description
                    "Operational state data for FlexE client interface";
                uses flexe-client-config;
            } // END of state-container definition.
            uses flexe-client-slot-map-top;
            uses flexe-client-binding-top;
            uses flexe-client-bandwidth-map-top;
        } // END of flexe-client-container definition.
    } // END of flexe-client-top definition.
    grouping flexe-client-interface-config {
        description
            "Grouping for FlexE client interface configuration";
        leaf name  {
            type  leafref {
                path  "/ipi-interface:interfaces/ipi-interface:interface/ipi-interface:name";
            }
            description "FlexE client interface name";
        } // END of name definition.

    } // END of flexe-client-interface-config definition.

    grouping  interfaces-grouping {
    description
        "Top level container for FlexE client interfaces";
    container interfaces {
        if-feature feature-list:HAVE_FLEXE;
        description
            "Top level container for FlexE client interfaces";

        list interface {
        // when " ipi-flexe:flexe/global/config/flexe-mode ";
            key "name";
            description
                "List for flexe client interfaces";
            leaf name  {
                type  leafref {
                    path  "../config/name";
                }
                description "FlexE client interface name";
            } // END of name definition.

            container config {
                description
                    "Configuration data for FlexE client interface";
                uses flexe-client-interface-config;
            } // END of config-container definition.
            container state {
                config false;
                description
                    "Operational state data for FlexE client interface";
                uses flexe-client-interface-config;
            } // END of state-container definition.
            uses flexe-client-top;
        } // End of interface-list
    } // END of interfaces-container definition.
    } // END of interfaces-grouping definition.


}
