/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-flexe-types.yang
*
*/

module ipi-flexe-types {

    yang-version 1.1;

    namespace   "http://www.ipinfusion.com/yang/ocnos/ipi-flexe-types";

    prefix "ipi-flexe-types";

    organization
        "IP Infusion Inc.";

    contact
        "Address: 3965 Freedom Circle, Suite 200, Santa Clara, CA 95054
         Phone: +1 408-400-1900
         E-mail: support@ipinfusion.com
         Web: http://www.ipinfusion.com/";

    description
        "FlexE data types";


    revision "2023-10-24" {
        description "Initial Version";
        reference " 0.1.0.";
    }



    typedef  flexe_slot_granularity_t {
        type enumeration {
            enum 1G {
                value 1000;
                description "Slot granularity 1G";
            }
            enum 1.25G {
                value 1250;
                description "Slot granularity 1.25G";
            }
            enum 5G {
                value 5000;
                description "Slot granularity 5G";
            }
        }
        description "type definition for FLEXE_SLOT_GRANULARITY_T";
    }

}
