/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-flexe-group.yang
*
*/

submodule ipi-flexe-group {

    yang-version 1.1;

    belongs-to  ipi-flexe { prefix ipi-flexe; }

    import feature-list {
        prefix feature-list;
        revision-date 2026-09-15;
    }

    import ipi-interface {
        prefix ipi-interface;
        revision-date 2026-03-10;
    }

    import cml-data-types {
        prefix cml-data-types;
        revision-date 2026-05-15;
    }

    organization
        "IP Infusion Inc.";

    contact
        "Address: 3965 Freedom Circle, Suite 200, Santa Clara, CA 95054
         Phone: +1 408-400-1900
         E-mail: support@ipinfusion.com
         Web: http://www.ipinfusion.com/";

    description
        "FlexE Group Configurations";


    revision "2023-10-24" {
        description "Initial Version";
        reference " 0.1.0.";
    }

    grouping flexe-group-port-config {
        description
            "Grouping for FlexE port attributes";
        leaf flexe-port  {
            type  leafref {
                path  "/ipi-interface:interfaces/ipi-interface:interface/ipi-interface:name";
            }
            description "Use this attribute to set the FlexE port interface name";
        } // END of flexe-port definition.

        leaf logical-id  {
            type  uint8 {
                 range "1..8"  {
                    description "1..8: Supported range 1 - 8";
                 }
            }
            mandatory true;
            description "Use this attribute to set the logical-id for the FlexE port interface";
        } // END of logical-id definition.

    } // END of flexe-group-port-config definition.
    grouping flexe-group-port-top {
        description
            "FlexE group port top level configuration";
        container flexe-group-ports {
            description
                "FlexE groups ports";

            list flexe-group-port {
                key "flexe-port";
                description
                    "FlexE group port";
                leaf flexe-port  {
                    type  leafref {
                        path  "../config/flexe-port";
                    }
                    description "Use this attribute to set the port interface name";
                } // END of flexe-port definition.

                container config {
                    description
                        "Configuration data for FlexE port";
                    uses flexe-group-port-config;
                } // END of config-container definition.
                container state {
                    config false;
                    description
                        "Operational state data for FlexE port";
                    uses flexe-group-port-config;
                } // END of state-container definition.
            } // End of flexe-group-port-list
        } // END of flexe-group-ports-container definition.
    } // END of flexe-group-port-top definition.
    grouping flexe-group-config {
        description
            "Grouping for FlexE group attributes";
        leaf group-id  {
            type  uint8 {
                 range "1..8"  {
                    description "1..8: Supported range 1 - 8";
                 }
            }
            description "Use this attribute to set FlexE group id";
        } // END of group-id definition.

        leaf description  {
            type  cml-data-types:cml_line_t {
                length "1..1965";
            }
            description "FlexE group specific description";
        } // END of description definition.

        leaf rate  {
            type  uint16 {
                 range "1..1000"  {
                    description "1..1000: Supported range 1 - 1000";
                 }
            }
            units "Gbps";
            description "Flexe shape rate";
        } // END of rate definition.

    } // END of flexe-group-config definition.

    grouping  flexe-groups-grouping {
    description
        "Container for FlexE groups configuration";
    container flexe-groups {
        // when " ipi-flexe:flexe/global/config/flexe-mode ";
        if-feature feature-list:HAVE_FLEXE;
        description
            "Container for FlexE groups configuration";

        list flexe-group {
            key "group-id";
            description
                "FlexE group list";
            leaf group-id  {
                type  leafref {
                    path  "../config/group-id";
                }
                description "Use this attribute to set the flexe group Id";
            } // END of group-id definition.

            container config {
                description
                    "Configuration data for FlexE group";
                uses flexe-group-config;
            } // END of config-container definition.
            container state {
                config false;
                description
                    "Operation state data for FlexE group";
                uses flexe-group-config;
            } // END of state-container definition.
            uses flexe-group-port-top;
        } // End of flexe-group-list
    } // END of flexe-groups-container definition.
    } // END of flexe-groups-grouping definition.


}
