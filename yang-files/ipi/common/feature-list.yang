/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : feature-list.yang
*
*/

module feature-list {

    yang-version 1.1;
    namespace "http://ipinfusion.com/ns/feature-list";

    prefix "feature-list";

    organization
        "IP Infusion Inc.";

    contact
        "3965 Freedom Circle, Suite 200
        Santa Clara, CA 95054 +1 408-400-1900
        E-mail: support@ipinfusion.com
        Web: http://www.ipinfusion.com/";

    description "List of features used in Zebos Module";

    revision "2026-09-15"{
        description "Updated list of OcNOS features";
        reference "0.4.0";
    }
    revision "2021-05-03" {
        description "Added support for import by revision-date";
        reference "0.3.0";
    }
    revision "2020-11-13" {
        description "Datamodel restructuring : revisied on 2020-11-13.";
        reference "0.2.0";
    }
    revision "2015-10-15" {
        description "initial version: revisied on 2015-10-15.";
        reference "0.1.0";
    }

    feature HAVE_NETCONF {
        description "NETCONF feature";
    }

    feature HAVE_CMLD {
        description "CMLD feature";
    }

    feature HAVE_NETCONF_OC_TRANSLATION {
        description "NETCONF translation feature";
    }

    feature HAVE_VRF {
        description "Virtual routing and forwarding";
    }

    feature HAVE_TELEMETRY {
        description "Streaming Telemetry Feature";
    }

    feature HAVE_CFM {
        description "HAVE_CFM feature is enabled";
    }

    feature HAVE_ONMD {
        description "HAVE_ONMD feature is enabled";
    }

    feature HAVE_ETH_SAT {
        description "HAVE_ETH_SAT feature is enabled";
    }

    feature HAVE_EDPL {
        description "HAVE_EDPL feature is enabled";
    }

    feature HAVE_VR {
        description "Virtual Router feature";
    }

    feature HAVE_BGP_EVPN {
        description "BGP EVPN feature";
    }

    feature HAVE_BGP_MVPN {
        description "BGP MVPN Feature";
    }

    feature HAVE_NVO {
        description "NVO feature";
    }

    feature HAVE_L3 {
        description "L3 feature";
    }

    feature HAVE_SERVICE_MAPPING {
        description "SERVICE MAPPING feature ";
    }

    feature HAVE_SRV6 {
        description "SRV6 feature ";
    }

    feature HAVE_MRIB_IPV4 {
        description "MRIB IPV4 feature";
    }

    feature HAVE_SNMP {
        description "SNMP feature";
    }

    feature HAVE_HOSTPD {
        description "HOSTP feature";
    }

    feature HAVE_MPLS {
        description "MPLS feature";
    }

    feature HAVE_DUNE {
        description "Qumran hardware feature";
    }

    feature HAVE_EVPN_VXLAN_STITCHING {
        description "Enable EVPN VXLAN stitching features";
    }

    feature HAVE_FLEXPORT {
        description "Flexport Feature";
    }

    feature HAVE_TOMAHAWK {
        description "Tomahawk Feature";
    }

    feature HAVE_BROADCOM {
        description "broadcom feature";
    }

    feature HAVE_HAL {
        description "hal feature";
    }

    feature HAVE_SWFWDR {
        description "swfwdr feature";
    }

    feature HAVE_VXLAN {
        description "vxlan feature";
    }

    feature HAVE_DNX {
        description "DNX feature";
    }

    feature HAVE_VLAN_STACK {
        description "vlan stack feature";
    }

    feature HAVE_L2 {
        description "L2 feature";
    }

    feature HAVE_LINK_BONDING {
        description "Link Bonding Feature";
    }

    feature HAVE_MARVELL {
        description "MARVELL feature";
    }

    feature HAVE_TIBIT {
        description "TIBIT feature";
    }

    feature HAVE_MLAG {
        description "mlag feature";
    }

    feature HAVE_DHCP_CLIENT {
        description "dhcp feature";
    }

    feature HAVE_IPV6 {
        description "IPV6 feature";
    }

    feature HAVE_NSM_IF_UNNUMBERED {
        description "nsm interface unnumbered feature";
    }

    feature HAVE_MCAST_IPV6 {
        description "MCAST-IPV6 feature";
    }

    feature HAVE_VRRP_V3 {
        description "VRRP V3 Feature";
    }

    feature HAVE_NSM_IF_ARBITER {
        description "NSM Interface Arbiter";
    }

    feature HAVE_QOS {
        description "qos  feature";
    }

    feature HAVE_LBD {
        description "lbd feature";
    }

    feature HAVE_RATE_LIMIT {
        description "rate limit feature";
    }

    feature HAVE_INTERFACE_NAME_MAPPING {
        description "original ifname feature";
    }

    feature HAVE_SUBINTERFACE {
        description "subinterface feature";
    }

    feature HAVE_MACSEC {
        description "MACsec feature";
    }

    feature HAVE_ALLOWED_ETHERTYPE {
        description "allowed ethertype feature";
    }

    feature HAVE_TFO {
        description "tfo  feature";
    }

    feature HAVE_UDLD {
        description "udld  feature";
    }

    feature HAVE_TDM_VC {
        description "TDM VC mpls feature";
    }

    feature HAVE_TUNNEL {
        description "tunnel feature";
    }

    feature HAVE_TUNNEL_IPV6 {
        description "tunnel ipv6 feature";
    }

    feature HAVE_GRE_KEY {
        description "tunnel gre-key feature";
    }

    feature HAVE_USER_HSL {
        description "User HSL feature";
    }

    feature HAVE_OBM_DROP_CNTRS {
        description "OBM drop counters feature";
    }

    feature HAVE_SR_MPLS {
        description "Segment-routing mpls feature";
    }

    feature HAVE_POND {
        description "PON feature";
    }

    feature HAVE_LACP {
        description "lacp feature";
    }

    feature HAVE_SNIFF_INTF {
        description "sniff feature";
    }

    feature HAVE_PROVIDER_BRIDGE {
        description "Provider Bridge feature";
    }

    feature HAVE_TE {
        description "TE Enabled";
    }

    feature HAVE_BGP_FLOWSPEC {
        description "BGP Flowspec Feature";
    }

    feature HAVE_SYNCED {
        description "Precision Time Protocol (PTP) feature";
    }

    feature BUILD_PRODUCT_VERSION {
        description "Software build product version feature";
    }

    feature BUILD_NUMBER {
        description "Software build number feature";
    }

    feature HAVE_HA {
        description "HA feature";
    }

    feature HAVE_TRILLD {
        description "TRILL feature";
    }

    feature HAVE_IPSEC {
        description "IPSEC feature";
    }

    feature HAVE_BFD {
        description "BFD feature";
    }

    feature HAVE_ASYNC {
        description "Async feature";
    }

    feature HAVE_DCB {
        description "dcb feature";
    }

    feature HAVE_DEFAULT_BRIDGE {
        description "default bridge feature";
    }

    feature HAVE_VLAN {
        description "vlan feature";
    }

    feature HAVE_I_BEB {
        description "vlan feature";
    }

    feature HAVE_B_BEB {
        description "vlan feature";
    }

    feature HAVE_RPVST_PLUS {
        description "rpvst feature";
    }

    feature HAVE_SPBD {
        description "spbd feature";
    }

    feature HAVE_CUSTOM2_QOS {
        description "QoS custom options2";
    }

    feature HAVE_MSTPD {
        description "MSTPD feature";
    }

    feature HAVE_VLAN_CLASS {
        description "VLAN Classifier feature";
    }

    feature HAVE_PBB_TE {
        description "PBB TE bridge feature";
    }

    feature HAVE_PVLAN {
        description "PVLAN feature";
    }

    feature HAVE_G8032V2 {
        description "g8032v2 feature";
    }

    feature HAVE_G8032 {
        description "g8032 feature";
    }

    feature NSM_VLAN_ERPS_CONF {
        description "VLAN erps conf feature";
    }

    feature HAVE_ACL {
        description "ACL feature";
    }

    feature HAVE_VLAN_ACCESS_MAP {
        description "VLAN access-map feature";
    }

    feature HAVE_CUSTOM4_QOS {
        description "QoS custom options4 Marvell AC5X";
    }

    feature HAVE_INTELFM {
        description "intelfm feature enabled";
    }

    feature HAVE_PB_STATIC_FDB_CUSTOM_CONFIG {
        description "Provider bridge static MAC feature";
    }

    feature HAVE_HELIX4 {
        description "Have helix4";
    }

    feature HAVE_VLAN_XC {
        description "VLAN XC support enabled";
    }

    feature HAVE_PORT_XC {
        description "PORT XC support enabled";
    }

    feature HAVE_L2GP {
        description "l2gp feature";
    }

    feature HAVE_DPDK {
        description "dpdk Feature";
    }

    feature HAVE_ROUTED_VLAN {
        description "routed vlan Feature";
    }

    feature HAVE_MCEC {
        description "MCEC feature";
    }

    feature HAVE_LACPV2 {
        description "LLDPV2 feature enabled";
    }

    feature HAVE_LAGD {
        description "HAVE_LAGD feature is enabled";
    }

    feature HAVE_LLDPV2 {
        description "HAVE_LLDPV2 feature is enabled";
    }

    feature HAVE_POE {
        description "PoE feature";
    }

    feature HAVE_RIBD {
        description "HAVE_RIBD feature is enabled";
    }

    feature HAVE_OBJ_TRACKING {
        description "Object tracking feature";
    }

    feature HAVE_MPLS_AWARE_RIB {
        description "Support for recursive static and BGP routes resolved with MPLS nexthop";
    }

    feature HAVE_MULTIPATH {
        description "multipath feature";
    }

    feature HAVE_BGP_LS {
        description "Border Gateway Protocol (BGP) Link State";
    }

    feature HAVE_DSTE {
        description "Diff Serv TE feature ";
    }

    feature HAVE_GMPLS {
        description "Generalized Multi-Protocol Label Switching (GMPLS)";
    }

    feature HAVE_LDPD {
        description "Label Distribution Protocol (LDP)";
    }

    feature HAVE_LSP_PROTECTION {
        description "Label-Switched Path (LSP) protection";
    }

    feature HAVE_NSSA {
        description "Not-So-Stubby Area (NSSA)";
    }

    feature HAVE_OPAQUE_LSA {
        description "Opaque Link-State Advertisement (LSA)";
    }

    feature HAVE_OSPF_DB_OVERFLOW {
        description "OSPF DataBase (DB) overflow";
    }

    feature HAVE_OSPF_CSPF {
        description "OSPF Constrained Shortest Path First (CSPF)";
    }

    feature HAVE_OSPF_LFA {
        description "OSPF Loop Free Alternate (LFA)";
    }

    feature HAVE_OSPF_TE {
        description "OSPF Traffic Engineering (TE)";
    }

    feature HAVE_OSPF_TI_LFA {
        description "OSPF topology independent Loop Free Alternate (LFA)";
    }

    feature HAVE_RESTART {
        description "Restart capability";
    }

    feature HAVE_TDM {
        description "SONET, SDH, OTN feature";
    }

    feature HAVE_VRF_OSPF {
        description "OSPF Virtual Routing and Forwarding (VRF)";
    }

    feature HAVE_OSPF_STUB_ROUTER {
        description "Generate lsa with max-metric";
    }

    feature HAVE_OSPFD {
        description "HAVE_OSPFD feature is enabled";
    }

    feature HAVE_OSPF_MULTI_INST {
        description "OSPF Multiple Instances";
    }

    feature HAVE_OSPF_OD {
        description "OSPF Deman Circuit";
    }

    feature HAVE_OSPF_MULTI_AREA {
        description "OSPF Multi Area";
    }

    feature HAVE_OSPF6_CSPF {
        description "OSPFv3 Constrained Shortest Path First (CSPF)";
    }

    feature HAVE_OSPF6_LFA {
        description "OSPFv3 Loop Free Alternate (LFA)";
    }

    feature HAVE_OSPF6_OD {
        description "OSPFv3 Deman Circuit";
    }

    feature HAVE_OSPF6_TE {
        description "OSPFv3 Traffic Engineering (TE)";
    }

    feature HAVE_VRF_OSPF6 {
        description "OSPFv3 Virtual Routing and Forwarding (VRF)";
    }

    feature HAVE_OSPF6D {
        description "HAVE_OSPF6D feature is enabled";
    }

    feature HAVE_BGPD {
        description "HAVE_BGPD feature is enabled";
    }

    feature HAVE_VPN_ECMP {
        description "HAVE_VPN_ECMP feature enabled";
    }

    feature BGP_L2VPN_VPLS_MODE {
        description "l2vpn vpls feature enabled";
    }

    feature HAVE_EXT_CAP_ASN {
        description "EXT-CAP-ASN feature enabled";
    }

    feature HAVE_BGP_VPLS {
        description "bgp vpls feature enabled";
    }

    feature HAVE_6PE {
        description "bgp 6PE feature enabled";
    }

    feature HAVE_BGP_TABLE_MAP {
        description "bgp table map feature enabled";
    }

    feature HAVE_TCP_MD5SIG {
        description "tcp md5 feature enabled";
    }

    feature HAVE_BGP_ADD_PATH {
        description "additional path feature enabled";
    }

    feature HAVE_BGP_AIGP {
        description "AIGP feature enabled";
    }

    feature HAVE_BGP_LU {
        description "bgp lu feature";
    }

    feature HAVE_BGP_MPLS_RESTART {
        description "bgp BGP-MPLS-RESTART feature enabled";
    }

    feature HAVE_BGP_PIC_CORE_EDGE {
        description "pic core feature";
    }

    feature HAVE_MPLS_LSP_TRACKING {
        description "MPLS LSP tracking";
    }

    feature HAVE_BGP_RPKI_ORIGIN_VALIDATION {
        description "BGP RPKI Origin Validation State";
    }

    feature HAVE_UNNUM {
        description "BGP unnumbered feature";
    }

    feature HAVE_BGP_EPE {
        description "BGP Egress Peer Engineering feature";
    }

    feature HAVE_BFD_MAIN {
        description "BFD feature enabled";
    }

    feature HAVE_BFD_MONO {
        description "BFD-MONO feature enabled";
    }

    feature HAVE_BFD_HW_OFFLOAD {
        description "BFD HW Offload feature";
    }

    feature HAVE_MPLS_OAM {
        description "MPLS-OAM feature enabled";
    }

    feature HAVE_MPLS_TP {
        description "MPLS TP feature";
    }

    feature HAVE_CUSTOM1_MPLS_BFD {
        description "MPLS LSP BFD feature enabled";
    }

    feature HAVE_VCCV {
        description "MPLS VCCV feature";
    }

    feature HAVE_SBFD {
        description "HAVE_SBFD feature is enabled";
    }

    feature HAVE_MPLS_TUNNEL {
        description "Generic MPLS Tunnel Infra Feature";
    }

    feature HAVE_SR_POLICY {
        description "SR policy feature";
    }

    feature HAVE_TWAMP {
        description "TE feature";
    }

    feature HAVE_VRRPD {
        description "HAVE_VRRPD feature is enabled";
    }

    feature HAVE_COPP_FILTER {
        description "COPP filter feature";
    }

    feature HAVE_ISISD {
        description "HAVE_ISISD feature is enabled";
    }

    feature HAVE_MULTI_TOPOLOGY {
        description "multi-topology feature";
    }

    feature HAVE_VRF_ISIS {
        description "ISIS VRF feature";
    }

    feature HAVE_ISIS_LFA {
        description "ISIS feature";
    }

    feature HAVE_ISIS_TI_LFA {
        description "ISIS TILFA feature";
    }

    feature HAVE_PROTOCOL_TOPOLOGY {
        description "Protocol topology feature";
    }

    feature HAVE_WIDE_METRIC {
        description "wide metric feature";
    }

    feature HAVE_ISIS_TE {
        description "ISIS-TE feature";
    }

    feature HAVE_ISIS_CSPF {
        description "ISIS-CSPF feature";
    }

    feature HAVE_ISIS_SR {
        description "ISIS SR Feature";
    }

    feature HAVE_MPLS_P2MP {
        description "MPLS P2MP feature";
    }

    feature HAVE_SRLG {
        description "ISIS Traffic Engineering Shared-Risk Link Group feature";
    }

    feature HAVE_PIMD {
        description "PIM capability";
    }

    feature HAVE_PIM_IPV4 {
        description "PIM capability";
    }

    feature HAVE_PIM_IPV6 {
        description "PIM IPv6 feature";
    }

    feature HAVE_PIM_BIDIR {
        description "PIM Bidirectional";
    }

    feature HAVE_PIM_ECMP_REDIRECT {
        description "PIM Equal-Cost Multi-Path (ECMP)";
    }

    feature HAVE_PIM_MSDP_API {
        description "PIM Multicast Source Discovery Protocol";
    }

    feature HAVE_PIM_SM {
        description "PIM Sparse Mode (SM)";
    }

    feature HAVE_PIM_SMDM {
        description "PIM Sparse Mode and Dense Mode (SMDM)";
    }

    feature HAVE_PIM_SSM {
        description "PIM Source Specific Multicast (SSM)";
    }

    feature HAVE_PIM_DM {
        description "PIM dense mode";
    }

    feature HAVE_PIM_MSDP {
        description "PIM Multicast Source Discovery Protocol";
    }

    feature HAVE_PIM_SM_VRRP_AWARE {
        description "PIM sparse mode Virtual Router Redundancy Protocol (VRRP) aware";
    }

    feature HAVE_EVPN_VPWS {
        description "EVPN-Xconnect feature enabled";
    }

    feature HAVE_XGS5 {
        description "XGS feature";
    }

    feature HAVE_RTAG7 {
        description "RTAG7 feature";
    }

    feature HAVE_NVGRE {
        description "NVGRE feature";
    }

    feature HAVE_SYSLOG {
        description "syslog feature";
    }

    feature HAVE_IMI {
        description "HAVE_IMI feature is enabled";
    }

    feature HAVE_FMS {
        description "FMS feature";
    }

    feature HAVE_VLOGD {
        description "VLOGD Feature";
    }

    feature HAVE_EVENT_MANAGER {
        description "Event Manager Feature";
    }

    feature HAVE_DHCP_SNOOP {
        description "HAVE_DHCP_SNOOP feature is enabled";
    }

    feature HAVE_HOSTP_DHCP_RELAY {
        description "HAVE_HOSTP_DHCP_RELAY feature is enabled";
    }

    feature HAVE_HOSTP_DHCP_SERVER {
        description "HAVE_HOSTP_DHCP_SERVER feature is enabled";
    }

    feature HAVE_AAA {
        description "aaa feature";
    }

    feature HAVE_RADIUS_CLIENT {
        description "HAVE_RADIUS_CLIENT feature is enabled";
    }

    feature HAVE_LDAP_CLIENT {
        description "ldap-client feature enabled";
    }

    feature HAVE_USER_MGMT {
        description "user management feature";
    }

    feature HAVE_RBAC {
        description "Role Based Access Control feature";
    }

    feature HAVE_SSH_SERVER {
        description "ssh server feature";
    }

    feature HAVE_TELNET_SERVER {
        description "telnet-server feature";
    }

    feature HAVE_MGMT_PORT_VRF_NS {
        description "mgmt-port-vrf-ns feature";
    }

    feature HAVE_HOSTP_NTP {
        description "ntp feature";
    }

    feature HAVE_TACACS_CLIENT {
        description "tacacs client feature";
    }

    feature HAVE_DNS_CLIENT {
        description "dns-client feature";
    }

    feature HAVE_SFLOW {
        description "sFlow feature";
    }

    feature HAVE_CUSTOM1_ACL {
        description "custom1 access-list options";
    }

    feature HAVE_UT {
        description "ut";
    }

    feature HAVE_IPFIX {
        description "HAVE_IPFIX feature is enabled";
    }

    feature HAVE_COHERENT_OPTICS {
        description "Coherent Optics";
    }

    feature HAVE_FLEXLM {
        description "License feature enabled";
    }

    feature HAVE_PSERVD {
        description "Watchdog feature";
    }

    feature HAVE_ZEBOS_CORE_ANALYSER {
        description "Core file management";
    }

    feature HAVE_MRIBD {
        description "HAVE_MRIBD feature is enabled";
    }

    feature HAVE_L2MRIBD {
        description "HAVE_L2MRIBD feature is enabled";
    }

    feature HAVE_MLD_SNOOP {
        description "mld snooping feature";
    }

    feature HAVE_PBR {
        description "PBR feature";
    }

    feature HAVE_G8031 {
        description "G8031 feature ";
    }

    feature HAVE_GELS {
        description "gels feature ";
    }

    feature HAVE_RIPD {
        description "HAVE_RIPD feature is enabled";
    }

    feature HAVE_RIP_GR_SUPPORT {
        description "RIP Graceful Restart feature";
    }

    feature HAVE_VRF_RIP {
        description "RIP VRF feature";
    }

    feature HAVE_SNMP_AGENT {
        description "SNMP-AGENT feature";
    }

    feature HAVE_AGENTX {
        description "SNMP-AGENTX feature";
    }

    feature HAVE_SNMP_V3 {
        description "snmp version v3";
    }

    feature HAVE_MLDP_P2MP {
        description "MLDP P2MP feature";
    }

    feature HAVE_MLDP_MP2MP {
        description "MLDP_MP2MP feature";
    }

    feature HAVE_HA_MPLS {
        description "MPLS feature";
    }

    feature HAVE_HA_LDP_GR {
        description "HA LDP GR Feature enabled";
    }

    feature HAVE_MPLS_VC {
        description "MPLS VC enabled";
    }

    feature HAVE_LDP_INTER_AREA {
        description "INTER AREA feature";
    }

    feature HAVE_ICCP {
        description "ICCP feature";
    }

    feature HAVE_ICCP_CLI {
        description "ICCP CLI feature";
    }

    feature HAVE_CUSTOM1_MPLS {
        description "Custom flag for XGS";
    }

    feature HAVE_LDP_LFA {
        description "LDP FRR feature";
    }

    feature HAVE_LDP_SESS_PROT {
        description "LDP Session Protection feature";
    }

    feature HAVE_LDP_TUNNELING {
        description "LDP over RSVP feature";
    }

    feature HAVE_VPLS {
        description "vpls feature";
    }

    feature HAVE_CUSTOM1_QOS {
        description "QoS custom options1";
    }

    feature HAVE_SERVICE_QUEUING_2 {
        description "Service queueing for DNX";
    }

    feature HAVE_EXTENDED_QOS {
        description "QoS extended options";
    }

    feature HAVE_POLICE_MAX_RATE_500GBPS {
        description "QoS police cir/eir maximum rate supported is 500GBPS";
    }

    feature HAVE_DIFFSERV {
        description "Diffserv feature";
    }

    feature HAVE_QOS_MAPPING_PROFILE {
        description "QoS Mapping Profile feature";
    }

    feature HAVE_BUFFER_TUNING {
        description "Buffer Tuning feature";
    }

    feature HAVE_CUSTOM3_QOS {
        description "QoS custom options3";
    }

    feature HAVE_RSVPD {
        description "HAVE_RSVPD feature is enabled";
    }

    feature HAVE_MPLS_FRR {
        description "MPLS-FRR feature";
    }

    feature HAVE_CSPF {
        description "CSPF feature";
    }

    feature HAVE_RSVP_GRST {
        description "grst feature";
    }

    feature HAVE_MPLS_FWD {
        description "MPLS Forwarder feature";
    }

    feature HAVE_AUTO_BANDWIDTH {
        description "Auto bandwidth feature";
    }

    feature HAVE_RSVP_MULTIPATH {
        description "RSVP multipath feature";
    }

    feature HAVE_PCEP_RSVP {
        description "gmpls feature";
    }

    feature HAVE_CUSTOM2_MPLS {
        description "Custom flag for Dune";
    }

    feature HAVE_PCE {
        description "pce feature";
    }

    feature HAVE_CUSTOM_INTRA {
        description "Intarcom feature";
    }

    feature IF_BANDWIDTH_INFO {
        description "Helix feature";
    }

    feature HAVE_MPLS_ECMP {
        description "LDP ECMP FEATURE";
    }

    feature HAVE_L2VPN_STITCHING {
        description "Enable L2VPN stitching related features";
    }

    feature HAVE_MPLS_STATS {
        description "MPLS Stats Feature";
    }

    feature HAVE_FEC129 {
        description "Generic FEC129 Feature";
    }

    feature HAVE_UNI_CLI {
        description "UNI CLI";
    }

    feature HAVE_PCEP_SR {
        description "pcep support for sr policy feature";
    }

    feature HAVE_PCEP_SRV6 {
        description "support for PCEP srv6 feature";
    }

    feature HAVE_GMPLS_SONET_SIMULATION {
        description "GMPLS SONET Simulation";
    }

    feature HAVE_TRIDENT2 {
        description "trident2 feature";
    }

    feature HAVE_TRIDENT2PLUS {
        description "trident2plus feature";
    }

    feature HAVE_CMMD {
        description "HAVE_CMMD feature is enabled";
    }

    feature HAVE_VPIU_EMULATION {
        description "Video PIU Emulation";
    }

    feature HAVE_PTP_HW_OFFLOAD {
        description "PTP hardware offload feature enabled";
    }

    feature HAVE_PTP_HW_OFFLOAD_CUSTOM1 {
        description "PTP hardware offload feature enabled";
    }

    feature HAVE_XCVR_MODEL {
        description "XCVR CLI model";
    }

    feature HAVE_BCM_UFT {
        description "bcm uft feature";
    }

    feature HAVE_CUSTOM1_HW_BFD {
        description "dune bfd hardware offload feature";
    }

    feature CCM_HW_OFFLOAD {
        description "cfm ccm hardware offload feature";
    }

    feature HAVE_ELK_TCAM {
        description "elk tcam feature";
    }

    feature HAVE_CUSTOM3_ACL {
        description "DNX";
    }

    feature HAVE_TWAMP_HW_OFFLOAD {
        description "twamp test pkt hardware offload feature";
    }

    feature HAVE_ADVANCE_MIRROR {
        description "advance mirror feature";
    }

    feature ENABLE_HAL_PATH {
        description "hal path feature";
    }

    feature HAVE_VXLAN_STATS {
        description "vxlan counters";
    }

    feature HAVE_L2_AGE_SHOW {
        description "L2 age show";
    }

    feature HAVE_ARM_ARCH {
        description "HAVE_ARM_ARCH feature is enabled";
    }

    feature HAVE_AUTHD {
        description "HAVE_AUTHD feature";
    }

    feature HAVE_MAC_AUTH {
        description "MAC_AUTH feature";
    }

    feature HAVE_ENCRYPT_CLEARTEXT {
        description "OpenSSL crypto library available";
    }

    feature HAVE_CUSTOM2_ACL {
        description "CUSTOM2 ACL feature";
    }

    feature HAVE_PLATFORM_RAS {
        description "HAVE_PLATFORM_RAS feature is enabled";
    }

    feature HAVE_RPF {
        description "Unicast Reverse Path Forwarding feature";
    }

    feature HAVE_GLOBAL_URPF_ALLOW_DEFAULT {
        description "Default route check globally ";
    }

    feature HAVE_RIPNGD {
        description "HAVE_RIPNGD feature is enabled";
    }

    feature HAVE_VRF_RIPNG {
        description "RIPng VRF feature";
    }

    feature HAVE_TRILL_OAM {
        description "trill OAM feature";
    }

    feature HAVE_NDD {
        description "HAVE_NDD feature is enabled";
    }

    feature HAVE_CUSTOM2_NDD {
        description " custom2 cli for DUNE board";
    }

    feature HAVE_VRF_ND {
        description "vrf nd feature";
    }

    feature PNE_VERSION_6_9 {
        description "clear user feature";
    }

    feature HAVE_REBOOT {
        description "imi reboot feature";
    }

    feature HAVE_RTADV {
        description "IPv6 Router Advertisement";
    }

    feature HAVE_MIP6 {
        description "Mobility for IPv6";
    }

    feature HAVE_NAT {
        description "NAT feature";
    }

    feature Y1731_HW_OFFLOAD {
        description "CFM Y1731 Packets generated from hardware";
    }

    feature HAVE_VXLAN_OAM {
        description "CFM over VxLAN support feature";
    }

    feature HAVE_CFM_Y1731 {
        description "CFM Y1731 feature";
    }

    feature HAVE_EFM {
        description "Ethernet OAM feature";
    }

    feature HAVE_PTPD {
        description "HAVE_PTPD feature is enabled";
    }

    feature HAVE_PTP_HW_OFFLOAD_CUSTOM2 {
        description "Precision Time Protocol (PTP) custom2 feature";
    }

    feature HAVE_GUEST_VM {
        description "Virtual Machine feature";
    }

    feature HAVE_GUEST_VM_HIDDEN_CLI {
        description "Hiding GUEST VM cli feature";
    }

    feature HAVE_PCEP {
        description "HAVE_PCEP feature is enabled";
    }

    feature HAVE_IPSLA {
        description "ip-sla feature";
    }

    feature HAVE_CUSTOM1_SUBINTERFACE {
        description "subinterface feature";
    }

    feature HAVE_MACSEC_J2P_SEC_TAG_VALIDATE_STRICT_MODE_NOT_SET {
        description "MACsec tag validation configurable";
    }

    feature HAVE_IPSEC_HW {
        description "IPsec HW feature";
    }

    feature HAVE_FLEXE {
        description "FlexE Feature";
    }

    feature HAVE_HWTABLE_SNMP {
        description "HWTABLE warning/alert thresholds SNMP monitoring";
    }

    feature HAVE_ALL_PHOTONICS_CUSTOM {
        description "All Photonics custom feature";
    }

    feature HAVE_AI_ML {
        description "AI ML features";
    }

    feature HAVE_DLB {
        description "dlb feature";
    }

    feature HAVE_CUSTOM5_QOS {
        description "It is of HAVE_CUSTOM5_QOS Feature";
    }

    feature HAVE_DVMRPD {
        description "It is of HAVE_DVMRPD Feature";
    }

    feature HAVE_GMRP {
        description "It is of HAVE_GMRP Feature";
    }

    feature HAVE_GVRP {
        description "It is of HAVE_GVRP Feature";
    }

    feature HAVE_HTTP_SUPPORT {
        description "It is of HAVE_HTTP_SUPPORT Feature";
    }

    feature HAVE_PVLAN_TRUNK {
        description "It is of HAVE_PVLAN_TRUNK Feature";
    }

    feature HAVE_RMOND {
        description "It is of HAVE_RMOND Feature";
    }

    feature NOT_HAVE_ADVANCE_MIRROR {
        description "It is negation of HAVE_ADVANCE_MIRROR";
    }

    feature NOT_HAVE_ARM_ARCH {
        description "It is negation of HAVE_ARM_ARCH";
    }

    feature NOT_HAVE_BFD_HW_OFFLOAD {
        description "It is negation of HAVE_BFD_HW_OFFLOAD";
    }

    feature NOT_HAVE_BROADCOM {
        description "It is negation of HAVE_BROADCOM";
    }

    feature NOT_HAVE_COPP_FILTER {
        description "It is negation of HAVE_COPP_FILTER";
    }

    feature NOT_HAVE_CUSTOM1_HW_BFD {
        description "It is negation of HAVE_CUSTOM1_HW_BFD";
    }

    feature NOT_HAVE_CUSTOM1_MPLS {
        description "It is negation of HAVE_CUSTOM1_MPLS";
    }

    feature NOT_HAVE_CUSTOM1_SUBINTERFACE {
        description "It is negation of HAVE_CUSTOM1_SUBINTERFACE";
    }

    feature NOT_HAVE_CUSTOM2_MPLS {
        description "It is negation of HAVE_CUSTOM2_MPLS";
    }

    feature NOT_HAVE_CUSTOM2_QOS {
        description "It is negation of HAVE_CUSTOM2_QOS";
    }

    feature NOT_HAVE_CUSTOM3_ACL {
        description "It is negation of HAVE_CUSTOM3_ACL";
    }

    feature NOT_HAVE_CUSTOM3_QOS {
        description "It is negation of HAVE_CUSTOM3_QOS";
    }

    feature NOT_HAVE_CUSTOM4_QOS {
        description "It is negation of HAVE_CUSTOM4_QOS";
    }

    feature NOT_HAVE_CUSTOM5_LTSW {
        description "It is negation of HAVE_CUSTOM5_LTSW";
    }

    feature NOT_HAVE_CUSTOM5_QOS {
        description "It is negation of HAVE_CUSTOM5_QOS";
    }

    feature NOT_HAVE_DNX {
        description "It is negation of HAVE_DNX";
    }

    feature NOT_HAVE_DUNE {
        description "It is negation of HAVE_DUNE";
    }

    feature NOT_HAVE_FLEXLM {
        description "It is negation of HAVE_FLEXLM";
    }

    feature NOT_HAVE_HELIX4 {
        description "It is negation of HAVE_HELIX4";
    }

    feature NOT_HAVE_MARVELL {
        description "It is negation of HAVE_MARVELL";
    }

    feature NOT_HAVE_MGMT_PORT_VRF_NS {
        description "It is negation of HAVE_MGMT_PORT_VRF_NS";
    }

    feature NOT_HAVE_MPLS_TUNNEL {
        description "It is negation of HAVE_MPLS_TUNNEL";
    }

    feature NOT_HAVE_NDD {
        description "It is negation of HAVE_NDD";
    }

    feature NOT_HAVE_OSPF6_TE {
        description "It is negation of HAVE_OSPF6_TE";
    }

    feature NOT_HAVE_POND {
        description "It is negation of HAVE_POND";
    }

    feature NOT_HAVE_RESTART {
        description "It is negation of HAVE_RESTART";
    }

    feature NOT_HAVE_SWFWDR {
        description "It is negation of HAVE_SWFWDR";
    }

    feature NOT_HAVE_TDM {
        description "It is negation of HAVE_TDM";
    }

    feature NOT_HAVE_TIBIT {
        description "It is negation of HAVE_TIBIT";
    }

    feature NOT_HAVE_TRIDENT2 {
        description "It is negation of HAVE_TRIDENT2";
    }

    feature NOT_HAVE_TRIDENT2PLUS {
        description "It is negation of HAVE_TRIDENT2PLUS";
    }

    feature NOT_HAVE_USER_HSL {
        description "It is negation of HAVE_USER_HSL";
    }

    feature NOT_HAVE_VRRP_V3 {
        description "It is negation of HAVE_VRRP_V3";
    }

    feature NOT_HAVE_VXLAN_OAM {
        description "It is negation of HAVE_VXLAN_OAM";
    }

    feature NOT_HAVE_XCVR_MODEL {
        description "It is negation of HAVE_XCVR_MODEL";
    }

    feature NOT_IF_BANDWIDTH_INFO {
        description "It is negation of IF_BANDWIDTH_INFO";
    }

    feature NOT_PNE_VERSION_3_7 {
        description "It is negation of PNE_VERSION_3_7";
    }

    feature NOT_PNE_VERSION_6_9 {
        description "It is negation of PNE_VERSION_6_9";
    }

    feature HAVE_SERVICE_MAPPING_OR_HAVE_SRV6 {
        description "It is or feature of HAVE_SERVICE_MAPPING_OR_HAVE_SRV6";
    }

    feature HAVE_MPLS_OR_HAVE_SRV6 {
        description "It is or feature of HAVE_MPLS_OR_HAVE_SRV6";
    }

    feature HAVE_BROADCOM_OR_HAVE_MARVELL {
        description "It is or feature of HAVE_BROADCOM_OR_HAVE_MARVELL";
    }

    feature HAVE_CUSTOM2_QOS_OR_HAVE_CUSTOM4_QOS {
        description "It is or feature of HAVE_CUSTOM2_QOS_OR_HAVE_CUSTOM4_QOS";
    }

    feature HAVE_PROVIDER_BRIDGE_OR_HAVE_B_BEB {
        description "It is or feature of HAVE_PROVIDER_BRIDGE_OR_HAVE_B_BEB";
    }

    feature HAVE_DUNE_OR_HAVE_MARVELL {
        description "It is or feature of HAVE_DUNE_OR_HAVE_MARVELL";
    }

    feature HAVE_ISIS_LFA_OR_HAVE_ISIS_TI_LFA {
        description "It is or feature of HAVE_ISIS_LFA_OR_HAVE_ISIS_TI_LFA";
    }

    feature HAVE_ISIS_SR_OR_HAVE_SRV6 {
        description "It is or feature of HAVE_ISIS_SR_OR_HAVE_SRV6";
    }

    feature HAVE_PIM_IPV4_OR_HAVE_PIM_IPV6 {
        description "It is or feature of HAVE_PIM_IPV4_OR_HAVE_PIM_IPV6";
    }

    feature HAVE_MPLS_OR_HAVE_VXLAN_OR_HAVE_SRV6 {
        description "It is or feature of HAVE_MPLS_OR_HAVE_VXLAN_OR_HAVE_SRV6";
    }

    feature HAVE_DHCP_CLIENT_OR_HAVE_HOSTPD_OR_HAVE_DHCP_SNOOP {
        description "It is or feature of HAVE_DHCP_CLIENT_OR_HAVE_HOSTPD_OR_HAVE_DHCP_SNOOP";
    }

    feature HAVE_CUSTOM1_ACL_OR_HAVE_COPP_FILTER {
        description "It is or feature of HAVE_CUSTOM1_ACL_OR_HAVE_COPP_FILTER";
    }

    feature NOT_HAVE_DUNE_OR_HAVE_DNX {
        description "It is or feature of NOT_HAVE_DUNE_OR_HAVE_DNX";
    }

    feature HAVE_CUSTOM1_QOS_OR_HAVE_CUSTOM3_QOS_OR_HAVE_CUSTOM4_QOS {
        description "It is or feature of HAVE_CUSTOM1_QOS_OR_HAVE_CUSTOM3_QOS_OR_HAVE_CUSTOM4_QOS";
    }

    feature HAVE_CUSTOM3_QOS_OR_HAVE_CUSTOM4_QOS {
        description "It is or feature of HAVE_CUSTOM3_QOS_OR_HAVE_CUSTOM4_QOS";
    }

    feature HAVE_CUSTOM1_QOS_OR_HAVE_CUSTOM4_QOS {
        description "It is or feature of HAVE_CUSTOM1_QOS_OR_HAVE_CUSTOM4_QOS";
    }

    feature HAVE_CUSTOM1_QOS_OR_HAVE_CUSTOM3_QOS {
        description "It is or feature of HAVE_CUSTOM1_QOS_OR_HAVE_CUSTOM3_QOS";
    }

    feature HAVE_VPLS_OR_HAVE_MPLS_VC {
        description "It is or feature of HAVE_VPLS_OR_HAVE_MPLS_VC";
    }

    feature HAVE_SR_POLICY_OR_HAVE_SRV6 {
        description "It is or feature of HAVE_SR_POLICY_OR_HAVE_SRV6";
    }

    feature HAVE_PCEP_SR_OR_HAVE_PCEP_SRV6 {
        description "It is or feature of HAVE_PCEP_SR_OR_HAVE_PCEP_SRV6";
    }

    feature HAVE_SR_POLICY_OR_HAVE_PCEP_SRV6 {
        description "It is or feature of HAVE_SR_POLICY_OR_HAVE_PCEP_SRV6";
    }

    feature HAVE_SRV6_OR_HAVE_SR_MPLS_OR_HAVE_SR_POLICY {
        description "It is or feature of HAVE_SRV6_OR_HAVE_SR_MPLS_OR_HAVE_SR_POLICY";
    }

    feature HAVE_SR_POLICY_OR_HAVE_SRV6_OR_HAVE_SR_MPLS {
        description "It is or feature of HAVE_SR_POLICY_OR_HAVE_SRV6_OR_HAVE_SR_MPLS";
    }

    feature Y1731_HW_OFFLOAD_OR_HAVE_SWFWDR {
        description "It is or feature of Y1731_HW_OFFLOAD_OR_HAVE_SWFWDR";
    }

    feature NOT_HAVE_CUSTOM1_MPLS_OR_HAVE_VXLAN_OAM {
        description "It is or feature of NOT_HAVE_CUSTOM1_MPLS_OR_HAVE_VXLAN_OAM";
    }

    feature HAVE_PTP_HW_OFFLOAD_CUSTOM1_OR_HAVE_PTP_HW_OFFLOAD_CUSTOM2 {
        description "It is or feature of HAVE_PTP_HW_OFFLOAD_CUSTOM1_OR_HAVE_PTP_HW_OFFLOAD_CUSTOM2";
    }

    feature HAVE_SRV6_OR_HAVE_SR_MPLS_OR_HAVE_MPLS {
        description "It is or feature of HAVE_SRV6_OR_HAVE_SR_MPLS_OR_HAVE_MPLS";
    }

}
