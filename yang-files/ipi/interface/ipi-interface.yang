/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-interface.yang
*
*/

module ipi-interface {

    yang-version 1.1;

    namespace   "http://www.ipinfusion.com/yang/ocnos/ipi-interface";

    prefix "ipi-interface";

    import cml-data-types {
        prefix cml-data-types;
        revision-date 2026-05-15;
    }

    import ietf-yang-types {
        prefix yang;
        revision-date 2013-07-15;
    }

    import ipi-if-types {
        prefix ipi-if-types;
        revision-date 2026-03-10;
    }

    import ipi-network-instance {
        prefix ipi-network-instance;
        revision-date 2026-08-12;
    }

    import ipi-vrf {
        prefix ipi-vrf;
        revision-date 2026-08-12;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for interface object";


    revision "2026-03-10" {
        description "Added attribute for media type";
        reference " 0.23.0.";
    }

    revision "2026-02-12" {
        description "Added dependency for port-security";
        reference " 0.22.8.";
    }

    revision "2026-01-08" {
        description "Added until api for attribute 'vrf-name'";
        reference " 0.22.7.";
    }

    revision "2026-01-06" {
        description "Added dependentObject between interface and port-channel";
        reference " 0.22.6.";
    }

    revision "2025-10-17" {
        description "Reverting changes for LACP and vrf";
        reference " 0.22.5.";
    }

    revision "2025-10-14" {
        description "Added the dependency and corrected sequence for LACP and vrf";
        reference " 0.22.4.";
    }

    revision "2025-10-10" {
        description "Avoid checking UNIQUE in case of default values";
        reference " 0.22.3.";
    }

    revision "2025-10-09" {
        description "Removed blocking for crossconect for XGs platforms";
        reference " 0.22.2.";
    }

    revision "2025-10-07" {
        description "Blocking Bridge-domain and cross-connect for all XGS (DC) platforms";
        reference " 0.22.1.";
    }

    revision "2025-10-06" {
        description "Added acl-set dependentObjects for switchport on interface";
        reference " 0.21.9.";
    }

    revision "2025-09-24" {
        description "Changed the datatype for ether-type attribute";
        reference " 0.21.8.";
    }

    revision "2025-09-11" {
        description "Added dependentObject to cleanup subinterface-encapsulation config, when subinterface is unconfigured.";
        reference " 0.21.7.";
    }

    revision "2025-09-04" {
        description "Removed EVPN_IRB_IF_MODE while configuring IRB interface";
        reference " 0.21.6.";
    }

    revision "2025-08-22" {
        description "Changed error disable type from bits to enum";
        reference " 0.21.5.";
    }

    revision "2025-07-29" {
        description "reinstate:Dependency for subinterface deletion";
        reference " 0.21.4.";
    }

    revision "2025-07-14" {
        description "revert:Dependency for subinterface deletion";
        reference " 0.21.3.";
    }

    revision "2025-07-10" {
        description "Dependency for subinterface deletion";
        reference " 0.21.2.";
    }

    revision "2025-06-27" {
        description "New cmd added - l2protocol all learn-disable";
        reference " 0.21.1.";
    }

    revision "2025-06-25" {
        description "Updated datatype 'IF_ERRDISABLE_STATE_T 'values";
        reference " 0.21.0.";
    }

    revision "2025-06-03" {
        description "Added port dfe and unreliable-los support";
        reference " 0.20.23.";
    }

    revision "2025-05-11" {
        description "Add 'CML_UNIQUE' support for attribute 'vrf-name' and 'primary-ip-addr'";
        reference " 0.20.22.";
    }

    revision "2025-05-09" {
        description "Fix compilation warnings";
        reference " 0.20.21.";
    }

    revision "2025-05-07" {
        description "Removed 'CML_UNIQUE' support for attribute 'vrf-name' and 'primary-ip-addr'";
        reference " 0.20.20.";
    }

    revision "2025-04-29" {
        description "Add 'CML_UNIQUE' support for attribute 'vrf-name' and 'primary-ip-addr'";
        reference " 0.20.19.";
    }

    revision "2025-04-14" {
        description "Added port link training config";
        reference " 0.20.18.";
    }

    revision "2025-04-04" {
        description "Added dependentobject to cleanup the qos/acl configs first";
        reference " 0.20.17.";
    }

    revision "2025-03-17" {
        description "Revert of EFM flag for l2pt efm CLI";
        reference " 0.20.16.";
    }

    revision "2025-01-22" {
        description "Updated helstring for ethertype for DC and SP";
        reference " 0.20.15.";
    }

    revision "2024-12-26" {
        description "Added static MAC support for bridge-domain";
        reference " 0.20.14.";
    }

    revision "2024-12-14" {
        description "Updated  length check for interface name ";
        reference " 0.20.13.";
    }

    revision "2024-11-18" {
        description "Added new datatype IF_ERRDIS_STATUS";
        reference " 0.20.12.";
    }

    revision "2024-10-29" {
        description "Add subtypes for global mtu configuration";
        reference " 0.20.11.";
    }

    revision "2024-10-25" {
        description "Added dependentObject tags related to static-routing";
        reference " 0.20.10.";
    }

    revision "2024-10-17" {
        description "Added missing interface types for IF_HW_TYPE_T";
        reference " 0.20.9.";
    }

    revision "2024-10-03" {
        description "Added support to 400G and 200G in interface negotiated-port-speed";
        reference " 0.20.8.";
    }

    revision "2024-09-19" {
        description "Modified cli helpstring for mac ageing mode";
        reference " 0.20.7.";
    }

    revision "2024-09-11" {
        description "Added when tag under vrf-name pointing to channel-group";
        reference " 0.20.6.";
    }

    revision "2024-09-03" {
        description "CL108 FEC config support";
        reference " 0.20.5.";
    }

    revision "2024-08-21" {
        description "Added CML_MAC_AGEING_T ";
        reference " 0.20.4.";
    }

    revision "2024-08-19" {
        description "Added global mtu configuration support";
        reference " 0.20.3.";
    }

    revision "2024-08-12" {
        description "Added global l2protocol configuration";
        reference " 0.20.2.";
    }

    revision "2024-07-26" {
        description "Make previous revision tag consistent";
        reference " 0.20.1.";
    }

    revision "2024-07-25" {
        description "Added UCMP CLI option";
        reference " 0.20.0.";
    }

    revision "2024-07-24" {
        description "Fixed circular dependencies";
        reference " 0.19.9.";
    }

    revision "2024-07-08" {
        description "Fixed port mirror / interface dependencies";
        reference " 0.19.8.";
    }

    revision "2024-06-18" {
        description "Added BVI element in hardware type datatype";
        reference " 0.19.6.";
    }

    revision "2024-06-07" {
        description "Added CML_BASE_CONFIG_SET_DB_FIRST flag for enable-switchport";
        reference " 0.19.5.";
    }

    revision "2024-05-28" {
        description "Added HAVE_PROVIDER_BRIDGE flag for port-vlan related dependentObject tag";
        reference " 0.19.4.";
    }

    revision "2024-05-23" {
        description "Added depenentObject tag for Service bridge configs unconfigs";
        reference " 0.19.3.";
    }

    revision "2024-05-21" {
        description "Added depenentObject tag for customer bridge configs";
        reference " 0.19.2.";
    }

    revision "2024-05-20" {
        description "Added depenentObject tag for xst datamodel";
        reference " 0.19.1.";
    }

    revision "2024-05-16" {
        description "Removed when tag from ipv6/addresses";
        reference " 0.19.0.";
    }

    revision "2024-04-15" {
        description "Updated the help string for protected-port";
        reference " 0.18.4.";
    }

    revision "2024-03-27" {
        description "Added limited autonegotiation support";
        reference " 0.18.3.";
    }

    revision "2024-02-23" {
        description "Updated max mtu value for Marvell";
        reference " 0.18.2.";
    }

    revision "2024-01-24" {
        description "If Type data-model revision has higher date";
        reference " 0.18.1.";
    }

    revision "2024-01-06" {
        description "Added storm-control errdisable";
        reference " 0.18.0.";
    }

    revision "2024-01-04" {
        description "Removing the  pattern check for description";
        reference " 0.17.5.";
    }

    revision "2023-12-21" {
        description "Added dependentObject tag ipv6 object";
        reference " 0.17.4.";
    }

    revision "2023-12-20" {
        description "Added a new datatype IF_RAON_AODU_STATE";
        reference " 0.17.4.";
    }

    revision "2023-12-18" {
        description "when expression added for LBG db-sync issue";
        reference " 0.17.3.";
    }

    revision "2023-11-15" {
        description "New ELPS CLI restructuring support";
        reference " 0.17.2.";
    }

    revision "2023-11-09" {
        description "Updated datatype for attribute 'eee'";
        reference " 0.17.1.";
    }

    revision "2023-10-24" {
        description "Add the proper dependencies for FlexE objects";
        reference " 0.17.0.";
    }

    revision "2023-10-13" {
        description "Added dependentObject tag for secondayaddress and ipv6 address in vrf fowarding";
        reference " 0.16.20.";
    }

    revision "2023-10-10" {
        description "Change storm-control maximum level to 99%";
        reference " 0.16.19.";
    }

    revision "2023-10-05" {
        description "Updated the help string for mtu";
        reference " 0.16.18.";
    }

    revision "2023-08-23" {
        description "Added datatype IF_ACLIF_TYPE_T";
        reference " 0.16.17.";
    }

    revision "2023-08-18" {
        description "Added pattern tag for the datatype IF_SUBIF_OUTER_TPID_T";
        reference " 0.16.16.";
    }

    revision "2023-08-07" {
        description "Combined breakout and breakout-ifname containers for port breakout";
        reference " 0.16.15.";
    }

    revision "2023-07-25" {
        description "Enable MTU command on IRB interface";
        reference " 0.16.14.";
    }

    revision "2023-07-19" {
        description "Restructred port breakout data model";
        reference " 0.16.13.";
    }

    revision "2023-07-13" {
        description "Inclusion of streaming telemetry yaml file";
        reference " 0.16.12.";
    }

    revision "2023-07-11" {
        description "Enable qos CLI commands for Marvell device";
        reference " 0.16.11.";
    }

    revision "2023-06-30" {
        description "Add mcec as a dependency for deletion";
        reference " 0.16.10.";
    }

    revision "2023-06-26" {
        description "Added install condition for protected-port";
        reference " 0.16.9.";
    }

    revision "2023-05-26" {
        description "Added element types for FEC type configuration support";
        reference " 0.16.8.";
    }

    revision "2023-05-24" {
        description "Updated pattern for description attribute";
        reference " 0.16.7.";
    }

    revision "2023-05-13" {
        description "Updated service-queue command dependencies for save and reload";
        reference " 0.16.6.";
    }

    revision "2023-05-10" {
        description "Added l2 move-allow-first-frame command to DC boards";
        reference " 0.16.5.";
    }

    revision "2023-05-08" {
        description "added support for dune port mode";
        reference " 0.16.4.";
    }

    revision "2023-05-04" {
        description "updated helpstring for mtu";
        reference " 0.16.3.";
    }

    revision "2023-04-28" {
        description "removed HARDWARE_PORT_MODE data type";
        reference " 0.16.2.";
    }

    revision "2023-04-12" {
        description "Added dependency for port breakout config";
        reference " 0.16.1.";
    }

    revision "2023-04-04" {
        description "Removed when tag from ipv4/secondary-addresses for dependency check on 'primary-ip-addr'";
        reference " 0.16.0.";
    }

    revision "2023-03-20" {
        description "Bridge-domain forward cli when flags updated";
        reference " 0.15.7.";
    }

    revision "2023-03-08" {
        description "Cli Error feature improvement for interface cli";
        reference " 0.15.6.";
    }

    revision "2023-03-06" {
        description "Blocked interface level port breakout for Q2";
        reference " 0.15.5.";
    }

    revision "2023-03-03" {
        description "Added datatype for split-horizon";
        reference " 0.15.4.";
    }

    revision "2023-02-28" {
        description "Removing ERPSv2 Bridge id dependency";
        reference " 0.15.3.";
    }

    revision "2023-02-17" {
        description "Updated mtu value for ipv4 packet";
        reference " 0.15.2.";
    }

    revision "2023-02-15" {
        description "Added VxLAN object lists double-tagged-access-interface, untagged-access-interface and tagged-access-interface as dependent object on interfaces/interface/config";
        reference " 0.15.1.";
    }

    revision "2023-02-06" {
        description "Added a trigger to remove the irb interface for 'evpn-mpls-irb'";
        reference " 0.15.0.";
    }

    revision "2022-12-15" {
        description "Added a trigger to remove mtu from po interface when mapped to mlag and members";
        reference " 0.14.3.";
    }

    revision "2022-11-24" {
        description "Blocked interface level port breakout command for DNX";
        reference " 0.14.2.";
    }

    revision "2022-11-14" {
        description "Added support for Storm-control by Frame per second";
        reference " 0.14.1.";
    }

    revision "2022-11-08" {
        description "Depcrating Static Source-guard CLIs";
        reference " 0.14.0.";
    }

    revision "2022-09-27" {
        description "Added loopback-detection in ipi-if-types";
        reference " 0.13.2.";
    }

    revision "2022-09-13" {
        description "Added if-feature HAVE_BGP_EVPN for accessing evpn data model";
        reference " 0.13.1.";
    }

    revision "2022-08-24" {
        description "Added dependent object in interfaces container for re-ordering erpsv2 config. deletion";
        reference " 0.13.0.";
    }

    revision "2022-07-21" {
        description "Add dependent object between interface and port breakout objects";
        reference " 0.12.";
    }

    revision "2022-07-13" {
        description "Added DB trigger for 'ip vrf forwarding' to lo.vrf interface";
        reference " 0.11.1.";
    }

    revision "2022-07-12" {
        description "Added dependent-object-sequencing tag for config container";
        reference " 0.11.1.";
    }

    revision "2022-06-01" {
        description "Updated the yang file with feature";
        reference " 0.11.0.";
    }

    revision "2022-05-12" {
        description "Renamed EVPN IRB related attributes";
        reference " 0.10.0.";
    }

    revision "2022-04-28" {
        description "Renamed EVPN IRB related attributes";
        reference " 0.10.0.";
    }

    revision "2022-04-05" {
        description "Add dependent object between interface and NDD objects";
        reference " 0.9.3.";
    }

    revision "2021-12-15" {
        description "Add if-feature on dependent object between interface and DHCP snooping objects";
        reference " 0.9.2.";
    }

    revision "2021-12-07" {
        description "Add dependent object for between interface and DHCP snooping objects";
        reference " 0.9.1.";
    }

    revision "2021-11-29" {
        description "Leaf port-breakout moved to its own datamodel ipi-port-breakout.";
        reference " 0.9.0.";
    }

    revision "2021-11-16" {
        description "SKU compilation fixes";
        reference " 0.8.1.";
    }

    revision "2021-11-10" {
        description "Add dependentObject when operation is delete to remove module ipi-cross-connect:cross-connect before than interfaces module.";
        reference " 0.8.0.";
    }

    revision "2021-11-08" {
        description "Fix the when tags related to the intra-domain peer configuration";
        reference " 0.7.1.";
    }

    revision "2021-10-20" {
        description "Removed dot1q-ether-type dependency from LAG interface having mlag-id";
        reference " 0.7.0.";
    }

    revision "2021-09-29" {
        description "Updated attribute dot1q-ether-type description, added length and pattern tag";
        reference " 0.6.5.";
    }

    revision "2021-09-28" {
        description "Changed interface name and CLI for ethertype configuration
                       Modified when tags dependent on MCEC configurations
        ";
        reference " 0.6.4.";
    }

    revision "2021-09-20" {
        description "Changed interface name description to add subinterface details";
        reference " 0.6.3.";
    }

    revision "2021-09-10" {
        description "Changed max MTU from 65536 to 65535";
        reference " 0.6.2.";
    }

    revision "2021-09-01" {
        description "Changed name of attribute enabled and switchport-status to shutdown and enable-switchport and data-types from CML_BOOL_T to CML_EMPTY_T.";
        reference " 0.6.1.";
    }

    revision "2021-07-15" {
        description "Added new attribute switchport-protected.";
        reference " 0.6.0.";
    }

    revision "2021-07-07" {
        description "Add a specific condition in the triggers for MTU and Ethertype related to the mlag IDL interface.";
        reference " 0.5.4.";
    }

    revision "2021-06-29" {
        description "Add a trigger to remove mtu from interface when it is a mlag IDL.";
        reference " 0.5.3.";
    }

    revision "2021-06-24" {
        description "Add a trigger to remove dot1q-ether-type from interface when it is a mlag IDL.";
        reference " 0.5.2.";
    }

    revision "2021-06-14" {
        description "Moved attibute dot1q-ether-type from extended interface module to base interface module.";
        reference " 0.5.1.";
    }

    revision "2021-03-16" {
        description "Combined switchport with switchport-status and updated when tags for sub-interface remodelling.";
        reference " 0.5.0.";
    }

    revision "2021-03-01" {
        description "Changed data-types of attribute mtu and ifindex to CML_UINT32_T";
        reference " 0.4.0.";
    }

    revision "2020-12-15" {
        description "Change to have data-types in lower case instead of camel case";
        reference " 0.3.0.";
    }

    revision "2020-11-13" {
        description "For attributes using string data type, changed range to length";
        reference " 0.2.0.";
    }

    revision "2020-07-15" {
        description "Initial Version. Openconfig Yang model : https://github.com/openconfig/public/blob/master/release/models/interfaces/openconfig-interfaces.yang";
        reference " 0.1.0.";
    }

    grouping interface-common-config {
        description
            "Configuration data data nodes common to physical interfaces and
                        subinterfaces";
        leaf description  {
            type  cml-data-types:cml_line_t {
                length "1..128";
            }
            description "Use this attribute to set description for the interface";
        } // END of description definition.

        leaf shutdown  {
            type  empty;
            description "Use this attribute to enable the selected interface.
                        This leaf contains the configured, desired state of the interface.
                        The testing(3) state indicates that no operational packets can be
                        passed.
                        When a managed system initializes, all interfaces start with
                        ifAdminStatus in the down(2) state.
                        As a result of either explicit management action or per configuration
                        information retained by the managed system,
                        ifAdminStatus is then changed to either the up(1) or testing(3)
                        states (or remains in the down(2) state).";
        } // END of shutdown definition.

    } // END of interface-common-config definition.
    grouping interface-phys-config {
        description
            "Configuration data for physical interfaces";
        leaf name  {
            type  string {
                length "1..49";
                pattern "[^?' =,>|]+";
            }
            description "The textual name of the interface. The value of this
                        object should
                        be the name of the interface as assigned by the local device and
                        should be suitable for use in commands entered at the device's
                        `console'. This might be a text name, such as `le0' or a simple
                        port number, such as `1', depending on the interface naming syntax
                        of the device. If several entries in the ifTable together represent
                        a single interface as named by the device, then each will have the
                        same value of name . Note that for an agent which responds to SNMP
                        queries concerning an interface on some other (proxied) device,
                        then the value of name for such an interface is the proxied
                        device's local name for it. If there is no local name, or this
                        object is otherwise not applicable, then this object contains a
                        zero-length string. To configure a subinterface, use the name of
                        the base interface followed by a dot and a number in the range
                        of 1-2000 (eg: xe1.1).";
        } // END of name definition.

        leaf enable-switchport  {
            type  empty;
            description "This attribute is used to set the mode of the Hybrid Switch Router
                        feature to switched only.All interfaces are configured routed by
                        default";
        } // END of enable-switchport definition.

        leaf vrf-name  {
            if-feature feature-list:HAVE_VRF;
            type  leafref {
                path  "/ipi-network-instance:network-instances/ipi-network-instance:network-instance/ipi-vrf:vrf/ipi-vrf:config/ipi-vrf:vrf-name";
            }
            description "This attribute is used to associates an interface with a VRF";
        } // END of vrf-name definition.

        leaf vr-name  {
            if-feature feature-list:HAVE_VR;
            type  string {
                length "1..1965";
                pattern "[^?' =,>|]+";
            }
            description "This attribute is used to associates an interface with a VR";
        } // END of vr-name definition.

        leaf type  {
            type  ipi-if-types:if_iana_if_type_t;
            description "The type of the interface.
                        When an interface entry is created, a server MAY
                        initialize the type leaf with a valid value, e.g., if it
                        is possible to derive the type from the name of the
                        interface.";
        } // END of type definition.

        leaf mtu  {
            type  uint32 {
                 range "64..65535"  {
                    description "64..65535:Feature : HAVE_DNX or HAVE_MARVELL Supported range 64 -
                            65535Not Feature : HAVE_DUNE,HAVE_MARVELL  Supported range 64 -
                            65535Not Feature : HAVE_DNX,HAVE_MARVELL  Supported range 64 - 65535";
                 }
            }
            description "This attribute is used to set mtu value to interface.The size of the
                        largest packet which can be sent/received on the interface, specified
                        in octets.  For interfaces that are used for transmitting network
                        datagrams, this is the size of the largest network datagram that can
                        be sent on the interface.";
        } // END of mtu definition.

        leaf allow-first-frame  {
            // when " ipi-interface:interfaces/interface/config/enable-switchport == '1' ";
            if-feature feature-list:NOT_HAVE_DUNE;
            type  empty;
            description "This Object is used to allow or drop first frame on L2 movement
                        actions";
        } // END of allow-first-frame definition.

        leaf dot1ad-ether-type  {
            if-feature feature-list:HAVE_VLAN_STACK;
            if-feature feature-list:NOT_HAVE_SWFWDR;
            type  string {
                length "6";
                pattern "0[xX][0-9a-fA-F]+";
            }
            description "This attribute is used to configure the ethertype value for the
                        interface in the format 0xhhhh. Currently supported values are 0x8100
                        (default) or 0x88a8 or 0x9100 or 0x9200.";
        } // END of dot1ad-ether-type definition.

        leaf domain-fastflush-config  {
            if-feature feature-list:HAVE_DNX;
            type  empty;
            description "Attribute to change domain fastflush value";
        } // END of domain-fastflush-config definition.

        leaf protected-port  {
            if-feature feature-list:HAVE_DUNE;
            type  ipi-if-types:if_protected_port_type_t;
            default "promiscuous";
            description "Attribute to change port protectedtype value";
        } // END of protected-port definition.

        leaf bridge-domain-forward  {
            // when " ipi-interface:interfaces/interface/config/enable-switchport ";
            if-feature feature-list:HAVE_DUNE;
            type  empty;
            description "Attribute to change domain forward value";
        } // END of bridge-domain-forward definition.

        leaf phy-link-training  {
            type  ipi-if-types:if_port_phy_settings_t;
            description "This attribute is used to enable port link training";
        } // END of phy-link-training definition.

        leaf phy-dfe  {
            type  ipi-if-types:if_port_phy_settings_t;
            description "This attribute is used to enable port decision feedback equalizer(dfe)";
        } // END of phy-dfe definition.

        leaf phy-unreliable-los  {
            type  ipi-if-types:if_port_phy_settings_t;
            description "This attribute is used to enable port unreliable loss of signal(los)";
        } // END of phy-unreliable-los definition.

        leaf phy-media  {
            type  ipi-if-types:if_port_phy_media_settings_t;
            description "This attribute is used to set the media type for the interface";
        } // END of phy-media definition.

        uses interface-common-config;
    } // END of interface-phys-config definition.
    grouping interface-loopback-config {
        description
            "Interface Loopback Config";
        leaf if-loopback  {
            type  ipi-if-types:if_loopback_dir_type_t;
            mandatory true;
            description "This attribute is used to enable port loopback";
        } // END of if-loopback definition.

        leaf if-loopback-level  {
            type  ipi-if-types:if_loopback_type_t;
            mandatory true;
            description "This attribute is used to enable port loopback";
        } // END of if-loopback-level definition.

    } // END of interface-loopback-config definition.
    grouping interface-common-state {
        description
            "Operational state data (in addition to intended configuration) at the
                        global level for this interface";
        leaf ifindex  {
            type  uint32;
            config false;
            description "System assigned number for each interface. A unique value,
                        greater
                        than zero, for each interface.It is recommended that values are
                        assigned contiguously starting from 1.The value for each interface
                        sub-layer must remain constant at least from one re-initialization
                        of the entity's network management system to the next
                        re-initialization.";
        } // END of ifindex definition.

        leaf admin-status  {
            type  ipi-if-types:if_interface_admin_status_t;
            config false;
            description "The desired state of the interface. It reflects the
                        administrative
                        state as set by enabling or disabling the interface.";
        } // END of admin-status definition.

        leaf oper-status  {
            type  ipi-if-types:if_interface_oper_status_t;
            config false;
            description "The current operational state of the interface.  The
                        testing(3) state indicates that no operational packets can
                        be passed.  If admin-status is down(2) then oper-status
                        should be down(2).  If admin-status is changed to up(1)
                        then oper-status should change to up(1) if the interface is
                        ready to transmit and receive network traffic; it should
                        change to dormant(5) if the interface is waiting for
                        external actions (such as a serial line waiting for an
                        incoming connection); it should remain in the down(2) state
                        if and only if there is a fault that prevents it from going
                        to the up(1) state; it should remain in the notPresent(6)
                        state if the interface has missing (typically, hardware)
                        components.";
        } // END of oper-status definition.

        leaf last-change  {
            type  yang:timeticks;
            config false;
            description "The value of sysUpTime at the time the interface entered
                        its current operational state.If the current state was
                        entered prior to the last re-initialization of the local
                        network management subsystem then this object contains a
                        zero value";
        } // END of last-change definition.

        leaf logical  {
            type  boolean;
            config false;
            description "When set to true, the interface is a logical interface
                        which does not have an associated physical port or channel on the
                        system";
        } // END of logical definition.

    } // END of interface-common-state definition.
    grouping interface-counters-state {
        description
            "Operational state representing interface counters and statistics.";
        container counters {
            config false;
            description
                "A collection of interface-related statistics objects";
            leaf in-octets  {
                type  yang:counter64;
                description "The total number of octets received on the interface,
                            including
                            framing characters. Discontinuities in the value of this counter
                            can occur at re-initialization of the management system,
                            and at other times as indicated by the value of 'last-clear'.";
            } // END of in-octets definition.

            leaf in-pkts  {
                type  yang:counter64;
                description "The total number of packets received on the interface,
                            including all unicast, multicast, broadcast and bad packets etc.";
            } // END of in-pkts definition.

            leaf in-unicast-pkts  {
                if-feature feature-list:HAVE_BROADCOM;
                if-feature feature-list:HAVE_HAL;
                if-feature feature-list:NOT_HAVE_SWFWDR;
                type  yang:counter64;
                description "The number of packets, delivered by this sub-layer to a
                            higher (sub-)layer, which were not addressed to a multicast
                            or broadcast address at this sub-layer.
                            Discontinuities in the value of this counter can occur at
                            re-initialization of the management system, and at other
                            times as indicated by the value of
                            ifCounterDiscontinuityTime.";
            } // END of in-unicast-pkts definition.

            leaf in-broadcast-pkts  {
                if-feature feature-list:HAVE_BROADCOM;
                if-feature feature-list:HAVE_HAL;
                if-feature feature-list:NOT_HAVE_SWFWDR;
                type  yang:counter64;
                description "The number of packets, delivered by this sub-layer to a
                            higher (sub-)layer, that were addressed to a broadcast
                            address at this sub-layer.
                            Discontinuities in the value of this counter can occur
                            at re-initialization of the management system, and at
                            other times as indicated by the value of
                            'last-clear'.";
            } // END of in-broadcast-pkts definition.

            leaf in-multicast-pkts  {
                type  yang:counter64;
                description "The number of packets, delivered by this sub-layer to a
                            higher (sub-)layer, that were addressed to a multicast
                            address at this sub-layer.  For a MAC-layer protocol,
                            this includes both Group and Functional addresses.
                            Discontinuities in the value of this counter can occur
                            at re-initialization of the management system, and at
                            other times as indicated by the value of
                            'last-clear'.";
            } // END of in-multicast-pkts definition.

            leaf in-discards  {
                type  yang:counter64;
                description "The number of inbound packets that were chosen to be
                            discarded even though no errors had been detected to
                            prevent their being deliverable to a higher-layer
                            protocol.  One possible reason for discarding such a
                            packet could be to free up buffer space.
                            Discontinuities in the value of this counter can occur
                            at re-initialization of the management system, and at
                            other times as indicated by the value of
                            'last-clear'";
            } // END of in-discards definition.

            leaf in-errors  {
                type  yang:counter64;
                description "For packet-oriented interfaces, the number of inbound
                            packets that contained errors preventing them from being
                            deliverable to a higher-layer protocol.  For character-
                            oriented or fixed-length interfaces, the number of
                            inbound transmission units that contained errors
                            preventing them from being deliverable to a higher-layer
                            protocol. Discontinuities in the value of this counter can occur
                            at re-initialization of the management system, and at
                            other times as indicated by the value of
                            'last-clear'";
            } // END of in-errors definition.

            leaf in-fcs-errors  {
                if-feature feature-list:HAVE_BROADCOM;
                if-feature feature-list:HAVE_HAL;
                if-feature feature-list:NOT_HAVE_SWFWDR;
                type  yang:counter64;
                description "Number of received packets which had errors in the
                            frame check sequence (FCS), i.e., framing errors.
                            Discontinuities in the value of this counter can occur
                            when the device is re-initialization as indicated by the
                            value of 'last-clear'.";
            } // END of in-fcs-errors definition.

            leaf out-octets  {
                type  yang:counter64;
                description "The total number of octets transmitted out of the
                            interface, including framing characters.
                            Discontinuities in the value of this counter can occur
                            at re-initialization of the management system, and at
                            other times as indicated by the value of
                            'last-clear'.";
            } // END of out-octets definition.

            leaf out-pkts  {
                type  yang:counter64;
                description "The total number of packets transmitted out of the
                            interface, including all unicast, multicast, broadcast,
                            and bad packets etc.";
            } // END of out-pkts definition.

            leaf out-unicast-pkts  {
                if-feature feature-list:HAVE_BROADCOM;
                if-feature feature-list:HAVE_HAL;
                if-feature feature-list:NOT_HAVE_SWFWDR;
                type  yang:counter64;
                description "The total number of packets that higher-level protocols
                            requested be transmitted, and which were not addressed to a
                            multicast or broadcast address at this sub-layer, including
                            those that were discarded or not sent.
                            Discontinuities in the value of this counter can occur at
                            re-initialization of the management system, and at other
                            times as indicated by the value of
                            ifCounterDiscontinuityTime.";
            } // END of out-unicast-pkts definition.

            leaf out-broadcast-pkts  {
                if-feature feature-list:HAVE_BROADCOM;
                if-feature feature-list:HAVE_HAL;
                if-feature feature-list:NOT_HAVE_SWFWDR;
                type  yang:counter64;
                description "The total number of packets that higher-level protocols
                            requested be transmitted, and that were addressed to a
                            broadcast address at this sub-layer, including those
                            that were discarded or not sent.
                            Discontinuities in the value of this counter can occur
                            at re-initialization of the management system, and at
                            other times as indicated by the value of
                            'last-clear'";
            } // END of out-broadcast-pkts definition.

            leaf out-multicast-pkts  {
                if-feature feature-list:HAVE_BROADCOM;
                if-feature feature-list:HAVE_HAL;
                if-feature feature-list:NOT_HAVE_SWFWDR;
                type  yang:counter64;
                description "The total number of packets that higher-level protocols
                            requested be transmitted, and which were addressed to a
                            multicast address at this sub-layer, including those that
                            were discarded or not sent.  For a MAC layer protocol, this
                            includes both Group and Functional addresses.
                            Discontinuities in the value of this counter can occur at
                            re-initialization of the management system, and at other
                            times as indicated by the value of
                            ifCounterDiscontinuityTime.";
            } // END of out-multicast-pkts definition.

            leaf out-discards  {
                type  yang:counter64;
                description "The number of outbound packets that were chosen to be
                            discarded even though no errors had been detected to
                            prevent their being transmitted.  One possible reason
                            for discarding such a packet could be to free up buffer
                            space.
                            Discontinuities in the value of this counter can occur
                            at re-initialization of the management system, and at
                            other times as indicated by the value of
                            'last-clear'.";
            } // END of out-discards definition.

            leaf out-errors  {
                type  yang:counter64;
                description "For packet-oriented interfaces, the number of outbound
                            packets that could not be transmitted because of errors.
                            For character-oriented or fixed-length interfaces, the
                            number of outbound transmission units that could not be
                            transmitted because of errors.
                            Discontinuities in the value of this counter can occur
                            at re-initialization of the management system, and at
                            other times as indicated by the value of
                            'last-clear'.";
            } // END of out-errors definition.

            leaf last-clear  {
                type  ipi-if-types:if_last_clear_time_t {
                    length "1..1965";
                }
                description "This Object describes the last counter clear";
            } // END of last-clear definition.

        } // END of counters-container definition.
    } // END of interface-counters-state definition.

    grouping  interfaces-grouping {
    description
        "Top level container for interfaces, including configuration and state
                data";
    container interfaces {
        description
            "Top level container for interfaces, including configuration and state
                    data";

        list interface {
            key "name";
            unique "config/vrf-name";
            description
                "The list of named interfaces on the device.";
            leaf name  {
                type  leafref {
                    path  "../config/name";
                }
                description "The textual name of the interface. The value of this
                            object should
                            be the name of the interface as assigned by the local device and
                            should be suitable for use in commands entered at the device's
                            `console'. This might be a text name, such as `le0' or a simple
                            port number, such as `1', depending on the interface naming syntax
                            of the device. If several entries in the ifTable together represent
                            a single interface as named by the device, then each will have the
                            same value of name. Note that for an agent which responds to SNMP
                            queries concerning an interface on some other (proxied) device,
                            then the value of name for such an interface is the proxied
                            device's local name for it. If there is no local name, or this
                            object is otherwise not applicable, then this object contains a
                            zero-length string.";
            } // END of name definition.

            container config {
                description
                    "Configurable items at the global, physical interface level";
                uses interface-phys-config;
            } // END of config-container definition.
            container state {
                config false;
                description
                    "Operational state data at the global interface level";
                uses interface-phys-config;
                uses interface-common-state;
                uses interface-counters-state;
            } // END of state-container definition.
            container interface-loopback {
                description
                    "Configurable items at the global, physical interface level";
                container config {
                    presence "if-loopback";
                    description
                        "Operational state data at the global interface level";
                    uses interface-loopback-config;
                } // END of config-container definition.
                container state {
                    config false;
                    description
                        "Operational state data at the global interface level";
                    uses interface-loopback-config;
                } // END of state-container definition.
            } // END of interface-loopback-container definition.
        } // End of interface-list
    } // END of interfaces-container definition.
    } // END of interfaces-grouping definition.

    uses interfaces-grouping;

    rpc clear-interface-counters {
        description "Use clear-interface-counters to clear all interface counters, to clear
                    counters for a specific interface pass the interface name . E.g
                    clear-interface-counters name=eth1";
        input  {
            leaf name  {
                type string;
                mandatory true;
                description "Name of the interface to clear counters for. Specify NULL to clear
                            counters for all interfaces";
            }
        }
    }

    notification interface-link-state-change-notification {

        description "A linkDown specifies that one of the communication links is about to enter the down state from some other state (but not from the notPresent state).  This other state is indicated by the included value of ifOperStatus. A linkUp trap signifies that one of communication links left the down state and transitioned into some other state (but not into the notPresent state).  This other state is indicated by the included value of ifOperStatus. Severity level is CRITICAL for link state Down and MINOR for link state Up..";

        leaf severity {
            type cml-data-types:cml_notif_severity_t;
            description "Notification severity level";
        }

        leaf eventClass {
            type cml-data-types:cml_notif_class_t;
            description "Notification event class (value: STATE)";
        }

        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf oper-status {
            type ipi-if-types:if_interface_oper_status_t;
        description
            "The current operational state of the interface.  The
                    testing(3) state indicates that no operational packets can
                    be passed.  If admin-status is down(2) then oper-status
                    should be down(2).  If admin-status is changed to up(1)
                    then oper-status should change to up(1) if the interface is
                    ready to transmit and receive network traffic; it should
                    change to dormant(5) if the interface is waiting for
                    external actions (such as a serial line waiting for an
                    incoming connection); it should remain in the down(2) state
                    if and only if there is a fault that prevents it from going
                    to the up(1) state; it should remain in the notPresent(6)
                    state if the interface has missing (typically, hardware)
                    components.";
        }
    }

}
