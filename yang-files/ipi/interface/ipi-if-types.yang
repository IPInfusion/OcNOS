/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-if-types.yang
*
*/

module ipi-if-types {

    yang-version 1.1;

    namespace   "http://www.ipinfusion.com/yang/ocnos/ipi-if-types";

    prefix "ipi-if-types";

    import ietf-inet-types {
        prefix inet;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-if-types";


    revision "2026-03-10" {
        description "Added the datatype for media-type attribute";
        reference " 0.16.0.";
    }

    revision "2025-09-24" {
        description "Changed the datatype for ether-type attribute";
        reference " 0.15.3.";
    }

    revision "2025-08-22" {
        description "Changed error disable type from bits to enum";
        reference " 0.15.2.";
    }

    revision "2025-06-27" {
        description "New cmd added - l2protocol all learn-disable";
        reference " 0.15.1.";
    }

    revision "2025-06-25" {
        description "Updated datatype 'IF_ERRDISABLE_STATE_T 'values";
        reference " 0.15.0.";
    }

    revision "2025-06-03" {
        description "Added port dfe and unreliable-los support";
        reference " 0.14.14.";
    }

    revision "2025-03-17" {
        description "Revert of EFM flag for l2pt efm CLI";
        reference " 0.14.13.";
    }

    revision "2024-11-18" {
        description "Added new datatype IF_ERRDIS_STATUS";
        reference " 0.14.11.";
    }

    revision "2024-10-29" {
        description "Add subtypes for global mtu configuration";
        reference " 0.14.10.";
    }

    revision "2024-10-17" {
        description "Added missing interface types for IF_HW_TYPE_T";
        reference " 0.14.9.";
    }

    revision "2024-10-03" {
        description "Added support to 400G and 200G in interface negotiated-port-speed";
        reference " 0.14.8.";
    }

    revision "2024-09-19" {
        description "Modified cli helpstring for mac ageing mode";
        reference " 0.14.7.";
    }

    revision "2024-09-03" {
        description "CL108 FEC config support";
        reference " 0.14.8.";
    }

    revision "2024-08-21" {
        description "Added CML_MAC_AGEING_T ";
        reference " 0.14.7.";
    }

    revision "2024-08-19" {
        description "Added global mtu configuration support";
        reference " 0.14.6.";
    }

    revision "2024-08-12" {
        description "Added global l2protocol configuration";
        reference " 0.14.5.";
    }

    revision "2024-07-26" {
        description "Make previous revision tag consistent";
        reference " 0.14.4.";
    }

    revision "2024-07-25" {
        description "Added UCMP CLI option";
        reference " 0.14.3.";
    }

    revision "2024-06-18" {
        description "Added BVI element in hardware type datatype";
        reference " 0.14.2.";
    }

    revision "2024-03-27" {
        description "Added limited autonegotiation support";
        reference " 0.14.1.";
    }

    revision "2024-01-30" {
        description "Conditional enabling of EFM";
        reference " 0.14.12.";
    }

    revision "2024-01-24" {
        description "Added data-types for Flexible Algorithm features";
        reference " 0.14.0.";
    }

    revision "2024-01-06" {
        description "Added storm-control errdisable";
        reference " 0.13.0.";
    }

    revision "2023-12-20" {
        description "Added a new datatype IF_RAON_AODU_STATE";
        reference " 0.12.7.";
    }

    revision "2023-10-10" {
        description "Change storm-control maximum level to 99%";
        reference " 0.12.6.";
    }

    revision "2023-08-23" {
        description "Added datatype IF_ACLIF_TYPE_T";
        reference " 0.12.5.";
    }

    revision "2023-08-18" {
        description "Added pattern tag for the datatype IF_SUBIF_OUTER_TPID_T";
        reference " 0.12.4.";
    }

    revision "2023-05-26" {
        description "Added element types for FEC type configuration support";
        reference " 0.12.3.";
    }

    revision "2023-04-28" {
        description "Removed HARDWARE_PORT_MODE data type";
        reference " 0.12.2.";
    }

    revision "2023-03-03" {
        description "Added datatype for split-horizon";
        reference " 0.12.1.";
    }

    revision "2022-11-14" {
        description "Added support for Storm-control by Frame per second";
        reference " 0.12.0.";
    }

    revision "2022-09-27" {
        description "Added loopback-detection in err disable cause";
        reference " 0.11.0.";
    }

    revision "2022-06-01" {
        description "Updated the yang file with feature";
        reference " 0.10.0.";
    }

    revision "2021-11-10" {
        description "Moved IF_XC_OPER_STATUS_T datatype to new cross-connect model on network-instance module";
        reference " 0.9.0.";
    }

    revision "2021-09-15" {
        description "Added IF_XC_OPER_STATUS_T to show cross connect operational status";
        reference " 0.8.0.";
    }

    revision "2021-08-26" {
        description "Added IF_SNIFF_ACTION_T for sniff command";
        reference " 0.7.0.";
    }

    revision "2021-08-24" {
        description "Updated IF_HW_TYPE_T with additional types for IRB and PON interfaces";
        reference " 0.6.0.";
    }

    revision "2021-03-16" {
        description "Modified IF_SUBIF_ENCAP_T, IF_HW_TYPE_T, IF_SUBIF_L2_VLAN_ACTIONTYPE_T and IF_SUBIF_REWRITE_POP_TYPE_T for subinterface remodelling";
        reference " 0.5.0.";
    }

    revision "2021-01-27" {
        description "Removed datatype IF_MONITOR_TYPE_T";
        reference " 0.4.0.";
    }

    revision "2020-12-15" {
        description "Change to have data-types in lower case instead of camel case";
        reference " 0.3.0.";
    }

    revision "2020-11-13" {
        description "Updated datatype as part of extended interface module, removed speed values for auto-neg, moved datatype IF_LACP_PSC_T to LACP data model";
        reference " 0.2.0.";
    }

    revision "2020-07-15" {
        description "Initial Version";
        reference " 0.1.0.";
    }



    typedef  if_interface_oper_status_t {
        type enumeration {
            enum up {
                value 1;
                description "ready to pass packets";
            }
            enum down {
                value 2;
                description "down state";
            }
            enum testing {
                value 3;
                description "in some test mode";
            }
            enum unknown {
                value 4;
                description "status can not be determined for some reason";
            }
            enum dormant {
                value 5;
                description "not in a condition to pass packets but is instead in a pending state waiting for some external event. ";
            }
            enum notPresent {
                value 6;
                description "some component is missing";
            }
            enum lowerLayerDown {
                value 7;
                description "down due to state of lower-layer interface(s)";
            }
        }
        description "datatype for operational state of the interface";
    }

    typedef  if_iface_prop_t {
        type bits {
            bit interface_active {
                position 0;
                description "active interface";
            }
            bit dhcp_addr {
                position 15;
                description "IPV4 DHCP client is enabled";
            }
            bit dhcp6_addr {
                position 16;
                description "IPV6 DHCP IA-NA client is enabled";
            }
            bit Breakout_control_port {
                position 20;
                description "Breakout Control Port (Active)";
            }
            bit Bundle_control_port {
                position 21;
                description "Bundle Control Port (Active)";
            }
            bit Breakout_enable {
                position 22;
                description "port breakout enable";
            }
            bit Bundle_enable {
                position 23;
                description "port bundle enable";
            }
            bit Sbuport_inactive {
                position 24;
                description "Non Control Port (InActive)";
            }
        }
        description "datatype for interface mapping properties";
    }

    typedef  if_duplex_t {
        type enumeration {
            enum half {
                value 0;
                description "set half duplex";
            }
            enum full {
                value 1;
                description "set full duplex";
            }
        }
        description "datatype for interface duplex-mode";
    }

    typedef  if_interface_admin_status_t {
        type enumeration {
            enum up {
                value 1;
                description "ready to pass packets";
            }
            enum down {
                value 2;
                description "down state";
            }
            enum testing {
                value 3;
                description "in some test mode";
            }
        }
        description "datatype for interface admin status";
    }

    typedef  if_iana_if_type_t {
        type enumeration {
            enum other {
                value 1;
                description "other";
            }
            enum regular1822 {
                value 2;
                description "regular1822";
            }
            enum hdh1822 {
                value 3;
                description "hdh1822";
            }
            enum ddnX25 {
                value 4;
                description "ddnX25";
            }
            enum rfc877x25 {
                value 5;
                description "rfc877x25 ";
            }
            enum ethernetCsmacd {
                value 6;
                description "ethernetCsmacd";
            }
        }
        description "datatype for interface type";
    }

    typedef  if_global_mtu_if_type_t {
        type enumeration {
            enum eth-switchport {
                value 1;
                description "Physical L2 interface";
            }
            enum eth-routed {
                value 2;
                description "Physical L3 interface";
            }
            enum l2-subif {
                value 3;
                description "L2 subinterface";
            }
            enum l3-subif {
                value 4;
                description "L3 subinterface";
            }
            enum svi {
                value 7;
                description "VLAN interface";
            }
            enum lag {
                value 9;
                description "Port-channel and static-aggregate";
            }
            enum pbb {
                value 11;
                if-feature feature-list:HAVE_PBB_TE;
                description "PBB logical Port";
            }
            enum mlag {
                value 16;
                description "Mlag Aggregate interface";
            }
            enum bvi {
                value 27;
                if-feature feature-list:HAVE_SUBINTERFACE;
                description "BVI Interface";
            }
            enum irb {
                value 110;
                description "IRB logical Interface";
            }
            enum nni {
                value 113;
                if-feature feature-list:HAVE_POND;
                description "NNI Interface";
            }
        }
        description "datatype to describe Interface Type for Global MTU configuration";
    }

    typedef  if_hw_type_t {
        type enumeration {
            enum UNK {
                value 0;
                description "UNK-Interface type unknown";
            }
            enum LB {
                value 1;
                description "LB-loopback";
            }
            enum ETH {
                value 2;
                description "ETH-Ethernet";
            }
            enum HDLC {
                value 3;
                description "HDLC";
            }
            enum PPP {
                value 4;
                description "PPP";
            }
            enum ATM {
                value 5;
                description "ATM";
            }
            enum FR {
                value 6;
                description "FR-Frame Relay";
            }
            enum SVI {
                value 7;
                description "VLAN";
            }
            enum AGG {
                value 9;
                description "AGG-aggregate";
            }
            enum PBB {
                value 11;
                description "PBB- PBB logical Port";
            }
            enum VP {
                value 12;
                description "VPORT- Virtual port";
            }
            enum CVP {
                value 13;
                description "CVP-Channelised Virtual port";
            }
            enum METH {
                value 14;
                description "Management Ethernet";
            }
            enum MLAG {
                value 16;
                description "MLAG-Mlag Aggregate";
            }
            enum SONET {
                value 17;
                description "SONET";
            }
            enum SDH {
                value 18;
                description "SDH";
            }
            enum OTN {
                value 19;
                description "SONET";
            }
            enum MODEM {
                value 20;
                description "Modem Interface";
            }
            enum LBG {
                value 21;
                description "LBG Interface";
            }
            enum FLEXE-CLIENT {
                value 24;
                description "Flexe Client Interface";
            }
            enum FLEXE-ETH-L1 {
                value 25;
                description "Flexe Eth L1 Interface";
            }
            enum FLEXE-PORT {
                value 26;
                description "Flexe Port Interface";
            }
            enum BVI {
                value 27;
                description "BVI Interface";
            }
            enum TUN {
                value 101;
                description "TUN-Tunnel";
            }
            enum TUNGRE {
                value 102;
                description "TUNGREIP-Tunnel";
            }
            enum TUN6 {
                value 103;
                description "TUNIPV6-Tunnel";
            }
            enum MPLS {
                value 106;
                description "MPLS";
            }
            enum VXLAN {
                value 107;
                description "VXLAN";
            }
            enum NVGRE {
                value 108;
                description "NVGRE";
            }
            enum NVOACCESS {
                value 109;
                description "NVO Access Port";
            }
            enum IRB {
                value 110;
                description "IRB logical Interface";
            }
            enum SUBINTERFACE {
                value 111;
                description "Subinterface";
            }
            enum PON {
                value 112;
                description "PON Interface";
            }
            enum NNI {
                value 113;
                description "NNI Interface";
            }
            enum PMSI {
                value 114;
                description "MVPN PMSI Interface";
            }
            enum IPSEC {
                value 115;
                description "IPSEC Interface";
            }
            enum IRBTUN {
                value 116;
                description "IRB TUN-Tunnel Interface";
            }
        }
        description "datatype to describes HardWare Type";
    }

    typedef  if_interface_speed_t {
        type enumeration {
            enum 10m {
                value 0;
                description "10 mega bits";
            }
            enum 100m {
                value 1;
                description "100 mega bits";
            }
            enum 1g {
                value 2;
                description "1 giga bits";
            }
            enum 2.5g {
                value 3;
                description "2.5 giga bits";
            }
            enum 10g {
                value 4;
                description "10 giga bits";
            }
            enum 20g {
                value 5;
                description "20 giga bits";
            }
            enum 25g {
                value 6;
                description "25 giga bits";
            }
            enum 40g {
                value 7;
                description "40 giga bits";
            }
            enum 50g {
                value 8;
                description "50 giga bits";
            }
            enum 100g {
                value 9;
                description "100 giga bits";
            }
            enum 200g {
                value 10;
                description "200 giga bits";
            }
            enum 400g {
                value 11;
                description "400 giga bits";
            }
            enum auto {
                value 12;
                description "Auto Negotiation";
            }
            enum auto-10m {
                value 13;
                description "Auto Negotiation,10 mega bits only";
            }
            enum auto-100m {
                value 14;
                description "Auto Negotiation,100 mega bits only";
            }
            enum auto-1g {
                value 15;
                description "Auto Negotiation,1 giga bits only";
            }
        }
        description "datatype for port-speed of interface";
    }

    typedef  if_intf_fec_t {
        type enumeration {
            enum off {
                value 0;
                description "disable fec";
            }
            enum on {
                value 1;
                description "enable fec";
            }
            enum auto {
                value 2;
                description "enable fec auto";
            }
            enum on-cl74 {
                value 4;
                description "enable fec,type cl74";
            }
            enum on-cl91 {
                value 5;
                description "enable fec,type cl91";
            }
            enum on-cl108 {
                value 6;
                description "enable fec,type cl108";
            }
        }
        description "datatype for interface fec";
    }

    typedef  if_mautype_t {
        type enumeration {
            enum dot3MauType10BaseTHD {
                value 10;
                description "UTP MAU half duplex mode";
            }
            enum dot3MauType10BaseTFD {
                value 11;
                description "UTP MAU full duplex mode";
            }
            enum dot3MauType100BaseTXHD {
                value 15;
                description "2 pair category 5 UTP half duplex mode";
            }
            enum dot3MauType100BaseTXFD {
                value 16;
                description "2 pair category 5 UTP full duplex mode";
            }
            enum dot3MauType1000BaseXHD {
                value 21;
                description "PCS/PMA unknown PMD half duplex mode";
            }
            enum dot3MauType1000BaseXFD {
                value 22;
                description "PCS/PMA unknown PMD full duplex mode";
            }
            enum dot3MauType10GigBaseCX4 {
                value 41;
                description "X copper over 8 pair 100-Ohm balanced cable";
            }
            enum dot3MauType10GbaseKX4 {
                value 57;
                description "4 lane X backplane full duplex mode only";
            }
            enum dot3MauType10GbaseKR {
                value 58;
                description "R backplane full duplex mode only";
            }
            enum dot3MauType40GbaseCR4 {
                value 71;
                description "40GBASE-R PCS/PMA over 4 lane shielded copper balanced cable";
            }
        }
        description "datatype for mau type of interface";
    }

    typedef  if_interface_type_t {
        type enumeration {
            enum Router {
                value 0;
                description "L3 interface";
            }
            enum Switch {
                value 1;
                description "L2 interface";
            }
            enum TDM {
                value 2;
                description "TDM interface";
            }
        }
        description "datatype for interface type";
    }

    typedef  if_trust_state_t {
        type enumeration {
            enum none {
                value 0;
                description "mls qos trust none";
            }
            enum cos {
                value 1;
                description "mls qos trust cos";
            }
            enum dscp {
                value 2;
                description "mls qos trust dscp";
            }
            enum ip-precedence {
                value 3;
                description "mls qos trust ip-precedence";
            }
            enum dscp-cos {
                value 6;
                description "mls qos trust,cos and dscp both";
            }
        }
        description "datatype for trust interface state";
    }

    typedef  if_tfo_link_type_t {
        type enumeration {
            enum default {
                value 0;
                description "default link type";
            }
            enum uplink {
                value 1;
                description "link-type uplink";
            }
            enum downlink {
                value 2;
                description "link-type downlink";
            }
        }
        description "datatype for interface link type";
    }

    typedef  if_l2cp_t {
        type enumeration {
            enum stp {
                value 0;
                description "Spanning Tree Protocols";
            }
            enum gmrp {
                value 3;
                if-feature feature-list:HAVE_GMRP;
                description "GARP Multicast Registration Protocol";
            }
            enum gvrp {
                value 4;
                if-feature feature-list:HAVE_GVRP;
                description "GARP VLAN Registration Protocol";
            }
            enum lacp {
                value 7;
                description "Link Aggregation (LACP)";
            }
            enum dot1x {
                value 8;
                description "Port Authentication (802.1 X)";
            }
            enum lldp {
                value 9;
                description "Link layer discovery protocol";
            }
            enum efm {
                value 13;
                description "Ethernet first mile (Link OAM)";
            }
            enum elmi {
                value 14;
                description "Ethernet local management interface";
            }
            enum synce {
                value 16;
                if-feature feature-list:HAVE_SYNCED;
                description "Synchronous Ethernet";
            }
        }
        description "datatype for L2 Control Protocol";
    }

    typedef  if_l2cp_stats_process_t {
        type enumeration {
            enum peer {
                value 0;
                description "peer counters";
            }
            enum tunnel {
                value 1;
                description "tunnel counters";
            }
            enum discard {
                value 2;
                description "discard counters";
            }
            enum tunnel-discard {
                value 3;
                description "tunnel-discard counters";
            }
        }
        description "datatype for l2cp stats";
    }

    typedef  if_l2cp_process_t {
        type enumeration {
            enum peer {
                value 1;
                description "peer the protocol data unit";
            }
            enum tunnel {
                value 2;
                description "tunnel the protocol data unit";
            }
            enum discard {
                value 3;
                description "discard the protocol data unit";
            }
        }
        description "datatype for l2cp process";
    }

    typedef  if_error_set_type_t {
        type enumeration {
            enum packet-loss {
                value 0;
                description "Error-Type - Packet-loss";
            }
            enum stray-packets {
                value 1;
                description "Error-Type - Stray-packets";
            }
            enum malformed-packets {
                value 2;
                description "Error-Type - Malformed-packets";
            }
            enum excessive-packet-loss-rate {
                value 3;
                description "Error-Type - Excessive packet loss rate";
            }
            enum buffer-overrun {
                value 4;
                description "Error-Type - Buffer-overrun";
            }
            enum remote-packet-loss {
                value 5;
                description "Error-Type - Remote packet loss";
            }
        }
        description "datatype for interface error-set";
    }

    typedef  if_error_clear_type_t {
        type enumeration {
            enum packet-loss {
                value 6;
                description "Error-Type - Packet-loss";
            }
            enum stray-packets {
                value 7;
                description "Error-Type - Stray-packets";
            }
            enum malformed-packets {
                value 8;
                description "Error-Type - Malformed-packets";
            }
            enum excessive-packet-loss-rate {
                value 9;
                description "Error-Type - Excessive packet loss rate";
            }
            enum buffer-overrun {
                value 10;
                description "Error-Type - Buffer-overrun";
            }
            enum remote-packet-loss {
                value 11;
                description "Error-Type - Remote packet loss";
            }
        }
        description "datatype for interface error-clear";
    }

    typedef  if_rate_limit_level_t {
        type string;
        description "datatype for interface rate-limit-level";
    }

    typedef  if_rate_limit_t {
        type union {
            type uint32 {
                range "0..100000000";

            }
            type if_rate_limit_level_t {

            }
        }
        description "datatype for interface rate-limit";
    }

    typedef  if_rate_limit_type {
        type enumeration {
            enum level {
                value 0;
                description "Threshold level as a percentage";
            }
            enum kbps {
                value 1;
                description "Specifies the units of kilobits per second";
            }
            enum mbps {
                value 2;
                description "Specifies the units of megabits per second";
            }
            enum gbps {
                value 3;
                description "Specifies the units of gigabits per second";
            }
            enum fps {
                value 4;
                if-feature feature-list:HAVE_BROADCOM;
                if-feature feature-list:NOT_HAVE_DUNE;
                description "Specifies the units of frames per second";
            }
        }
        description "datatype for interface rate-limit-type";
    }

    typedef  if_subif_encap_type_t {
        type enumeration {
            enum dot1q {
                value 33024;
                description "IEEE 802.1Q VLAN-tagged packets";
            }
            enum dot1ad {
                value 34984;
                description "IEEE 802.1ad VLAN-tagged packets";
            }
        }
        description "datatype for sub-interface encap type";
    }

    typedef  if_subif_l2_vlan_actiontype_t {
        type enumeration {
            enum pop {
                value 1;
                description "Pop the outer vid";
            }
            enum push {
                value 2;
                description "Push the outer vid";
            }
            enum translate {
                value 3;
                description "Translate the outer vid";
            }
        }
        description "datatype for sub-interface l2 vlan action type";
    }

    typedef  if_subif_rewrite_pop_type_t {
        type enumeration {
            enum 1tag {
                value 1;
                description "Pop 1 tag";
            }
            enum 2tag {
                value 2;
                description "Pop 2 tags";
            }
        }
        description "datatype for sub-interface l2 rewrite pop options";
    }

    typedef  if_subif_l2_rewrite_actiontype_t {
        type enumeration {
            enum 1-to-1 {
                value 1;
                description "Swap 1-to-1 the outer vid/tpid";
            }
            enum 1-to-2 {
                value 2;
                description "Swap 1-to-2 the inner and outer vid/tpid";
            }
            enum 2-to-2 {
                value 3;
                description "Swap 2-to-2 the 2 vid/tpid";
            }
            enum 2-to-1 {
                value 4;
                description "Swap 2-to-1 the outer vid/tpid";
            }
        }
        description "datatype for sub-interface l2 vlan rewrite/swap action type";
    }

    typedef  if_subif_rewrite_tpid_type_t {
        type enumeration {
            enum dot1q {
                value 1;
                description "IEEE 802.1Q VLAN-tagged packets";
            }
            enum dot1ad {
                value 2;
                description "IEEE 802.1ad VLAN-tagged packets";
            }
        }
        description "datatype for sub-interface encap type";
    }

    typedef  if_subif_inner_dot1q_t {
        type enumeration {
            enum dot1q {
                value 1;
                description "IEEE 802.1Q VLAN-tagged packets";
            }
        }
        description "datatype for sub-interface encap type";
    }

    typedef  if_subif_outer_tpid_t {
        type string {
            pattern "0x[0-9a-fA-F]+";
        }
        description "datatype for sub-interface encap type";
    }

    typedef  if_subif_inner_tpid_t {
        type string;
        description "datatype for sub-interface encap type";
    }

    typedef  cml_outer_tpid_type_t {
        type union {
            type if_subif_rewrite_tpid_type_t {

            }
            type if_subif_outer_tpid_t {

            }
        }
        description "datatype for sub-interface l2 vlan rewrite/swap tpid type";
    }

    typedef  cml_inner_tpid_type_t {
        type union {
            type if_subif_inner_dot1q_t {

            }
            type if_subif_inner_tpid_t {

            }
        }
        description "datatype for sub-interface l2 vlan rewrite/swap tpid type";
    }

    typedef  if_subif_sevice_queue_t {
        type enumeration {
            enum physical {
                value 1;
                description "physical port queue";
            }
            enum flow-id {
                value 2;
                description "Flow id";
            }
        }
        description "datatype for service queue";
    }

    typedef  if_flowctrl_t {
        type enumeration {
            enum off {
                value 0;
                description "Turn off flowcontrol";
            }
            enum on {
                value 1;
                description "Turn on flowcontrol";
            }
        }
        description "datatype for flowcontrol";
    }

    typedef  if_raw_string_t {
        type string;
        description "datatype for string";
    }

    typedef  if_err_reason_t {
        type bits {
            bit lag-mismatch {
                position 0;
                description "Enable or Disable Lag-Mismatch";
            }
            bit link-flap {
                position 2;
                description "Enable or Disable Link-Flap";
            }
            bit mac-move-limit {
                position 3;
                description "Enable or Disable Mac-Move-Limit";
            }
            bit loopback-detection {
                position 4;
                if-feature feature-list:HAVE_LBD;
                description "Enable or Disable loopback-detection";
            }
            bit storm-control {
                position 5;
                if-feature feature-list:HAVE_RATE_LIMIT;
                description "Enable or Disable Storm-Control";
            }
        }
        description "datatype for nsm error reason";
    }

    typedef  if_tunnel_mode_t {
        type enumeration {
            enum vxlan {
                value 6;
                description "Vxlan encapsulation";
            }
        }
        description "datatype for tunnel mode";
    }

    typedef  if_tunnel_key_t {
        type union {
            type uint32 {
                range "0..4294967295";

            }
            type inet:ipv4-address {

            }
        }
        description "datatype for tunnel key";
    }

    typedef  if_port_group_speed_t {
        type enumeration {
            enum 1g {
                value 1;
                description "port group speed 1g";
            }
            enum 10g {
                value 2;
                description "port group speed 10g";
            }
            enum 25g {
                value 3;
                description "port group speed 25g";
            }
            enum 40g {
                value 4;
                description "port group speed 40g";
            }
            enum 50g {
                value 5;
                description "port group speed 50g";
            }
            enum 100g {
                value 6;
                description "port group speed 100g";
            }
        }
        description "datatype for interface port group speed";
    }

    typedef  if_errdisable_state_t {
        type enumeration {
            enum lag-mismatch {
                value 1;
                description "Lag-Mismatch";
            }
            enum stp-bpdu-guard {
                value 2;
                description "Stp-Bpdu-Guard";
            }
            enum link-flap {
                value 4;
                description "Link-Flap";
            }
            enum mac-move-limit {
                value 8;
                description "Mac-Move-Limit";
            }
            enum loopback-detect {
                value 16;
                description "Loopback-Detect";
            }
            enum storm-control {
                value 32;
                if-feature feature-list:HAVE_RATE_LIMIT;
                description "Storm-Control";
            }
            enum not-applicable {
                value 64;
                description "Not Applicable";
            }
        }
        description "datatype for error-disable state";
    }

    typedef  if_last_clear_time_t {
        type string;
        description "datatype for interface last clear time";
    }

    typedef  if_debounce_running_state {
        type enumeration {
            enum idle {
                value 0;
                description "Debounce timer is idle";
            }
            enum running {
                value 1;
                description "Debounce timer is running";
            }
            enum enable {
                value 2;
                description "Debounce time is configured";
            }
            enum disable {
                value 3;
                description "Debounce time is not configured";
            }
        }
        description "datatype for debounce running and configuration state";
    }

    typedef  if_loopback_dir_type_t {
        type enumeration {
            enum tx {
                value 0;
                description "tx";
            }
            enum rx {
                value 1;
                description "rx";
            }
        }
        description "datatype for interface loopback direction";
    }

    typedef  if_loopback_type_t {
        type enumeration {
            enum mac {
                value 0;
                description "mac";
            }
            enum phy {
                value 1;
                description "phy";
            }
        }
        description "datatype for interface loopback level";
    }

    typedef  if_protected_port_type_t {
        type enumeration {
            enum community {
                value 0;
                description "communicates only with community and promiscuous ports";
            }
            enum isolated {
                value 1;
                description "communicates only with promiscuous ports";
            }
            enum promiscuous {
                value 2;
                description "communicates with all ports";
            }
        }
        description "datatype for interface protected type";
    }

    typedef  if_sniff_action_t {
        type enumeration {
            enum rx {
                value 0;
                description "ingress packets only";
            }
            enum tx {
                value 1;
                description "egress packets only";
            }
            enum both {
                value 2;
                description "both ingress egress packets";
            }
        }
        description "type definition for IF_SNIFF_ACTION_T";
    }

    typedef  if_split_horizon_t {
        type enumeration {
            enum network {
                value 1;
                description "Split-horizon group name network";
            }
            enum access1 {
                value 2;
                description "Split-horizon group name access1";
            }
            enum access2 {
                value 3;
                description "Split-horizon group name access2";
            }
        }
        description "type definition for IF_SPLIT_HORIZON_T";
    }

    typedef  if_aclif_type_t {
        type enumeration {
            enum failover {
                value 1;
                description "Configure failover";
            }
            enum no-failover {
                value 2;
                description "Configiure no failover";
            }
        }
        description "type definition for IF_ACLIF_TYPE_T";
    }

    typedef  if_raon_aodu_state {
        type enumeration {
            enum enable {
                value 1;
                description "Enable";
            }
        }
        description "type definition for IF_RAON_AODU_STATE";
    }

    typedef  if_l2_proto_type {
        type enumeration {
            enum all {
                value 1;
                description "Configure all";
            }
        }
        description "type definition for IF_L2_PROTO_TYPE";
    }

    typedef  if_ucmp_state {
        type enumeration {
            enum enable {
                value 1;
                description "Enable";
            }
        }
        description "type definition for IF_UCMP_STATE";
    }

    typedef  if_errdis_status_t {
        type enumeration {
            enum Enabled {
                value 1;
                description "Enable";
            }
            enum Disabled {
                value 2;
                description "Disabled";
            }
        }
        description "type definition for IF_ERRDIS_STATUS_T";
    }

    typedef  cml_mac_ageing_t {
        type enumeration {
            enum src {
                value 1;
                description "enable source mac hit based ageing";
            }
            enum dst-src {
                value 2;
                description "enable destination-or-source mac hit based ageing";
            }
        }
        description "type definition for CML_MAC_AGEING_T";
    }

    typedef  if_port_phy_settings_t {
        type enumeration {
            enum disable {
                value 1;
                description "disable";
            }
            enum enable {
                value 2;
                description "enable";
            }
        }
        description "type definition for IF_PORT_PHY_SETTINGS_T";
    }

    typedef  if_port_phy_media_settings_t {
        type enumeration {
            enum copper {
                value 1;
                description "copper";
            }
            enum backplane {
                value 2;
                description "backplane";
            }
            enum optics {
                value 3;
                description "optics";
            }
        }
        description "type definition for IF_PORT_PHY_MEDIA_SETTINGS_T";
    }

}
