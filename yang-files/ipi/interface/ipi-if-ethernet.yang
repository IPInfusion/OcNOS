/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-if-ethernet.yang
*
*/

module ipi-if-ethernet {

    yang-version 1.1;

    namespace   "http://www.ipinfusion.com/yang/ocnos/ipi-if-ethernet";

    prefix "ipi-if-ethernet";

    import cml-data-types {
        prefix cml-data-types;
        revision-date 2026-05-15;
    }

    import ipi-if-types {
        prefix ipi-if-types;
        revision-date 2026-03-10;
    }

    import ietf-yang-types {
        prefix yang;
        revision-date 2013-07-15;
    }

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Model for managing Ethernet interfaces -- augments the OpenConfig
                model for interface configuration and state.";


    revision "2026-03-10" {
        description "Added the datatype for media-type attribute";
        reference " 0.15.0.";
    }

    revision "2025-09-24" {
        description "Changed the datatype for ether-type attribute";
        reference " 0.14.4.";
    }

    revision "2025-09-04" {
        description "Removed EVPN_IRB_IF_MODE while configuring IRB interface";
        reference " 0.14.3.";
    }

    revision "2025-08-22" {
        description "Changed error disable type from bits to enum";
        reference " 0.14.2.";
    }

    revision "2025-06-27" {
        description "New cmd added - l2protocol all learn-disable";
        reference " 0.14.1.";
    }

    revision "2025-06-25" {
        description "Updated datatype 'IF_ERRDISABLE_STATE_T 'values";
        reference " 0.14.0.";
    }

    revision "2025-06-03" {
        description "Added port dfe and unreliable-los support";
        reference " 0.13.2.";
    }

    revision "2025-03-17" {
        description "Revert of EFM flag for l2pt efm CLI";
        reference " 0.13.1.";
    }

    revision "2025-02-19" {
        description "Added streaming telemetry support";
        reference " 0.13.0.";
    }

    revision "2024-11-18" {
        description "Added new datatype IF_ERRDIS_STATUS";
        reference " 0.12.13.";
    }

    revision "2024-10-29" {
        description "Add subtypes for global mtu configuration";
        reference " 0.12.12.";
    }

    revision "2024-10-22" {
        description "Additional change required for support of 200g and 400g speed";
        reference " 0.12.10.";
    }

    revision "2024-10-17" {
        description "Added missing interface types for IF_HW_TYPE_T";
        reference " 0.12.11.";
    }

    revision "2024-10-03" {
        description "Added support to 400G and 200G in interface negotiated-port-speed";
        reference " 0.12.9.";
    }

    revision "2024-09-19" {
        description "Modified cli helpstring for mac ageing mode";
        reference " 0.12.8.";
    }

    revision "2024-09-03" {
        description "CL108 FEC config support";
        reference " 0.12.9.";
    }

    revision "2024-08-21" {
        description "Added CML_MAC_AGEING_T ";
        reference " 0.12.8.";
    }

    revision "2024-08-19" {
        description "Added global mtu configuration support";
        reference " 0.12.7.";
    }

    revision "2024-08-12" {
        description "Added global l2protocol configuration";
        reference " 0.12.6.";
    }

    revision "2024-07-26" {
        description "Make previous revision tag consistent";
        reference " 0.12.5.";
    }

    revision "2024-07-25" {
        description "Added UCMP CLI option";
        reference " 0.12.4.";
    }

    revision "2024-06-18" {
        description "Added BVI element in hardware type datatype";
        reference " 0.12.3.";
    }

    revision "2024-03-27" {
        description "Added limited autonegotiation support";
        reference " 0.12.2.";
    }

    revision "2024-01-24" {
        description "If Type data-model revision has higher date";
        reference " 0.12.1.";
    }

    revision "2024-01-06" {
        description "Added storm-control errdisable";
        reference " 0.12.0.";
    }

    revision "2023-12-20" {
        description "Added a new datatype IF_RAON_AODU_STATE";
        reference " 0.11.9.";
    }

    revision "2023-10-10" {
        description "Change storm-control maximum level to 99%";
        reference " 0.11.8.";
    }

    revision "2023-08-23" {
        description "Added datatype IF_ACLIF_TYPE_T";
        reference " 0.11.7.";
    }

    revision "2023-08-18" {
        description "Added pattern tag for the datatype IF_SUBIF_OUTER_TPID_T";
        reference " 0.11.6.";
    }

    revision "2023-06-28" {
        description "Added when tag with skip-dependency-validation flag for the attribute mac-address";
        reference " 0.11.5.";
    }

    revision "2023-05-26" {
        description "Added element types for FEC type configuration support";
        reference " 0.11.4.";
    }

    revision "2023-04-28" {
        description "Removed HARDWARE_PORT_MODE data type";
        reference " 0.11.3.";
    }

    revision "2023-03-15" {
        description "Added when tag for ethernet container augmentation";
        reference " 0.11.2.";
    }

    revision "2023-03-03" {
        description "Added datatype for split-horizon";
        reference " 0.11.1.";
    }

    revision "2022-11-14" {
        description "Added support for Storm-control by Frame per second";
        reference " 0.11.0.";
    }

    revision "2022-09-27" {
        description "Added loopback-detection in ipi-if-types";
        reference " 0.10.0.";
    }

    revision "2022-08-11" {
        description "adding mac-address secondary command support for XGS";
        reference " 0.9.0.";
    }

    revision "2022-08-01" {
        description "adding mac-address secondary command support";
        reference " 0.8.0.";
    }

    revision "2022-07-30" {
        description "Updated when expressions in yang";
        reference " 0.8.0.";
    }

    revision "2022-06-01" {
        description "Updated the yang file with feature";
        reference " 0.7.0.";
    }

    revision "2022-04-28" {
        description "Renamed EVPN IRB related attributes";
        reference " 0.6.0.";
    }

    revision "2021-11-15" {
        description "Moved L2 depenedecies under HAVE_L2";
        reference "Initial Version";
    }

    revision "2021-09-03" {
        description "Update descriptions of attribute";
        reference " 0.5.0.";
    }

    revision "2021-03-16" {
        description "Added when tags to suppress attributes for subinterface";
        reference " 0.4.0.";
    }

    revision "2020-12-15" {
        description "Change to have data-types in lower case instead of camel case";
        reference " 0.3.0.";
    }

    revision "2020-11-13" {
        description "Updated mac-address attr for feature HAVE_DUNE";
        reference " 0.2.0.";
    }

    revision "2020-07-15" {
        description "Initial Version Openconfig Yang model : https://github.com/openconfig/public/blob/master/release/models/interfaces/openconfig-if-ethernet.yang";
        reference " 0.1.0.";
    }

    grouping ethernet-interface-config {
        description
            "Configuration items for Ethernet interfaces";
        leaf duplex-mode  {
            // when " contain(ipi-interface:interfaces/interface/name, 'vlan') + contain(ipi-interface:interfaces/interface/name, 'pmsi') + !contain(ipi-interface:interfaces/interface/name, '.') ";
            type  ipi-if-types:if_duplex_t;
            description "Use this attribute to set the duplex mode for the interface.
                        Auto-negotiation if enabled, is turned off when duplex mode is set for
                        the interface.
                        When auto-negotiation is enabled, the interface should negotiate the
                        duplex mode directly (typically full-duplex).";
        } // END of duplex-mode definition.

        leaf mac-address  {
            if-feature feature-list:NOT_HAVE_DUNE;
            type  cml-data-types:cml_mac_addr_t {
                length "1..20";
            }
            description "Use this attribute to set the mac address for an interface.
                        If not specified, the corresponding operational state leaf is
                        expected to show the system-assigned MAC address.";
        } // END of mac-address definition.

        leaf secondary-mac-address  {
            if-feature feature-list:HAVE_MLAG;
            type  empty;
            description "Use this attribute to set the secondary mac address for an
                        interface to terminate L3 packets.";
        } // END of secondary-mac-address definition.

        leaf port-speed  {
            if-feature feature-list:NOT_HAVE_TIBIT;
            type  ipi-if-types:if_interface_speed_t;
            description "This attribute is used to set the link speed for the interface.
                        To enable auto-negotiation for the interface, set this attribute to
                        value auto.
                        When auto-negotiation is enabled, it is expected that the interface
                        will select the highest speed available based on negotiation.
                        When auto-negotiation is not enabled, sets the link speed to a fixed
                        value -- supported values are defined by IF_INTERFACE_SPEED_T enum.
                        When limited auto-negotiation is required, select the speed after the
                        auto option. With this only the specified speed will be
                        advertised and interface will negotiate with peer with that speed
                        only.";
        } // END of port-speed definition.

    } // END of ethernet-interface-config definition.
    grouping flow-control-config {
        description
            "Grouping for Flow control Configuration data for ethernet interfaces";
        leaf enable-rcv  {
            if-feature feature-list:HAVE_L2;
            type  ipi-if-types:if_flowctrl_t;
            default "off";
            description "This attribute is used to show flow control on receive";
        } // END of enable-rcv definition.

        leaf enable-snd  {
            if-feature feature-list:HAVE_L2;
            type  ipi-if-types:if_flowctrl_t;
            default "off";
            description "This attribute is used to show flow control on send";
        } // END of enable-snd definition.

    } // END of flow-control-config definition.
    grouping flow-control-state {
        description
            "Grouping for Flow control State variables for Ethernet interfaces";
        leaf rcv-oper-status  {
            type  ipi-if-types:if_flowctrl_t;
            config false;
            description "This attribute is used to show Operations status of Flow control on
                        receive";
        } // END of rcv-oper-status definition.

        leaf snd-oper-status  {
            type  ipi-if-types:if_flowctrl_t;
            config false;
            description "This attribute is used to show Operations status of Flow control on
                        send";
        } // END of snd-oper-status definition.

    } // END of flow-control-state definition.
    grouping ethernet-in-frames-size-dist {
        description
            "Grouping for defining the size distribution of the frames received";
        container in-distribution {
            config false;
            description
                "In distribution interface counters";
            leaf in-frames-64-octets  {
                if-feature feature-list:HAVE_BROADCOM;
                if-feature feature-list:HAVE_HAL;
                if-feature feature-list:NOT_HAVE_SWFWDR;
                type  yang:counter64;
                description "Number of packets (including bad packets) received that
                            were 64 bytes in length (excluding framing bits but including FCS
                            bytes).";
            } // END of in-frames-64-octets definition.

            leaf in-frames-65-127-octets  {
                if-feature feature-list:HAVE_BROADCOM;
                if-feature feature-list:HAVE_HAL;
                if-feature feature-list:NOT_HAVE_SWFWDR;
                type  yang:counter64;
                description "Number of good and bad packets received that were
                            between 65 and 127 bytes in length (excluding framing bits but
                            including FCS bytes).";
            } // END of in-frames-65-127-octets definition.

            leaf in-frames-128-255-octets  {
                if-feature feature-list:HAVE_BROADCOM;
                if-feature feature-list:HAVE_HAL;
                if-feature feature-list:NOT_HAVE_SWFWDR;
                type  yang:counter64;
                description "Number of good and bad packets received that were
                            between 128 and 255 bytes in length inclusive
                            (excluding framing bits but including FCS bytes).";
            } // END of in-frames-128-255-octets definition.

            leaf in-frames-256-511-octets  {
                if-feature feature-list:HAVE_BROADCOM;
                if-feature feature-list:HAVE_HAL;
                if-feature feature-list:NOT_HAVE_SWFWDR;
                type  yang:counter64;
                description "Number of good and bad packets received that were
                            between 256 and 511 bytes in length inclusive
                            (excluding framing bits but including FCS bytes).";
            } // END of in-frames-256-511-octets definition.

            leaf in-frames-512-1023-octets  {
                if-feature feature-list:HAVE_BROADCOM;
                if-feature feature-list:HAVE_HAL;
                if-feature feature-list:NOT_HAVE_SWFWDR;
                type  yang:counter64;
                description "Number of good and bad packets received that were
                            between 512 and 1023 bytes in length inclusive
                            (excluding framing bits but including FCS bytes).";
            } // END of in-frames-512-1023-octets definition.

            leaf in-frames-1024-1518-octets  {
                if-feature feature-list:HAVE_BROADCOM;
                if-feature feature-list:HAVE_HAL;
                if-feature feature-list:NOT_HAVE_SWFWDR;
                type  yang:counter64;
                description "Number of good and bad packets received that were
                            between 1024 and 1518 bytes in length inclusive
                            (excluding framing bits but including FCS bytes).";
            } // END of in-frames-1024-1518-octets definition.

            leaf in-frames-1519-2047-octets  {
                if-feature feature-list:HAVE_BROADCOM;
                if-feature feature-list:HAVE_HAL;
                if-feature feature-list:NOT_HAVE_SWFWDR;
                type  yang:counter64;
                description "Number of good and bad packets received that were
                            between 1519 and 2047 bytes in length inclusive
                            (excluding framing bits but including FCS bytes).";
            } // END of in-frames-1519-2047-octets definition.

            leaf in-frames-2048-4095-octets  {
                if-feature feature-list:HAVE_BROADCOM;
                if-feature feature-list:HAVE_HAL;
                if-feature feature-list:NOT_HAVE_SWFWDR;
                type  yang:counter64;
                description "Number of good and bad packets received that were
                            between 2048 and 4095 bytes in length inclusive
                            (excluding framing bits but including FCS bytes).";
            } // END of in-frames-2048-4095-octets definition.

            leaf in-frames-4096-9216-octets  {
                if-feature feature-list:HAVE_BROADCOM;
                if-feature feature-list:HAVE_HAL;
                if-feature feature-list:NOT_HAVE_SWFWDR;
                type  yang:counter64;
                description "Number of good and bad packets received that were
                            between 4096 and 9216 bytes in length inclusive
                            (excluding framing bits but including FCS bytes).";
            } // END of in-frames-4096-9216-octets definition.

            leaf in-frames-9217-16383-octets  {
                if-feature feature-list:HAVE_BROADCOM;
                if-feature feature-list:HAVE_HAL;
                if-feature feature-list:NOT_HAVE_SWFWDR;
                type  yang:counter64;
                description "Number of good and bad packets received that were
                            between 9217 and 16383 bytes in length inclusive
                            (excluding framing bits but including FCS bytes).";
            } // END of in-frames-9217-16383-octets definition.

        } // END of in-distribution-container definition.
    } // END of ethernet-in-frames-size-dist definition.
    grouping ethernet-out-frames-size-dist {
        description
            "Grouping for defining the size distribution of the frames sent";
        container out-distribution {
            config false;
            description
                "Out distribution interface counters";
            leaf out-frames-64-octets  {
                if-feature feature-list:HAVE_BROADCOM;
                if-feature feature-list:HAVE_HAL;
                if-feature feature-list:NOT_HAVE_SWFWDR;
                type  yang:counter64;
                description "Number of packets (including bad packets) sent that
                            were 64 bytes in length (excluding framing bits but including FCS
                            bytes).";
            } // END of out-frames-64-octets definition.

            leaf out-frames-65-127-octets  {
                if-feature feature-list:HAVE_BROADCOM;
                if-feature feature-list:HAVE_HAL;
                if-feature feature-list:NOT_HAVE_SWFWDR;
                type  yang:counter64;
                description "Number of good and bad packets sent that were
                            between 65 and 127 bytes in length (excluding framing bits but
                            including FCS bytes).";
            } // END of out-frames-65-127-octets definition.

            leaf out-frames-128-255-octets  {
                if-feature feature-list:HAVE_BROADCOM;
                if-feature feature-list:HAVE_HAL;
                if-feature feature-list:NOT_HAVE_SWFWDR;
                type  yang:counter64;
                description "Number of good and bad packets sent that were
                            between 128 and 255 bytes in length inclusive
                            (excluding framing bits but including FCS bytes).";
            } // END of out-frames-128-255-octets definition.

            leaf out-frames-256-511-octets  {
                if-feature feature-list:HAVE_BROADCOM;
                if-feature feature-list:HAVE_HAL;
                if-feature feature-list:NOT_HAVE_SWFWDR;
                type  yang:counter64;
                description "Number of good and bad packets sent that were
                            between 256 and 511 bytes in length inclusive
                            (excluding framing bits but including FCS bytes).";
            } // END of out-frames-256-511-octets definition.

            leaf out-frames-512-1023-octets  {
                if-feature feature-list:HAVE_BROADCOM;
                if-feature feature-list:HAVE_HAL;
                if-feature feature-list:NOT_HAVE_SWFWDR;
                type  yang:counter64;
                description "Number of good and bad packets sent that were
                            between 512 and 1023 bytes in length inclusive
                            (excluding framing bits but including FCS bytes).";
            } // END of out-frames-512-1023-octets definition.

            leaf out-frames-1024-1518-octets  {
                if-feature feature-list:HAVE_BROADCOM;
                if-feature feature-list:HAVE_HAL;
                if-feature feature-list:NOT_HAVE_SWFWDR;
                type  yang:counter64;
                description "Number of good and bad packets sent that were
                            between 1024 and 1518 bytes in length inclusive
                            (excluding framing bits but including FCS bytes).";
            } // END of out-frames-1024-1518-octets definition.

            leaf out-frames-1519-2047-octets  {
                if-feature feature-list:HAVE_BROADCOM;
                if-feature feature-list:HAVE_HAL;
                if-feature feature-list:NOT_HAVE_SWFWDR;
                type  yang:counter64;
                description "Number of good and bad packets sent that were
                            between 1519 and 2047 bytes in length inclusive
                            (excluding framing bits but including FCS bytes).";
            } // END of out-frames-1519-2047-octets definition.

            leaf out-frames-2048-4095-octets  {
                if-feature feature-list:HAVE_BROADCOM;
                if-feature feature-list:HAVE_HAL;
                if-feature feature-list:NOT_HAVE_SWFWDR;
                type  yang:counter64;
                description "Number of good and bad packets sent that were
                            between 2048 and 4095 bytes in length inclusive
                            (excluding framing bits but including FCS bytes).";
            } // END of out-frames-2048-4095-octets definition.

            leaf out-frames-4096-9216-octets  {
                if-feature feature-list:HAVE_BROADCOM;
                if-feature feature-list:HAVE_HAL;
                if-feature feature-list:NOT_HAVE_SWFWDR;
                type  yang:counter64;
                description "Number of good and bad packets sent that were
                            between 4096 and 9216 bytes in length inclusive
                            (excluding framing bits but including FCS bytes).";
            } // END of out-frames-4096-9216-octets definition.

            leaf out-frames-9217-16383-octets  {
                if-feature feature-list:HAVE_BROADCOM;
                if-feature feature-list:HAVE_HAL;
                if-feature feature-list:NOT_HAVE_SWFWDR;
                type  yang:counter64;
                description "Number of good and bad packets sent that were
                            between 9217 and 16383 bytes in length inclusive
                            (excluding framing bits but including FCS bytes).";
            } // END of out-frames-9217-16383-octets definition.

        } // END of out-distribution-container definition.
    } // END of ethernet-out-frames-size-dist definition.
    grouping ethernet-interface-state-counters {
        description
            "Ethernet-specific counters and statistics";
        leaf in-mac-control-frames  {
            if-feature feature-list:HAVE_BROADCOM;
            if-feature feature-list:HAVE_HAL;
            if-feature feature-list:NOT_HAVE_SWFWDR;
            type  yang:counter64;
            config false;
            description "MAC layer control frames received on the interface";
        } // END of in-mac-control-frames definition.

        leaf in-mac-pause-frames  {
            type  yang:counter64;
            config false;
            description "MAC layer PAUSE frames received on the interface";
        } // END of in-mac-pause-frames definition.

        leaf in-undersize-frames  {
            if-feature feature-list:HAVE_BROADCOM;
            if-feature feature-list:HAVE_HAL;
            if-feature feature-list:NOT_HAVE_SWFWDR;
            type  yang:counter64;
            config false;
            description "The total number of frames received that were
                        less than 64 octets long (excluding framing bits,
                        but including FCS octets) and were otherwisewell formed.";
        } // END of in-undersize-frames definition.

        leaf in-oversize-frames  {
            if-feature feature-list:HAVE_BROADCOM;
            if-feature feature-list:HAVE_HAL;
            if-feature feature-list:NOT_HAVE_SWFWDR;
            type  yang:counter64;
            config false;
            description "The total number of frames received that were
                        longer than 1518 octets (excluding framing bits,
                        but including FCS octets) and were otherwise well formed.";
        } // END of in-oversize-frames definition.

        leaf in-fragment-frames  {
            if-feature feature-list:HAVE_BROADCOM;
            if-feature feature-list:HAVE_HAL;
            if-feature feature-list:NOT_HAVE_SWFWDR;
            type  yang:counter64;
            config false;
            description "The total number of frames received that were less than
                        64 octets in length (excluding framing bits but including
                        FCS octets) and had either a bad Frame Check Sequence
                        (FCS) with an integral number of octets (FCS Error) or a
                        bad FCS with a non-integral number of octets (Alignment Error).";
        } // END of in-fragment-frames definition.

        leaf in-jabber-frames  {
            if-feature feature-list:HAVE_BROADCOM;
            if-feature feature-list:HAVE_HAL;
            if-feature feature-list:NOT_HAVE_SWFWDR;
            type  yang:counter64;
            config false;
            description "Number of jabber frames received on the
                        interface.  Jabber frames are typically defined as oversize
                        frames which also have a bad CRC.  Implementations may use
                        slightly different definitions of what constitutes a jabber
                        frame.  Often indicative of a NIC hardware problem.";
        } // END of in-jabber-frames definition.

        leaf in-crc-errors  {
            if-feature feature-list:HAVE_BROADCOM;
            if-feature feature-list:HAVE_HAL;
            if-feature feature-list:NOT_HAVE_SWFWDR;
            type  yang:counter64;
            config false;
            description "The total number of frames received that
                        had a length (excluding framing bits, but including FCS octets) of
                        between 64 and 1518
                        octets, inclusive, but had either a bad Frame Check Sequence (FCS)
                        with an integral
                        number of octets (FCS Error) or a bad FCS with a non-integral number
                        of octets (Alignment Error)";
        } // END of in-crc-errors definition.

        leaf out-mac-control-frames  {
            if-feature feature-list:HAVE_BROADCOM;
            if-feature feature-list:HAVE_HAL;
            if-feature feature-list:NOT_HAVE_SWFWDR;
            type  yang:counter64;
            config false;
            description "MAC layer control frames sent on the interface";
        } // END of out-mac-control-frames definition.

        leaf out-mac-pause-frames  {
            type  yang:counter64;
            config false;
            description "MAC layer PAUSE frames sent on the interface";
        } // END of out-mac-pause-frames definition.

    } // END of ethernet-interface-state-counters definition.
    grouping ethernet-interface-state {
        description
            "Grouping for defining Ethernet-specific operational state";
        leaf hw-mac-address  {
            type  cml-data-types:cml_mac_addr_t {
                length "1..1965";
            }
            config false;
            description "Represenets the 'burned-in',  or system-assigned, MAC
                        address for the Ethernet interface.";
        } // END of hw-mac-address definition.

        leaf negotiated-duplex-mode  {
            type  ipi-if-types:if_duplex_t;
            config false;
            description "When auto-negotiate is set to TRUE, and the interface has
                        completed auto-negotiation with the remote peer, this value
                        shows the duplex mode that has been negotiated.";
        } // END of negotiated-duplex-mode definition.

        leaf negotiated-port-speed  {
            type  ipi-if-types:if_interface_speed_t;
            config false;
            description "When auto-negotiate is set to TRUE, and the interface has
                        completed auto-negotiation with the remote peer, this value
                        shows the speed that has been negotiated.";
        } // END of negotiated-port-speed definition.

        container counters {
            config false;
            description
                "Ethernet interface counters";
            uses ethernet-interface-state-counters;
            uses ethernet-in-frames-size-dist;
            uses ethernet-out-frames-size-dist;
        } // END of counters-container definition.
    } // END of ethernet-interface-state definition.

    grouping  ethernet-grouping {
    description
        "Top-level container for ethernet configuration";
    container ethernet {
        description
            "Top-level container for ethernet configuration";
        container config {
            description
                "Configuration data for ethernet interfaces";
            uses ethernet-interface-config;
        } // END of config-container definition.
        container state {
            config false;
            description
                "State variables for Ethernet interfaces";
            uses ethernet-interface-config;
            uses ethernet-interface-state;
        } // END of state-container definition.
        container flow-control {
            if-feature feature-list:HAVE_L2;
            description
                "Flow control container for ethernet configuration";
            container config {
                description
                    "Flow control Configuration data for ethernet interfaces";
                uses flow-control-config;
            } // END of config-container definition.
            container state {
                config false;
                description
                    "Flow control State variables for Ethernet interfaces";
                uses flow-control-config;
                uses flow-control-state;
            } // END of state-container definition.
        } // END of flow-control-container definition.
    } // END of ethernet-container definition.
    } // END of ethernet-grouping definition.

    augment /ipi-interface:interfaces/ipi-interface:interface {
    when " /ipi-interface:interfaces/ipi-interface:interface ";
        description
            "Top-level container for ethernet configuration";
        uses ethernet-grouping;
    }


}
