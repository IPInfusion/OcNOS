/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-if-ip.yang
*
*/

module ipi-if-ip {

    yang-version 1.1;

    namespace   "http://www.ipinfusion.com/yang/ocnos/ipi-if-ip";

    prefix "ipi-if-ip";

    import cml-data-types {
        prefix cml-data-types;
        revision-date 2026-05-15;
    }

    import ipi-network-instance {
        prefix ipi-network-instance;
        revision-date 2026-08-12;
    }

    import ipi-vrf {
        prefix ipi-vrf;
        revision-date 2026-08-12;
    }

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for IP interface module";


    revision "2025-10-08" {
        description "Avoid checking UNIQUE in case of default values";
        reference " 0.23.1.";
    }

    revision "2025-09-04" {
        description "Removed EVPN_IRB_IF_MODE while configuring IRB interface";
        reference " 0.23.0.";
    }

    revision "2025-05-11" {
        description "Add 'CML_UNIQUE' support for attribute 'vrf-name' and 'primary-ip-addr'";
        reference " 0.22.7.";
    }

    revision "2025-05-07" {
        description "Removed 'CML_UNIQUE' support for attribute 'vrf-name' and 'primary-ip-addr'";
        reference " 0.22.6.";
    }

    revision "2025-04-29" {
        description "Add 'CML_UNIQUE' support for attribute 'vrf-name' and 'primary-ip-addr'";
        reference " 0.22.5.";
    }

    revision "2025-03-26" {
        description "Updated when tag for sub-interface for ipv4 and ipv6 address";
        reference " 0.22.4.";
    }

    revision "2025-02-27" {
        description "Removed the CML-UNIQUE flag since its not required";
        reference " 0.22.3.";
    }

    revision "2025-02-19" {
        description "Added UNIQUE attr flag for primary-ip-addr";
        reference " 0.22.2.";
    }

    revision "2024-11-09" {
        description "Added exclusive-attr tag for primary-ip-addr and enable-dhcp-ip-address attributes";
        reference " 0.22.1.";
    }

    revision "2024-07-26" {
        description "Added implicit-delete vrf to config container";
        reference " 0.22.1.";
    }

    revision "2024-07-10" {
        description "Updated when tag flag for primary-ip-addr attribute";
        reference " 0.22.0.";
    }

    revision "2024-05-16" {
        description "Removed when tag from ipv6/addresses";
        reference " 0.21.0.";
    }

    revision "2024-03-28" {
        description "Added new optional CLI max-address along with ipv6 address autoconfig to support 64 address autoconfig";
        reference " 0.20.1.";
    }

    revision "2024-03-05" {
        description "Added when tag to resolve db-sync issue";
        reference " 0.20.0.";
    }

    revision "2023-11-21" {
        description "Added no config CLI support for ipv6 anycast option under interface mode ";
        reference " 0.19.3.";
    }

    revision "2023-10-24" {
        description "Add the proper dependencies for FlexE objects";
        reference " 0.19.2.";
    }

    revision "2023-10-05" {
        description "Changed the vrf when tag for ipv4 container from config level to secondary-addresses object level";
        reference " 0.19.1.";
    }

    revision "2023-09-22" {
        description "Added when tag for v6 autoconfig";
        reference " 0.19.0.";
    }

    revision "2023-06-12" {
        description "Added CML_RESET_INSTANCE flag for primary-ip-addr attribute";
        reference " 0.18.2.";
    }

    revision "2023-04-19" {
        description "Added HAVE_BGP_EVPN flag for referring EVPN data model objects";
        reference " 0.18.1.";
    }

    revision "2023-04-04" {
        description "Removed when tag from ipv4/secondary-addresses for dependency check on 'primary-ip-addr'";
        reference " 0.18.0.";
    }

    revision "2023-02-27" {
        description "Added dependentObject for IPv4/IPv6 address with gateway-mac";
        reference " 0.17.1.";
    }

    revision "2023-02-14" {
        description "Anycast flag added for IPv4 primary and secondary address";
        reference " 0.17.0.";
    }

    revision "2023-01-05" {
        description "Leafref correction for config container";
        reference " 0.16.2.";
    }

    revision "2022-12-20" {
        description "Added missing cliprependstr tags";
        reference " 0.16.1.";
    }

    revision "2022-11-16" {
        description "Added missing cliprependstr tags";
        reference " 0.16.0.";
    }

    revision "2022-09-06" {
        description "Corrected if-feature from HAVE_DHCP_SERVER to HAVE_HOSTP_DHCP_SERVER";
        reference " 0.15.3.";
    }

    revision "2022-09-05" {
        description "Added when tag to throw an error when dhcp server and client is enabled on an same interface";
        reference " 0.15.2.";
    }

    revision "2022-08-12" {
        description "Added when tag to delete ipv4 when interface is attached to a modem interface";
        reference " 0.15.1.";
    }

    revision "2022-08-10" {
        description "Debug hierarchy change";
        reference " 0.15.1.";
    }

    revision "2022-07-31" {
        description "Stop using inet:ipv4-prefix and inet:ipv6-prefix due to Cisco NSO iterop";
        reference " 0.15.0.";
    }

    revision "2022-07-30" {
        description "Updated when expressions in yang";
        reference " 0.15.0.";
    }

    revision "2022-07-21" {
        description "Added dependent ibject for ipv6 address list";
        reference " 0.14.0.";
    }

    revision "2022-07-08" {
        description "Added new attributes to support Get api for auto-ipv6-address learn from peer";
        reference " 0.13.0.";
    }

    revision "2022-06-29" {
        description "Added base interface config as dependent object for ipv4 and ipv6 address config containers";
        reference " 0.12.0.";
    }

    revision "2022-06-01" {
        description "Updated the yang file with feature";
        reference " 0.11.0.";
    }

    revision "2022-04-28" {
        description "Renamed VxLAN IRB to EVPN IRB";
        reference " 0.10.0.";
    }

    revision "2022-04-04" {
        description "Added if-feature whereever needed";
        reference " 0.9.0.";
    }

    revision "2022-02-09" {
        description "Changed datatype for enable-auto-router-id-selection attribute from boolean to empty";
        reference " 0.8.0.";
    }

    revision "2021-11-16" {
        description "Added some if-feature to fix customer SKU compilation";
        reference " 0.7.0.";
    }

    revision "2021-09-01" {
        description "Changed base interface module's switchport attribute name and the datatype from bool to empty";
        reference " 0.6.0.";
    }

    revision "2021-01-27" {
        description "Removed interface mode on ipv6 address attribute";
        reference " 0.5.0.";
    }

    revision "2021-01-14" {
        description "Changed datatype for IPv6 address anycast attr from boolean to empty";
        reference " 0.4.0.";
    }

    revision "2020-12-15" {
        description "Change to have data-types in lower case instead of camel case";
        reference " 0.3.0.";
    }

    revision "2020-11-13" {
        description "Updated IP/IPv6/ICMP forwarding attribute from bool to empty, Added new attribute enable-dhcp-ip-address and enable-dhcp-ipv6-address";
        reference " 0.2.0.";
    }

    revision "2020-07-15" {
        description "Initial Version Openconfig Yang model : https://github.com/openconfig/public/blob/master/release/models/interfaces/openconfig-if-ip.yang";
        reference " 0.1.0.";
    }

    grouping ipv4-interface-config {
        description
            "Configuration data for IPv4 per interface";
        leaf primary-ip-addr  {
            type  cml-data-types:cml_ipv4_prefix_t;
            description "Use this attribute to specify that an IP address and prefix length
                        will be used by this interface. If the secondary parameter is not
                        specified, this attribute overwrites the primary IP address. If the
                        secondary parameter is specified, this attribute adds a new IP address
                        to the interface. The secondary address cannot be configured in the
                        absence of a primary IP address. The primary address cannot be removed
                        when a secondary address is present.";
        } // END of primary-ip-addr definition.

        leaf enable-dhcp-ip-address  {
            // when " not(/ipi-interface:interfaces/ipi-interface:interface/ipi-interface:config/ipi-interface:enable-switchport) ";
            if-feature feature-list:HAVE_DHCP_CLIENT;
            type  empty;
            description "Use this attribute to  specify that a DHCP client will be used to
                        obtain an IP address for an interface.";
        } // END of enable-dhcp-ip-address definition.

        leaf prefix-length  {
            type  uint8;
            description "The subnet mask associated with the IPv4 address of this entry. The
                        value of the mask is an IPv4 address with all the network bits set to
                        1 and all the hosts bits set to 0.";
        } // END of prefix-length definition.

        leaf ip-addr-label  {
            // when " ipi-if-ip:ipv4/config/primary-ip-addr ";
            type  cml-data-types:cml_line_t {
                length "1..1965";
            }
            default "NULL";
            description "Label of this address.";
        } // END of ip-addr-label definition.

        leaf ipv4-unnumbered-if-name  {
            if-feature feature-list:HAVE_NSM_IF_UNNUMBERED;
            type  string {
                length "1..1965";
                pattern "[^?' =,>|]+";
            }
            description "This attribute is used to Enable IP processing without an explicit
                        address";
        } // END of ipv4-unnumbered-if-name definition.

        leaf remote-address  {
            if-feature feature-list:HAVE_NSM_IF_UNNUMBERED;
            type  string {
                length "1..1965";
                pattern "[^?' =,>|]+";
            }
            description "This attribute is used to set the remote address of the PPP link";
        } // END of remote-address definition.

        leaf primary-anycast  {
            // when " ipi-if-ip:ipv4/config/primary-ip-addr ";
            type  empty;
            description "Use this attribute to set the anycast flag for the IPv4 primary
                        address of an interface.";
        } // END of primary-anycast definition.

    } // END of ipv4-interface-config definition.
    grouping ipv4-sec-addr-config {
        description
            "Per IPv4 secondary adresss configuration data for the interface";
        leaf ip-address  {
            type  cml-data-types:cml_ipv4_prefix_t;
            description "Use this attribute to specify a secondary IP address that will be
                        used by this interface. The secondary address cannot be configured in
                        the absence of a primary IP address. The primary address cannot be
                        removed when a secondary address is present.";
        } // END of ip-address definition.

        leaf ip-label  {
            type  cml-data-types:cml_line_t {
                length "1..1965";
            }
            default "NULL";
            description "Use this attribute to specify a descriptive label for this IPv4
                        address.";
        } // END of ip-label definition.

        leaf secondary-anycast  {
            type  empty;
            description "Use this attribute to set the anycast flag for the IPv4 secondary
                        address of an interface.";
        } // END of secondary-anycast definition.

    } // END of ipv4-sec-addr-config definition.
    grouping ipv4-interface-state {
        description
            "IPv4 operational state for the interface";
        leaf dhcp-ip-adddress  {
            if-feature feature-list:HAVE_DHCP_CLIENT;
            type  cml-data-types:cml_ipv4_prefix_t;
            config false;
            description "This attribute displays the IPv4 address allocated by DHCP";
        } // END of dhcp-ip-adddress definition.

        leaf ipv4-enabled-status  {
            type  boolean;
            config false;
            description "This attribute displays IPv4 enable status";
        } // END of ipv4-enabled-status definition.

    } // END of ipv4-interface-state definition.
    grouping ipv6-interface-config {
        description
            "Configuration data for IPv6 per interface";
        leaf ipv6-unnumbered-if-name  {
            if-feature feature-list:HAVE_NSM_IF_UNNUMBERED;
            if-feature feature-list:HAVE_IPV6;
            type  string {
                length "1..1965";
                pattern "[^?' =,>|]+";
            }
            description "Use this attribute to enable IP processing without an explicit address";
        } // END of ipv6-unnumbered-if-name definition.

        leaf enable-dhcp-ipv6-address  {
            // when " not(/ipi-interface:interfaces/ipi-interface:interface/ipi-interface:config/ipi-interface:enable-switchport) ";
            if-feature feature-list:HAVE_DHCP_CLIENT;
            type  empty;
            description "Use this attribute to  specify that a DHCP client will be used to
                        obtain an IP address for an interface.";
        } // END of enable-dhcp-ipv6-address definition.

        leaf enable-dhcp-temporary-ipv6-address  {
            // when " not(/ipi-interface:interfaces/ipi-interface:interface/ipi-interface:config/ipi-interface:enable-switchport) ";
            if-feature feature-list:HAVE_DHCP_CLIENT;
            type  empty;
            description "Use this attribute to  specify that a DHCP client will be used to
                        obtain an temporary IP address for an interface.";
        } // END of enable-dhcp-temporary-ipv6-address definition.

        leaf dhcp-address-prefix-length  {
            // when " not(/ipi-interface:interfaces/ipi-interface:interface/ipi-interface:config/ipi-interface:enable-switchport) ";
            if-feature feature-list:HAVE_DHCP_CLIENT;
            type  uint8 {
                 range "1..128"  {
                    description "1..128: Supported range 1 - 128";
                 }
            }
            description "Use this attribute to configure the prefix length for the dynamically
                        learnt ipv6 address";
        } // END of dhcp-address-prefix-length definition.

        leaf enable-auto-config  {
            // when " not(/ipi-interface:interfaces/ipi-interface:interface/ipi-interface:config/ipi-interface:enable-switchport) ";
            if-feature feature-list:HAVE_IPV6;
            type  boolean;
            description "Use this attribute to enable autoconfiguration of IPv6 address in host
                        interface. IPv6 address are formed using the Prefix learned from RA
                        and suffix formed using EUI-64 method.";
        } // END of enable-auto-config definition.

        leaf max-autoconfig-address  {
            // when " not(/ipi-interface:interfaces/ipi-interface:interface/ipi-interface:config/ipi-interface:enable-switchport) ";
            type  uint8 {
                 range "1..64"  {
                    description "1..64: Supported range 1 - 64";
                 }
            }
            description "Use this attribute to set the autoconfiguration count of IPv6 address
                        to be allowed in host interface.";
        } // END of max-autoconfig-address definition.

    } // END of ipv6-interface-config definition.
    grouping ipv6-addr-config {
        description
            "Per IPV6 address configuration data for the interface";
        leaf ipv6-address  {
            type  cml-data-types:cml_ipv6_prefix_t;
            description "Use this attribute to set the IPv6 address of an interface";
        } // END of ipv6-address definition.

        leaf anycast  {
            type  empty;
            description "Use this attribute to set the anycast flag for the IPv6
                        address of an interface.
                        Anycast flag cannot be deleted for an IPv6 address once set. Please
                        delete IPv6 address and reconfigure to remove anycast property.";
        } // END of anycast definition.

    } // END of ipv6-addr-config definition.
    grouping ipv6-interface-state {
        description
            "IPv6 operational state for the interface";
        leaf dhcp-ipv6-adddress  {
            if-feature feature-list:HAVE_DHCP_CLIENT;
            type  cml-data-types:cml_ipv6_prefix_t;
            config false;
            description "This attribute is used to describes DHCP IPv6 Address";
        } // END of dhcp-ipv6-adddress definition.

        leaf forwarding-status  {
            if-feature feature-list:HAVE_IPV6;
            type  boolean;
            config false;
            description "This attribute describes the IPv6 Forwarding status";
        } // END of forwarding-status definition.

    } // END of ipv6-interface-state definition.
    grouping auto-ipv6-addr-state {
        description
            "Learnt IPV6 address operational data for the interface";
        leaf ipv6-address  {
            type  cml-data-types:cml_ipv6_prefix_t;
            description "Use this attribute to get the Auto IPv6 address of an interface";
        } // END of ipv6-address definition.

        leaf anycast  {
            type  empty;
            description "Use this attribute to get the anycast flag for the Auto IPv6
                        address of an interface.";
        } // END of anycast definition.

        leaf virtual  {
            type  empty;
            description "Use this attribute to get the virtual flag for the Auto IPv6
                        address of an interface.";
        } // END of virtual definition.

        leaf vrrp  {
            if-feature feature-list:HAVE_VRRP_V3;
            type  empty;
            description "Use this attribute to get the vrrp flag for the Auto IPv6
                        address of an interface.";
        } // END of vrrp definition.

    } // END of auto-ipv6-addr-state definition.
    grouping ip-global-config {
        description
            "Global IP related configuration data for the router";
        leaf router-id  {
            type  string {
                length "1..1965";
                pattern "[^?' =,>|]+";
            }
            description "Router id of the router - an unsigned 32-bit integer expressed in
                        dotted quad notation";
        } // END of router-id definition.

        leaf enable-auto-router-id-selection  {
            type  empty;
            description "Turn on Automatic Selection of Router ID";
        } // END of enable-auto-router-id-selection definition.

        leaf disable-ip-forwarding  {
            type  empty;
            description "Enable IP forwarding for the router";
        } // END of disable-ip-forwarding definition.

        leaf disable-ipv6-forwarding  {
            if-feature feature-list:HAVE_IPV6;
            type  empty;
            description "Enable IPv6 forwarding for the router";
        } // END of disable-ipv6-forwarding definition.

        leaf default-vrf-enable-icmp-broadcast  {
            type  empty;
            description "This attribute is used to control ICMP echo broadcast reply. It
                        ignores ICMP echo broacast when set to true";
        } // END of default-vrf-enable-icmp-broadcast definition.

    } // END of ip-global-config definition.
    grouping ip-vrf-config {
        description
            "Per VRF configuration data for the router";
        leaf vrf-name  {
            type  leafref {
                path  "/ipi-network-instance:network-instances/ipi-network-instance:network-instance/ipi-vrf:vrf/ipi-vrf:config/ipi-vrf:vrf-name";
            }
            description "VPN routing/forwarding Instance name";
        } // END of vrf-name definition.

        leaf disable-ip-vrf-forwarding  {
            type  empty;
            description "Turn on IP forwarding for the VRF instance";
        } // END of disable-ip-vrf-forwarding definition.

        leaf disable-ipv6-vrf-forwarding  {
            if-feature feature-list:HAVE_IPV6;
            type  empty;
            description "Turn on IPv6 forwarding for the VRF instance";
        } // END of disable-ipv6-vrf-forwarding definition.

        leaf enable-icmp-broadcast  {
            type  empty;
            description "This attribute is used to control ICMP echo broadcast reply for VRF
                        instance. It ignores ICMP echo broacast when set to true";
        } // END of enable-icmp-broadcast definition.

    } // END of ip-vrf-config definition.

    grouping  ipv4-grouping {
    description
        "Parameters for the IPv4 address family";
    container ipv4 {
        description
            "Parameters for the IPv4 address family";

        list secondary-addresses {
            key "ip-address";
            description
                "List of secondary IPv4 Addresses for the interface";
            leaf ip-address  {
                type  leafref {
                    path  "../config/ip-address";
                }
                description "Use this attribute to specify a secondary IP address that will be
                            used by this interface. The secondary address cannot be configured in
                            the absence of a primary IP address. The primary address cannot be
                            removed when a secondary address is present.";
            } // END of ip-address definition.

            container config {
                description
                    "IPv4 secondary address configuration data for the interface";
                uses ipv4-sec-addr-config;
            } // END of config-container definition.
            container state {
                config false;
                description
                    "IPv4 secondary address list operational information";
                uses ipv4-sec-addr-config;
            } // END of state-container definition.
        } // End of secondary-addresses-list
        container config {
            description
                "Top-level IPv4 configuration data for the interface";
            uses ipv4-interface-config;
        } // END of config-container definition.
        container state {
            config false;
            description
                "Top-level IPv4 operational state data for the interface";
            uses ipv4-interface-config;
            uses ipv4-interface-state;
        } // END of state-container definition.
    } // END of ipv4-container definition.
    } // END of ipv4-grouping definition.

    grouping  ipv6-grouping {
    description
        "Parameters for the IPv6 address family";
    container ipv6 {
        if-feature feature-list:HAVE_IPV6;
        description
            "Parameters for the IPv6 address family";

        list addresses {
        // when " ipi-interface:interfaces/interface/config/enable-switchport != '1' ";
            if-feature feature-list:HAVE_IPV6;
            key "ipv6-address";
            description
                "List of IPv6 Addresses for the interface";
            leaf ipv6-address  {
                type  leafref {
                    path  "../config/ipv6-address";
                }
                description "Use this attribute to set the IPv6 address of an interface";
            } // END of ipv6-address definition.

            container config {
                description
                    "IPv6 address configuration data for the interface";
                uses ipv6-addr-config;
            } // END of config-container definition.
            container state {
                config false;
                description
                    "IPv6 address list operational data for the interface";
                uses ipv6-addr-config;
            } // END of state-container definition.
        } // End of addresses-list
        container config {
            description
                "Top-level IPv6 configuration data for the interface";
            uses ipv6-interface-config;
        } // END of config-container definition.
        container state {
            config false;
            description
                "Top-level IPv6 operational state data for the interface";
            uses ipv6-interface-config;
            uses ipv6-interface-state;
        } // END of state-container definition.
        container auto-addresses {
            if-feature feature-list:HAVE_IPV6;
            config false;
            description
                "Parameters for the Learnt IPv6 address from Peer";

            list auto-address {
                key "ipv6-address";
                config false;
                description
                    "List of Learnt IPv6 address from Peer";
                leaf ipv6-address  {
                    type  leafref {
                        path  "../state/ipv6-address";
                    }
                    description "Use this attribute to get the Auto IPv6 address of an interface";
                } // END of ipv6-address definition.

                container state {
                    config false;
                    description
                        "Learnt IPv6 address list operational data for the interface";
                    uses auto-ipv6-addr-state;
                } // END of state-container definition.
            } // End of auto-address-list
        } // END of auto-addresses-container definition.
    } // END of ipv6-container definition.
    } // END of ipv6-grouping definition.

    grouping  ip-global-grouping {
    description
        "Global configuration container for the router";
    container ip-global {
        description
            "Global configuration container for the router";

        list vrf {
            if-feature feature-list:HAVE_VRF;
            key "vrf-name";
            description
                "List of Virtual Routing and Forwarding instances on the router";
            leaf vrf-name  {
                type  leafref {
                    path  "../config/vrf-name";
                }
                description "VPN routing/forwarding Instance name";
            } // END of vrf-name definition.

            container config {
                description
                    "Configuration parameters relating to a VRF instance";
                uses ip-vrf-config;
            } // END of config-container definition.
            container state {
                config false;
                description
                    "Configuration parameters relating to a VRF instance";
                uses ip-vrf-config;
            } // END of state-container definition.
        } // End of vrf-list
        container config {
            description
                "Global configuration parameters for the router";
            uses ip-global-config;
        } // END of config-container definition.
        container state {
            config false;
            description
                "Global operational parameters for the router";
            uses ip-global-config;
        } // END of state-container definition.
    } // END of ip-global-container definition.
    } // END of ip-global-grouping definition.

    augment /ipi-interface:interfaces/ipi-interface:interface {
        description
            "Parameters for the IPv4 address family";
        uses ipv4-grouping;
    }

    augment /ipi-interface:interfaces/ipi-interface:interface {
        description
            "Parameters for the IPv6 address family";
        uses ipv6-grouping;
    }

    uses ip-global-grouping;

}
