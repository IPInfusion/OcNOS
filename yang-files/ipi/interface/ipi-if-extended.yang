/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-if-extended.yang
*
*/

module ipi-if-extended {

    yang-version 1.1;

    namespace   "http://www.ipinfusion.com/yang/ocnos/ipi-if-extended";

    prefix "ipi-if-extended";

    import cml-data-types {
        prefix cml-data-types;
        revision-date 2026-05-15;
    }

    import ipi-if-types {
        prefix ipi-if-types;
        revision-date 2026-03-10;
    }

    import ipi-interface {
        prefix ipi-interface;
        revision-date 2026-03-10;
    }

    import ipi-if-ethernet {
        prefix ipi-if-ethernet;
        revision-date 2026-03-10;
    }

    import ipi-port-vlan {
        prefix ipi-port-vlan;
        revision-date 2026-02-12;
    }

    import ietf-inet-types {
        prefix inet;
        revision-date 2013-07-15;
    }

    import ietf-yang-types {
        prefix yang;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for IPI Interface extended module";


    revision "2026-05-25" {
        description "Updated the max range of outer-vlan-id attribute";
        reference " 6.2.12.";
    }

    revision "2026-05-08" {
        description "changed the datatype for outer-vlan-id attribute to range";
        reference " 6.2.11.";
    }

    revision "2026-03-10" {
        description "Added the datatype for media-type attribute";
        reference " 6.3.0.";
    }

    revision "2026-01-21" {
        description "Adding discards counter for ip rx and vlan transmit tx";
        reference " 6.2.4.";
    }

    revision "2025-12-31" {
        description "For protected-port unset cli, removed enum input";
        reference " 6.2.3.";
    }

    revision "2025-12-18" {
        description "Added NETCONF support for link-debounce-timer";
        reference " 6.2.2.";
    }

    revision "2025-11-25" {
        description "Added CML_UNSET_FIRST flag to encapsulation attribute to enforce unconfiguration of previously set value before configuring a new value.";
        reference " 6.2.0.";
    }

    revision "2025-11-21" {
        description "CLI Implementation snmp lowerlayer enable";
        reference " 6.1.4.";
    }

    revision "2025-10-30" {
        description "monitor ecn not applicable for Trident 4 LTSW New platform";
        reference " 6.1.3.";
    }

    revision "2025-10-09" {
        description "Removed blocking for crossconect for XGs platforms";
        reference " 6.1.2.";
    }

    revision "2025-10-08" {
        description "Blocking Bridge-domain and cross-connect for all XGS (DC) platforms";
        reference " 6.1.1.";
    }

    revision "2025-10-06" {
        description "Added when tag for rewrite config container";
        reference " 6.0.9.";
    }

    revision "2025-09-29" {
        description "Added dependency for encapsulation and lag-shaper";
        reference " 6.0.8.";
    }

    revision "2025-09-24" {
        description "Changed the datatype for ether-type attribute";
        reference " 6.0.7.";
    }

    revision "2025-08-26" {
        description "Added new CLI commands for PFC and ECN monitoring";
        reference " 6.0.6.";
    }

    revision "2025-08-22" {
        description "Changed error disable type from bits to enum";
        reference " 6.0.5.";
    }

    revision "2025-08-01" {
        description "Added platform checks for DC L3 subinterfaces";
        reference " 6.0.4.";
    }

    revision "2025-07-22" {
        description "Limit increased for link-debounce-time cmd";
        reference " 6.0.3.";
    }

    revision "2025-06-27" {
        description "New cmd added - l2protocol all learn-disable";
        reference " 6.0.2.";
    }

    revision "2025-06-25" {
        description "Updated datatype 'IF_ERRDISABLE_STATE_T 'values";
        reference " 6.0.1.";
    }

    revision "2025-06-22" {
        description "Compilation fix missing flag in import from";
        reference " 6.0.0.";
    }

    revision "2025-06-03" {
        description "Added port dfe and unreliable-los support";
        reference " 5.0.3.";
    }

    revision "2025-05-22" {
        description "Added dependency in tunnel container";
        reference " 5.0.2.";
    }

    revision "2025-04-15" {
        description "Changes in load-interval, added a skip-validation";
        reference " 5.0.1.";
    }

    revision "2025-03-28" {
        description "Added mode for clear commands";
        reference " 5.0.0.";
    }

    revision "2025-03-20" {
        description "Added when tags for encapsulation-type dot1q and untagged";
        reference " 0.23.14.";
    }

    revision "2025-03-17" {
        description "Revert of EFM flag for l2pt efm CLI";
        reference " 0.23.13.";
    }

    revision "2025-02-21" {
        description "Removed hidden-cli tag from 6.6.1 and allowed debounce-time from 0";
        reference " 0.23.12.";
    }

    revision "2025-02-03" {
        description "Added when tag to clear L2CP state from interface configuration for IDL interfaces";
        reference " 0.23.11.";
    }

    revision "2024-12-22" {
        description "Added when tag to clear the storm-control configs from Db on mapping the mlag on po";
        reference " 0.23.9.";
    }

    revision "2024-12-03" {
        description "Removed llf-enable attr from subinterface to access-if";
        reference " 0.23.8.";
    }

    revision "2024-11-18" {
        description "Getapi implementation for show errdisable details";
        reference " 0.23.6.";
    }

    revision "2024-11-12" {
        description "Support for Link-loss Forwarding";
        reference " 0.23.7.";
    }

    revision "2024-11-08" {
        description "Added support for sub-interface translation to prio-tag, range will be 0-4094 for translation";
        reference " 0.23.5.";
    }

    revision "2024-10-29" {
        description "Add subtypes for global mtu configuration";
        reference " 0.23.4.";
    }

    revision "2024-10-17" {
        description "Added missing interface types for IF_HW_TYPE_T";
        reference " 0.23.3.";
    }

    revision "2024-10-03" {
        description "Added support to 400G and 200G in interface negotiated-port-speed";
        reference " 0.23.2.";
    }

    revision "2024-09-19" {
        description "Modified cli helpstring for mac ageing mode";
        reference " 0.22.4.";
    }

    revision "2024-09-04" {
        description "CL108 FEC config support";
        reference " 0.23.1.";
    }

    revision "2024-09-03" {
        description "Added link-scan-timer support";
        reference " 0.23.0.";
    }

    revision "2024-09-02" {
        description "Fix global l2protocol vlan-d parameter after 0.22.1 change and move L2C type when tag to tunnel-vlan attribute";
        reference " 0.22.6.";
    }

    revision "2024-08-29" {
        description "Added HW_SWFDR for L2C type when tag ";
        reference " 0.22.5.";
    }

    revision "2024-08-21" {
        description "CLI implementation mac-ageing";
        reference " 0.22.4.";
    }

    revision "2024-08-20" {
        description "Added global mtu configuration support";
        reference " 0.22.3.";
    }

    revision "2024-08-19" {
        description "Adding support for configure global load-interval global. Interface level configuration has priority.";
        reference " 0.22.2.";
    }

    revision "2024-08-16" {
        description "Added the range for vlan-id and when tag under l2protocol";
        reference " 0.22.1.";
    }

    revision "2024-08-12" {
        description "Added global l2protocol configuration";
        reference " 0.22.0.";
    }

    revision "2024-08-09" {
        description "Help string change for disable-egr-pcp attribute";
        reference " 0.21.1.";
    }

    revision "2024-08-07" {
        description "Support for egress pcp disable";
        reference " 0.21.0.";
    }

    revision "2024-07-26" {
        description "Make previous revision tag consistent";
        reference " 0.20.19.";
    }

    revision "2024-07-25" {
        description "Added UCMP CLI option";
        reference " 0.20.18.";
    }

    revision "2024-07-19" {
        description "Fix storm-control and hardware-profile filter dependency in Q2 boards";
        reference " 0.20.17.";
    }

    revision "2024-06-27" {
        description "Changed xPathExpr in tunnel-config";
        reference " 0.20.16.";
    }

    revision "2024-06-18" {
        description "Added BVI element in hardware type datatype";
        reference " 0.20.15.";
    }

    revision "2024-06-12" {
        description "Added platform Clis checks for switchport protected CLI";
        reference " 0.20.14.";
    }

    revision "2024-05-24" {
        description "Removing restriction for split-horizon commands for DNX";
        reference " 0.20.13.";
    }

    revision "2024-04-15" {
        description "Updated the help string for protected-port";
        reference " 0.20.12.";
    }

    revision "2024-04-02" {
        description "Removed when tag for forward-err-correction attribute";
        reference " 0.20.11.";
    }

    revision "2024-03-27" {
        description "Added limited autonegotiation support";
        reference " 0.20.10.";
    }

    revision "2024-03-21" {
        description "Added skip-dependency-validation flag for raon attributes";
        reference " 0.20.9.";
    }

    revision "2024-03-04" {
        description "Added mode for clear interface counter command";
        reference " 0.20.8.";
    }

    revision "2024-02-27" {
        description "Added cpu-queue and copp support for Marvell";
        reference " 0.20.7.";
    }

    revision "2024-01-30" {
        description "Removed unused mcec import flag ";
        reference " 0.20.5.";
    }

    revision "2024-01-24" {
        description "Added attr mac-move-priority ";
        reference " 0.20.4.";
    }

    revision "2024-01-22" {
        description "Remove storm-control commands for Tomahawk 4 boards";
        reference " 0.20.3.";
    }

    revision "2024-01-16" {
        description "Changed if-feature flag for storm-control errdisable";
        reference " 0.20.2.";
    }

    revision "2024-01-10" {
        description "Added ethernet counters for Streaming Telemetry";
        reference " 0.20.1.";
    }

    revision "2024-01-09" {
        description "Minor errdisable fix in command description";
        reference " 0.20.0.";
    }

    revision "2024-01-06" {
        description "Added storm-control errdisable";
        reference " 0.20.0.";
    }

    revision "2024-01-05" {
        description "Fixed storm-control errdisable when tags";
        reference " 0.20.6.";
    }

    revision "2023-12-29" {
        description "Corrected the desc for the ip-switchover for cliprependstr ";
        reference " 0.19.5.";
    }

    revision "2023-12-28" {
        description "Changed the ipi-switchover to ip-switchover";
        reference " 0.19.4.";
    }

    revision "2023-12-27" {
        description "Removed raon CLIs dependency on mlag mode";
        reference " 0.19.3.";
    }

    revision "2023-12-26" {
        description "Added static MAC support for bridge-domain";
        reference " 0.23.10.";
    }

    revision "2023-12-20" {
        description "Implementation of raon CLI";
        reference " 0.19.2.";
    }

    revision "2023-12-15" {
        description "Corrected the patch version of ref tag from 29 to 30";
        reference " 0.19.1.";
    }

    revision "2023-11-09" {
        description "Updated datatype for attribute 'eee'";
        reference " 0.19.0.";
    }

    revision "2023-10-26" {
        description "Added dependentObject tag for label-switching over sub-intf encapsulation";
        reference " 0.18.30.";
    }

    revision "2023-10-25" {
        description "Added implicit_delete tag for aclif and service-queue";
        reference " 0.18.29.";
    }

    revision "2023-10-12" {
        description "Added dependentObject tag for aclif";
        reference " 0.18.28.";
    }

    revision "2023-10-11" {
        description "Added dependentObject tag for encapsulation";
        reference " 0.18.27.";
    }

    revision "2023-10-10" {
        description "Change storm-control maximum level to 99%";
        reference " 0.18.26.";
    }

    revision "2023-10-05" {
        description "Adding skip-delete for one of encap when expression";
        reference " 0.18.25.";
    }

    revision "2023-09-03" {
        description "Added a dependentObject tag under rewrite container";
        reference " 0.18.24.";
    }

    revision "2023-08-23" {
        description "Implementation of aclif CLI in interface mode";
        reference " 0.18.23.";
    }

    revision "2023-08-18" {
        description "Added utils_func tag for the attribute dot1q-dot1ad-tpid";
        reference " 0.18.22.";
    }

    revision "2023-06-27" {
        description "Added load-interval command for marvell";
        reference " 0.18.21.";
    }

    revision "2023-06-26" {
        description "Added install condition for protected-port";
        reference " 0.18.20.";
    }

    revision "2023-06-15" {
        description "Remove storm-control commands for Tomahawk 3 boards";
        reference " 0.18.19.";
    }

    revision "2023-06-09" {
        description "updated helpString for outer-vlan-id and inner-vlan-id attribute";
        reference " 0.18.18.";
    }

    revision "2023-05-30" {
        description "Added when tag for disable-snmp-trap-link-status";
        reference " 0.18.17.";
    }

    revision "2023-05-26" {
        description "Added element types for FEC type configuration support";
        reference " 0.18.16.";
    }

    revision "2023-05-13" {
        description "Updated service-queue command dependencies for save and reload";
        reference " 0.18.15.";
    }

    revision "2023-05-12" {
        description "Added CML_MULTI_VALUED for ether-type-value attribute";
        reference " 0.18.14.";
    }

    revision "2023-05-10" {
        description "Modified the trigger to remove bridge-group from po interface when mapped to mlag and members";
        reference " 0.18.13.";
    }

    revision "2023-05-09" {
        description "For bool type attribute error-disable-stp-bpdu-guard updated flag, to avoid invoking unset api.";
        reference " 0.18.12.";
    }

    revision "2023-04-28" {
        description "Removed hardware-profile portmode command ";
        reference " 0.18.11.";
    }

    revision "2023-04-25" {
        description "L2CP changes done w.r.t. CML infra";
        reference " 0.18.10.";
    }

    revision "2023-04-20" {
        description "Added pattern for the attribute ether-type-value to support the hexadecimal values only";
        reference " 0.18.9.";
    }

    revision "2023-04-17" {
        description "Added a trigger to remove bridge-group from po interface when mapped to mlag and members";
        reference " 0.18.8.";
    }

    revision "2023-04-10" {
        description "Added if-feature HAVE_SWFWDR for the attribute disable-multicast";
        reference " 0.18.7.";
    }

    revision "2023-03-14" {
        description "Moved bridge-domain from interfaces hierarchy to network-instance";
        reference " 0.18.6.";
    }

    revision "2023-03-07" {
        description "Added fix for DB sync issue";
        reference " 0.18.5.";
    }

    revision "2023-03-06" {
        description "Blocked hardware-profile portmode command for Q2";
        reference " 0.18.4.";
    }

    revision "2023-03-03" {
        description "Updated split-horizon datatype and attribute name";
        reference " 0.18.3.";
    }

    revision "2023-02-12" {
        description "Updated split-horizon with platform specific flags";
        reference " 0.18.2.";
    }

    revision "2023-02-08" {
        description "Fixed Tibit platform compilation l2cp issue";
        reference " 0.18.1.";
    }

    revision "2023-02-01" {
        description "Restrict l2cp command to L2 interfaces and fix l2cp cfg lag issue";
        reference " 0.18.0.";
    }

    revision "2023-01-20" {
        description "Added enclosing container for port vlan object list";
        reference " 0.17.7.";
    }

    revision "2022-12-14" {
        description "Updated double-tag-vlan-match list key name as encap-type";
        reference " 0.17.6.";
    }

    revision "2022-12-12" {
        description "Reverting port-vlan enclosing container changes";
        reference " 0.17.5.";
    }

    revision "2022-12-09" {
        description "Added enclosing container for port vlan object list";
        reference " 0.17.4.";
    }

    revision "2022-12-07" {
        description "Corrected the spelling mistake for address-table prependstr";
        reference " 0.17.3.";
    }

    revision "2022-12-06" {
        description "cli-sequence if-feature addition";
        reference " 0.17.2.";
    }

    revision "2022-12-05" {
        description "Added interface MACsec capability show";
        reference " 0.17.1.";
    }

    revision "2022-11-29" {
        description "Addressed make cmlgen warnings";
        reference " 0.17.0.";
    }

    revision "2022-11-28" {
        description "Removed ignore snmp genaration tah for error disable reason";
        reference " 0.16.9.";
    }

    revision "2022-11-14" {
        description "Added support for Storm-control by Frame per second";
        reference " 0.16.8.";
    }

    revision "2022-10-11" {
        description "Removed default value for link-flap-max-count and link-flap-timer-interval attrs in err disable cause";
        reference " 0.16.7.";
    }

    revision "2022-09-27" {
        description "Added loopback-detection in err disable cause";
        reference " 0.16.6.";
    }

    revision "2022-08-24" {
        description "Revert changes to fix pre-qat failures";
        reference " 0.16.5.";
    }

    revision "2022-08-18" {
        description "Updated db-trigger for snmp-trap";
        reference " 0.16.4.";
    }

    revision "2022-08-16" {
        description "Added vpls split-horizon support";
        reference " 0.16.3.";
    }

    revision "2022-08-11" {
        description "Modified when expression in extended container";
        reference " 0.16.2.";
    }

    revision "2022-08-10" {
        description "Debug hierarchy change";
        reference " 0.16.1.";
    }

    revision "2022-07-30" {
        description "Updated when expressions in yang";
        reference " 0.16.0.";
    }

    revision "2022-07-20" {
        description "Added trigger to delete switchport-allowed-ether-types when interface configured as aggregator-member";
        reference " 0.15.0.";
    }

    revision "2022-07-11" {
        description "Updated the subinterface encapsulation dependencies correctly";
        reference " 0.14.0.";
    }

    revision "2022-07-04" {
        description "Updated DB Triggers for snmp trap link-status";
        reference " 0.13.1.";
    }

    revision "2022-06-01" {
        description "Updated the yang file with feature";
        reference " 0.13.0.";
    }

    revision "2022-04-14" {
        description "Removed 're-routing' CLI from MEP mode and added in interface mode";
        reference " 0.12.0.";
    }

    revision "2022-02-10" {
        description "Remodelled attribute subif-service-queue for sub-interface";
        reference " 0.11.3.";
    }

    revision "2021-12-22" {
        description "FEC will be reset to auto mode upon speed change";
        reference " 0.11.2.";
    }

    revision "2021-11-16" {
        description "SKU compilation fixes";
        reference " 0.11.1.";
    }

    revision "2021-11-10" {
        description "Moved cross-connect to network-instance module";
        reference " 0.11.0.";
    }

    revision "2021-09-27" {
        description "Updated attribute push-tpid and translate-tpid description, added length and pattern tag";
        reference " 0.10.8.";
    }

    revision "2021-09-24" {
        description "Added notification to remove interfaces from bridge-domain";
        reference " 0.10.7.";
    }

    revision "2021-09-15" {
        description "Added xc-status to show cross connect operational status";
        reference " 0.10.6.";
    }

    revision "2021-09-09" {
        description "Inner VLAN ID for double tag match for subinterface encapsulation is changed from key to mandatory attr and made multi valued";
        reference " 0.10.5.";
    }

    revision "2021-09-01" {
        description "Changed data-types of attribute no-learning and rtp-header from CML_BOOL_T to CML_EMPTY_T.
                       Changed base interface module's switchport attribute name and the datatype from bool to empty.
        ";
        reference " 0.10.4.";
    }

    revision "2021-08-31" {
        description "Added dependents for different types of subinterface encapsulation";
        reference " 0.10.3.";
    }

    revision "2021-08-26" {
        description "Added sniff cli objectAction";
        reference " 0.10.2.";
    }

    revision "2021-08-18" {
        description "Removed default value tag for attribute warning-threshold, recovery-threshold and Updated description";
        reference " 0.10.1.";
    }

    revision "2021-08-13" {
        description "Added Multiple match support for L2 Subinterface";
        reference " 0.10.0.";
    }

    revision "2021-07-29" {
        description "Fix L2cp type options for Software Forwarder Feature";
        reference " 0.8.3.";
    }

    revision "2021-07-06" {
        description "Added link-debounce-time support";
        reference " 0.9.1.";
    }

    revision "2021-06-15" {
        description "Added burst-size option to storm-control CLI";
        reference " 0.9.0.";
    }

    revision "2021-06-10" {
        description "Added new attribute hardware-applied-bcast-value, hardware-applied-mcast-value and hardware-applied-dlf-bcast-value to show hardware applied storm control value in netconf";
        reference " 0.8.2.";
    }

    revision "2021-06-09" {
        description "Added yang support for attribute storm-total-discards";
        reference " 0.8.1.";
    }

    revision "2021-04-08" {
        description "Added notification to remove interfaces from cross connects";
        reference " 0.8.0.";
    }

    revision "2021-03-29" {
        description "Changed container name of hardware-profile to hardware-profile-flexport";
        reference " 0.7.0.";
    }

    revision "2021-03-16" {
        description "Remodelled encapsulation, rewrite and cross-connects for sub-interface remodelling.";
        reference " 0.6.0.";
    }

    revision "2021-03-05" {
        description "Added dot1q-ether-type from mo_ipi-port.xml to make it independent of bridge";
        reference " 0.5.0.";
    }

    revision "2021-03-01" {
        description "Added new atrribute in-bpdu-pkts, in-oamp-pkts, in-bfd-pkts, in-vrrp-rip-dhcp-pkts, in-rsvd-mc-pkts,
                       in-link-local-pkts, in-icmp-pkts, in-icmp-redirect-pkts, in-misc-pkts.
                       Removed attribute last-flap.
                       Added support for changing process type for L2 protocols for an interface.
        ";
        reference " 0.4.0.";
    }

    revision "2021-01-27" {
        description "Changed attribute multicast to disable-multicast and datatype from boolean to empty,
                       Removed attribute enable and added two attribute enable-speed and enable-queue-drops
                       and changed datatype to empty,
                       Removed attribute mac-learn-limit, mdi-crossover, autonegotiation-fault-advertised, autonegotiation-bits-advertised,
                       default-auto-negotiation and auto-negotiation,
                       Added new atrribute last-flapped and auto-ipv6-link-local-address,
                       Changed attribute snmp-trap-link-status to disable-snmp-trap-link-status and datatype from boolean to empty,
                       Added vxlan dependency on tunnel mode attribute.
        ";
        reference " 0.3.0.";
    }

    revision "2020-12-15" {
        description "Change to have data-types in lower case instead of camel case";
        reference " 0.2.0.";
    }

    revision "2020-11-13" {
        description "Initial Version";
        reference " 0.1.0.";
    }



    typedef  ipi_if_extended_rate_unit_t {
        type enumeration {
            enum kbps {
                value 1;
                description "Specifies the unit of kilobits per second";
            }
            enum mbps {
                value 2;
                description "Specifies the unit of megabits per second";
            }
            enum gbps {
                value 3;
                description "Specifies the unit of gigabits per second";
            }
        }
        description "type definition for IPI_IF_EXTENDED_RATE_UNIT_T";
    }

    grouping port-group-speed-map-grouping {
    description
        "Global configuration for Port-group";
        list port-group-speed-map {
            if-feature feature-list:HAVE_DUNE;
            if-feature feature-list:HAVE_HAL;
            if-feature feature-list:NOT_HAVE_SWFWDR;
            key "group-index";
            description
                "Global configuration for Port-group";
            leaf group-index  {
                type  leafref {
                    path  "../config/group-index";
                }
                description "This attribute specifies the port group number";
            } // END of group-index definition.

            container config {
                description
                    "Port-group global configuration data";
                uses port-group-config;
            } // END of config-container definition.
            container state {
                config false;
                description
                    "State data for Port-group";
                uses port-group-config;
            } // END of state-container definition.
        } // End of port-group-speed-map-list
    } // END of port-group-speed-map-grouping definition.
    grouping ipi-interface-extended-config {
        description
            "Grouping for interface-extended module config objects.";
        leaf disable-multicast  {
            if-feature feature-list:HAVE_SWFWDR;
            type  empty;
            description "This attribute is used to set multicast flag for the interface. For a
                        MAC layer protocol, this includes both Group and Functional addresses.
                        Multicast is enabled by default for L3 interfaces. Setting multicast
                        flag for loopback and L2 subinterface is not allowed";
        } // END of disable-multicast definition.

        leaf link-flap-error-disable  {
            if-feature feature-list:HAVE_L2;
            type  empty;
            description "This object specifies whether the interface is enabled for link-flap
                        error-disable or not. If this is '0', then interface is not enabled.
                        Otherwise it is enabled.";
        } // END of link-flap-error-disable definition.

        leaf storm-control-error-disable  {
            if-feature feature-list:HAVE_RATE_LIMIT;
            type  empty;
            description "This attribute specifies whether the interface is enabled for
                        storm-control error-disable or not. If this is not set, then the
                        interface is not enabled. Otherwise it is enabled.";
        } // END of storm-control-error-disable definition.

        leaf mac-move-limit-error-disable  {
            if-feature feature-list:HAVE_L2;
            type  empty;
            description "This object specifies whether the interface is enabled for
                        mac-move-limit error-disable or not. If this is '0', then interface is
                        not enabled. Otherwise it is enabled.";
        } // END of mac-move-limit-error-disable definition.

        leaf mac-move-priority  {
            if-feature feature-list:HAVE_L2;
            type  uint32 {
                 range "1..255"  {
                    description "1..255: Supported range 1 - 255";
                 }
            }
            description "This object used to set the priority of mac-move of an interface";
        } // END of mac-move-priority definition.

        leaf disable-snmp-trap-link-status  {
            type  empty;
            description "This Object is used to set the snmp trap link status in an interface";
        } // END of disable-snmp-trap-link-status definition.

        leaf mau-default-type  {
            if-feature feature-list:HAVE_L2;
            type  ipi-if-types:if_mautype_t;
            description "This attribute is used to set the mau type in an interface";
        } // END of mau-default-type definition.

        leaf debounce-time  {
            type  uint16 {
                 range "0..5000"  {
                    description "0..5000: Supported range 0 - 5000";
                 }
            }
            description "Use this attribute to set the interface debounce timer value";
        } // END of debounce-time definition.

        leaf protected-port  {
            type  ipi-if-types:if_protected_port_type_t;
            default "promiscuous";
            description "Attribute to change port protectedtype value";
        } // END of protected-port definition.

        leaf raon-aodu-port  {
            // when " !ipi-if-extended:extended/config/ucmp-port ";
            if-feature feature-list:HAVE_DUNE;
            type  ipi-if-types:if_raon_aodu_state;
            description "To enable RAON AODU connectivity over physical port.";
        } // END of raon-aodu-port definition.

        leaf ucmp-port  {
            type  ipi-if-types:if_ucmp_state;
            description "To enable UCMP support.";
        } // END of ucmp-port definition.

        leaf revertive-timer  {
            // when " ipi-if-extended:extended/config/enable-non-revertive !='1' ";
            if-feature feature-list:HAVE_DUNE;
            type  uint8 {
                 range "1..255"  {
                    description "1..255: Supported range 1 - 255";
                 }
            }
            default "10";
            description "Use this attribute to set the timer for MC-LAG switchover revertive
                        ty. Default switchover type is revertive 10s.";
        } // END of revertive-timer definition.

        leaf enable-non-revertive  {
            // when " !ipi-if-extended:extended/config/revertive-timer ";
            if-feature feature-list:HAVE_DUNE;
            type  empty;
            description "Use this attribute to set the MC-LAG switchover to non-revertive type.
                        Do not switch back to the initially-active node after failure
                        recovery. Default switchover type is revertive 10s.";
        } // END of enable-non-revertive definition.

    } // END of ipi-interface-extended-config definition.
    grouping ipi-interface-extended-state {
        description
            "Grouping for interface-extended module counters/state parameters.";
        leaf properties  {
            type  ipi-if-types:if_iface_prop_t;
            description "This attribute is used to display interface mapping properties";
        } // END of properties definition.

        leaf original-name  {
            if-feature feature-list:HAVE_INTERFACE_NAME_MAPPING;
            type  string {
                length "1..33";
                pattern "[^?' =,>|]+";
            }
            description "This Object is used to map the interface name";
        } // END of original-name definition.

        leaf mapped-name  {
            type  string {
                length "1..33";
                pattern "[^?' =,>|]+";
            }
            description "This Object is used to set interface mapped name";
        } // END of mapped-name definition.

        leaf if-counter-discontinuity-time  {
            type  yang:timestamp;
            description "The value of sysUpTime on the most recent occasion at which
                        any one or more of this interface's counters suffered a
                        discontinuity.  The relevant counters are the specific
                        instances associated with this interface of any Counter32 or
                        Counter64 object contained in the ifTable or ifXTable.  If
                        no such discontinuities have occurred since the last re-
                        initialization of the local management subsystem, then this
                        object contains a zero value.";
        } // END of if-counter-discontinuity-time definition.

        leaf slot-id  {
            type  uint32;
            description "This object describes slot-id";
        } // END of slot-id definition.

        leaf hardware-type  {
            type  ipi-if-types:if_hw_type_t;
            description "This Object describes hardware type";
        } // END of hardware-type definition.

        leaf storm-total-discards  {
            if-feature feature-list:HAVE_BROADCOM;
            if-feature feature-list:HAVE_RATE_LIMIT;
            if-feature feature-list:NOT_HAVE_DUNE;
            type  yang:counter64;
            description "This object describes total storm-discards";
        } // END of storm-total-discards definition.

        leaf metric  {
            type  int32;
            description "This Object is used to check interface Metric";
        } // END of metric definition.

        leaf if-type  {
            type  ipi-if-types:if_interface_type_t;
            description "This Object describes the interface type L2, L3, TDM";
        } // END of if-type definition.

        leaf trust-state  {
            if-feature feature-list:HAVE_QOS;
            type  ipi-if-types:if_trust_state_t;
            description "This Object describes the trust interface state";
        } // END of trust-state definition.

        leaf monitor-port-grp  {
            if-feature feature-list:HAVE_TFO;
            type  boolean;
            config false;
            description "This attribute describes Monitor Port Groups (MPG) interface";
        } // END of monitor-port-grp definition.

        leaf failover-link-type  {
            if-feature feature-list:HAVE_TFO;
            type  ipi-if-types:if_tfo_link_type_t;
            description "This attribute describes trigger failover(TFO) link type";
        } // END of failover-link-type definition.

        leaf udld-flush-transmitted  {
            if-feature feature-list:HAVE_UDLD;
            type  uint16;
            description "This attribute describes interface udld Flush transmitted";
        } // END of udld-flush-transmitted definition.

        leaf linkup-debounce-interval  {
            type  yang:counter32;
            default "0";
            config false;
            description "This attribute describes linkup debounce time interval";
        } // END of linkup-debounce-interval definition.

        leaf linkdown-debounce-interval  {
            type  yang:counter32;
            default "0";
            config false;
            description "This attribute describes linkdown debounce time interval";
        } // END of linkdown-debounce-interval definition.

        leaf link-debounce-flap-count  {
            type  uint16;
            config false;
            description "This attribute describes number of flap within link debounce time
                        interval";
        } // END of link-debounce-flap-count definition.

        leaf link-debounce-config-status  {
            type  ipi-if-types:if_debounce_running_state;
            config false;
            description "This attribute describes whether link debounce is configured or not";
        } // END of link-debounce-config-status definition.

        leaf link-debounce-last-flap-time  {
            type  yang:date-and-time {
                pattern "\\d{4}-\\d{2}-\\d{2}T\\d{2}:\\d{2}:\\d{2}(\\.\\d+)?(Z|[\\+\\-]\\d{2}:\\d{2})";
                }
                config false;
                description "This attribute describes the last link debounce flap time";
            } // END of link-debounce-last-flap-time definition.

            leaf linkup-debounce-running-status  {
                type  ipi-if-types:if_debounce_running_state;
                config false;
                description "This attribute describes linkup debounce time Running Status";
            } // END of linkup-debounce-running-status definition.

            leaf linkdown-debounce-running-status  {
                type  ipi-if-types:if_debounce_running_state;
                config false;
                description "This attribute describes linkdown debounce time Running Status";
            } // END of linkdown-debounce-running-status definition.

            leaf linkup-debounce-remain-time  {
                type  yang:counter32;
                config false;
                description "This attribute describes the remaining linkup debounce time interval";
            } // END of linkup-debounce-remain-time definition.

            leaf linkdown-debounce-remain-time  {
                type  yang:counter32;
                config false;
                description "This attribute describes the remaining linkdown debounce time interval";
            } // END of linkdown-debounce-remain-time definition.

            leaf debounce-flap-count  {
                type  uint16;
                config false;
                description "This attribute describes number of flap within debounce time interval";
            } // END of debounce-flap-count definition.

            leaf debounce-last-flap-time  {
                type  yang:date-and-time {
                    pattern "\\d{4}-\\d{2}-\\d{2}T\\d{2}:\\d{2}:\\d{2}(\\.\\d+)?(Z|[\\+\\-]\\d{2}:\\d{2})";
                    }
                    config false;
                    description "This attribute describes the last debounce flap time";
                } // END of debounce-last-flap-time definition.

                leaf debounce-remain-time  {
                    type  yang:counter32;
                    config false;
                    description "This attribute describes the remaining  debounce time interval";
                } // END of debounce-remain-time definition.

                leaf debounce-running-status  {
                    type  ipi-if-types:if_debounce_running_state;
                    config false;
                    description "This attribute describes debounce time Running Status";
                } // END of debounce-running-status definition.

                leaf debounce-config-status  {
                    type  ipi-if-types:if_debounce_running_state;
                    config false;
                    description "This attribute describes whether debounce is configured or not";
                } // END of debounce-config-status definition.

                leaf last-flapped  {
                    type  ipi-if-types:if_last_clear_time_t {
                        length "1..1965";
                    }
                    description "This Object describes time when the interface last
                                flapped.";
                } // END of last-flapped definition.

                leaf auto-ipv6-link-local-address  {
                    if-feature feature-list:HAVE_IPV6;
                    type  cml-data-types:cml_ipv6_prefix_t;
                    description "This Object describes the default link local IPv6 address
                                assigned to the interface.";
                } // END of auto-ipv6-link-local-address definition.

                leaf current-load-interval  {
                    if-feature feature-list:HAVE_BROADCOM_OR_HAVE_MARVELL;
                    type  uint16;
                    description "This attribute show the current load-interval period
                                configured on interface. It can use the global value or the interface
                                specific value.";
                } // END of current-load-interval definition.

    } // END of ipi-interface-extended-state definition.
    grouping minimum-bandwidth-config {
        description
            "Grouping for interface minimum-bandwidth configuration";
        leaf rate  {
            // when " ipi-if-extended:extended/minimum-bandwidth/config/rate-unit ";
            type  uint32 {
                 range "1..1000000000"  {
                    description "1..1000000000: Supported range 1 - 1000000000";
                 }
            }
            mandatory true;
            description "Interface minimum bandwidth";
        } // END of rate definition.

        leaf rate-unit  {
            // when " ipi-if-extended:extended/minimum-bandwidth/config/rate ";
            type  ipi_if_extended_rate_unit_t;
            mandatory true;
            description "Use this attribute to set minimum-banwidth rate unit";
        } // END of rate-unit definition.

    } // END of minimum-bandwidth-config definition.
    grouping link-debounce-time-config {
        description
            "Grouping for link-debounce-time.";
        leaf linkup-debounce-time  {
            type  uint32 {
                 range "0..1800000"  {
                    description "0..1800000: Supported range 0 - 1800000";
                 }
            }
            units "milliseconds";
            mandatory true;
            description "Link debounce timer value for down-up transition";
        } // END of linkup-debounce-time definition.

        leaf linkdown-debounce-time  {
            type  uint32 {
                 range "0..1800000"  {
                    description "0..1800000: Supported range 0 - 1800000";
                 }
            }
            units "milliseconds";
            mandatory true;
            description "Link debounce timer value for up-down transition";
        } // END of linkdown-debounce-time definition.

    } // END of link-debounce-time-config definition.
    grouping port-monitor-config {
        description
            "Grouping for Port-monitoring config";
        leaf enable-speed  {
            type  empty;
            description "This object is used to enable port-monitoring for the specified
                        parameters, average speed of the interface";
        } // END of enable-speed definition.

        leaf enable-queue-drops  {
            type  empty;
            description "This object is used to enable queue-drops of the interface";
        } // END of enable-queue-drops definition.

        leaf enable-pfc-mon  {
            type  empty;
            description "This object is used to enable PFC-monitoring of the interface";
        } // END of enable-pfc-mon definition.

        leaf enable-ecn-mon  {
            type  empty;
            description "This object is used to enable PFC-monitoring of the interface";
        } // END of enable-ecn-mon definition.

    } // END of port-monitor-config definition.
    grouping port-monitor-threshold-config {
        description
            "Grouping for Port-monitoring config";
        leaf warning-threshold  {
            type  uint8 {
                 range "1..100"  {
                    description "1..100: Supported range 1 - 100";
                 }
            }
            units "%";
            mandatory true;
            description "This object is used to specify warning threshold for port speed
                        monitor. Warning threshold must be greater than recovery threshold.
                        Default value of warning-threshold is 90.";
        } // END of warning-threshold definition.

        leaf recovery-threshold  {
            // when " ../warning-threshold ";
            type  uint8 {
                 range "1..100"  {
                    description "1..100: Supported range 1 - 100";
                 }
            }
            units "%";
            mandatory true;
            description "This object is used to specify recovery threshold for port speed
                        monitor.Default value of recovery-threshold is 80.";
        } // END of recovery-threshold definition.

    } // END of port-monitor-threshold-config definition.
    grouping capabilities-state {
        description
            "Grouping for physical interface capabilities";
        leaf speed-half-duplex  {
            type  string {
                length "1..1965";
                pattern "[^ ]*";
            }
            description "This Object describes the Interface Speed half duplex capability";
        } // END of speed-half-duplex definition.

        leaf speed-full-duplex  {
            type  string {
                length "1..1965";
                pattern "[^ ]*";
            }
            description "This Object describes the Interface Speed full duplex capability";
        } // END of speed-full-duplex definition.

        leaf pause  {
            type  ipi-if-types:if_raw_string_t {
                length "1..1965";
                pattern "[^ ]*";
            }
            description "This Object describes the Interface pause Capability";
        } // END of pause definition.

        leaf interface-type  {
            type  ipi-if-types:if_raw_string_t {
                length "1..1965";
                pattern "[^ ]*";
            }
            description "This Object describes the Interface Capability";
        } // END of interface-type definition.

        leaf medium  {
            type  ipi-if-types:if_raw_string_t {
                length "1..1965";
                pattern "[^ ]*";
            }
            description "This Object describes the Interface medium Capability";
        } // END of medium definition.

        leaf loopback  {
            type  ipi-if-types:if_raw_string_t {
                length "1..1965";
                pattern "[^ ]*";
            }
            description "This Object describes the Interface loopback Capability";
        } // END of loopback definition.

        leaf flags  {
            type  string {
                length "1..1965";
                pattern "[^?' =,>|]+";
            }
            description "This Object describes the Interface flags Capability";
        } // END of flags definition.

        leaf eee  {
            type  ipi-if-types:if_raw_string_t {
                length "1..1965";
                pattern "[^ ]*";
            }
            description "This Object describes the Interface eee Capability";
        } // END of eee definition.

        leaf fcmap  {
            type  string {
                length "1..1965";
                pattern "[^?' =,>|]+";
            }
            description "This Object describes the Interface fcmap Capability";
        } // END of fcmap definition.

        leaf encapsulation  {
            type  ipi-if-types:if_raw_string_t {
                length "1..1965";
                pattern "[^ ]*";
            }
            description "This Object describes the Interface encapsulation Capability";
        } // END of encapsulation definition.

        leaf fec  {
            type  ipi-if-types:if_raw_string_t {
                length "1..1965";
                pattern "[^?' =>|]+";
            }
            description "This Object describes the Interface fec Capability";
        } // END of fec definition.

        leaf macsec  {
            if-feature feature-list:HAVE_MACSEC;
            type  string {
                length "1..1965";
                pattern "[^?' =,>|]+";
            }
            description "This Object describes the Interface macsec Capability";
        } // END of macsec definition.

    } // END of capabilities-state definition.
    grouping extended-counters-state {
        description
            "Operational state representing extended interface statistics.";
        leaf in-compressed  {
            type  yang:counter64;
            config false;
            description "This Object describes Received compressed.This counter is only
                        applicable to loopback (lo) and management interfaces like eth0";
        } // END of in-compressed definition.

        leaf out-compressed  {
            type  yang:counter64;
            config false;
            description "This Object describes Transmitted compressed.This counter is only
                        applicable to loopback (lo) and management interfaces like eth0";
        } // END of out-compressed definition.

        leaf collisions  {
            type  yang:counter64;
            config false;
            description "This Object describes collisions.This counter is only applicable to
                        loopback (lo) and management interfaces like eth0";
        } // END of collisions definition.

        leaf unicast-rpf-discard  {
            type  yang:counter64;
            config false;
            description "This Object describes unicast RPF discards.This counter is only
                        applicable to loopback (lo) and management interfaces like eth0";
        } // END of unicast-rpf-discard definition.

        leaf in-length-errors  {
            type  yang:counter64;
            config false;
            description "This Object describes Received Length Errors.This counter is only
                        applicable to loopback (lo) and management interfaces like eth0";
        } // END of in-length-errors definition.

        leaf in-oversize-errors  {
            type  yang:counter64;
            config false;
            description "This Object describes Received over Errors.This counter is only
                        applicable to loopback (lo) and management interfaces like eth0";
        } // END of in-oversize-errors definition.

        leaf in-crc-errors  {
            type  yang:counter64;
            config false;
            description "This Object describes Received CRC Errors.This counter is only
                        applicable to loopback (lo) and management interfaces like eth0";
        } // END of in-crc-errors definition.

        leaf in-frame-errors  {
            type  yang:counter64;
            config false;
            description "This Object describes Received Frame Errors.This counter is only
                        applicable to loopback (lo) and management interfaces like eth0";
        } // END of in-frame-errors definition.

        leaf in-fifo-errors  {
            type  yang:counter64;
            config false;
            description "This Object describes Received Fifo Errors.This counter is only
                        applicable to loopback (lo) and management interfaces like eth0";
        } // END of in-fifo-errors definition.

        leaf in-missed-errors  {
            type  yang:counter64;
            config false;
            description "This Object describes Received Missed Errors.This counter is only
                        applicable to loopback (lo) and management interfaces like eth0";
        } // END of in-missed-errors definition.

        leaf out-aborted-errors  {
            type  yang:counter64;
            config false;
            description "This Object describes Transmitted Aborted Errors.This counter is only
                        applicable to loopback (lo) and management interfaces like eth0";
        } // END of out-aborted-errors definition.

        leaf out-carrier-errors  {
            type  yang:counter64;
            config false;
            description "This Object describes Transmitted Carrier Errors.This counter is only
                        applicable to loopback (lo) and management interfaces like eth0";
        } // END of out-carrier-errors definition.

        leaf out-fifo-errors  {
            type  yang:counter64;
            config false;
            description "This Object describes Transmitted Fifo Errors.This counter is only
                        applicable to loopback (lo) and management interfaces like eth0";
        } // END of out-fifo-errors definition.

        leaf out-heartbeat-errors  {
            type  yang:counter64;
            config false;
            description "This Object describes Transmitted Heart beat Errors.This counter is
                        only applicable to loopback (lo) and management interfaces like eth0";
        } // END of out-heartbeat-errors definition.

        leaf out-window-errors  {
            type  yang:counter64;
            config false;
            description "This Object describes Transmitted Window Errors.This counter is only
                        applicable to loopback (lo) and management interfaces like eth0";
        } // END of out-window-errors definition.


        list l2-protocol-pkt-stat {
            if-feature feature-list:HAVE_HAL;
            if-feature feature-list:HAVE_BROADCOM;
            key "l2cp-counter-type";
            config false;
            description
                "This list is used to display statistics for L2 protocol control
                            packets";
            leaf lacp-counters  {
                type  yang:counter64;
                description "This attribute specifies LACP Protocol Packets received on the
                            interface";
            } // END of lacp-counters definition.

            leaf stp-counters  {
                type  yang:counter64;
                description "This attribute specifies stp protocol packets";
            } // END of stp-counters definition.

            leaf lldp-counters  {
                type  yang:counter64;
                description "This attribute specifies lldp protocol Packets received on the
                            interface";
            } // END of lldp-counters definition.

            leaf efmCounters  {
                type  yang:counter64;
                description "This attribute specifies efm protocol Packets received on the
                            interface";
            } // END of efmCounters definition.

            leaf elmi-counters  {
                type  yang:counter64;
                description "This attribute specifies elmi protocol Packets received on the
                            interface";
            } // END of elmi-counters definition.

            leaf dot1x-counters  {
                type  yang:counter64;
                description "This attribute specifies dot1x protocol Packets received on the
                            interface";
            } // END of dot1x-counters definition.

            leaf synce-counters  {
                type  yang:counter64;
                description "This attribute specifies synce protocol Packets received on the
                            interface";
            } // END of synce-counters definition.

            leaf l2cp-counter-type  {
                type  ipi-if-types:if_l2cp_stats_process_t;
                description "This attribute specifies the Protocol Packets received on the
                            interface";
            } // END of l2cp-counter-type definition.

        } // End of l2-protocol-pkt-stat-list
    } // END of extended-counters-state definition.
    grouping extended-ethernet-config {
        description
            "Grouping for extended ethernet module config objects.";
        leaf forward-err-correction  {
            type  ipi-if-types:if_intf_fec_t;
            default "auto";
            description "This Object is used to set forward-error-correction to interface";
        } // END of forward-err-correction definition.

        leaf load-interval  {
            if-feature feature-list:HAVE_BROADCOM_OR_HAVE_MARVELL;
            type  uint16 {
                 range "30..300"  {
                    description "30..300: Supported range 30 - 300";
                 }
            }
            default "300";
            description "This attribute is used to configure load interval period in multiples
                        of 30 seconds";
        } // END of load-interval definition.

    } // END of extended-ethernet-config definition.
    grouping extended-ethernet-state {
        description
            "Grouping for extended ethernet module counters/state parameters.";
        leaf default-duplex-mode  {
            type  uint8;
            description "This object specifies interface default Duplex";
        } // END of default-duplex-mode definition.

        leaf default-speed  {
            type  string {
                length "1..1965";
                pattern "[^?' =,>|]+";
            }
            description "This Object describes interface default link speed, bytes/s";
        } // END of default-speed definition.

    } // END of extended-ethernet-state definition.
    grouping extended-ethernet-counters-state {
        description
            "Operational data representing extended interface ethernet counters";
        leaf in-good-octets  {
            type  yang:counter64;
            config false;
            description "This Object describes Good Octets Received";
        } // END of in-good-octets definition.

        leaf in-bad-octets  {
            type  yang:counter64;
            config false;
            description "This Object describes Bad Octets Received.This counter is currently
                        not supported for Broadcom hardware";
        } // END of in-bad-octets definition.

        leaf mac-transmit-error  {
            type  yang:counter64;
            config false;
            description "This Object describes MAC Transmit Error";
        } // END of mac-transmit-error definition.

        leaf in-good-pkts  {
            type  yang:counter64;
            config false;
            description "This Object describes Good packets Received";
        } // END of in-good-pkts definition.

        leaf in-bad-pkts  {
            type  yang:counter64;
            config false;
            description "This Object describes Bad packets Received";
        } // END of in-bad-pkts definition.

        leaf out-good-octets  {
            type  yang:counter64;
            config false;
            description "This Object describes Good Octets Send";
        } // END of out-good-octets definition.

        leaf out-good-pkts  {
            type  yang:counter64;
            config false;
            description "This Object describes Good Packets Send";
        } // END of out-good-pkts definition.

        leaf excessive-collisions  {
            type  yang:counter64;
            config false;
            description "This Object describes Excessive Collisions";
        } // END of excessive-collisions definition.

        leaf in-unrecognized-mac-control  {
            type  yang:counter64;
            config false;
            description "This Object describes unrecognized mac control received";
        } // END of in-unrecognized-mac-control definition.

        leaf drop-events  {
            type  yang:counter64;
            config false;
            description "This Object describes Drop Events";
        } // END of drop-events definition.

        leaf in-mac-errors  {
            type  yang:counter64;
            config false;
            description "This Object describes MAC Reacived Error";
        } // END of in-mac-errors definition.

        leaf in-dribble-errors  {
            type  yang:counter64;
            config false;
            description "This Object describes Dribble";
        } // END of in-dribble-errors definition.

        leaf collisions-state  {
            type  yang:counter64;
            config false;
            description "collisions State";
        } // END of collisions-state definition.

        leaf late-collisions  {
            type  yang:counter64;
            config false;
            description "This Object describes late Collisions";
        } // END of late-collisions definition.

        leaf deferred-tx  {
            type  yang:counter64;
            config false;
            description "This Object describes Deferred Transmitted";
        } // END of deferred-tx definition.

        leaf mtu-exceed-discards  {
            type  yang:counter64;
            config false;
            description "This Object describes mtu Exceed count";
        } // END of mtu-exceed-discards definition.

        leaf in-jumbo-frames  {
            type  yang:counter64;
            config false;
            description "This Object describes inJumbo count";
        } // END of in-jumbo-frames definition.

        leaf out-jumbo-frames  {
            type  yang:counter64;
            config false;
            description "This Object describes outJumbo count";
        } // END of out-jumbo-frames definition.

        leaf receive-pkt-rate  {
            type  yang:counter64;
            config false;
            description "This Object describes Recived Packet Rate";
        } // END of receive-pkt-rate definition.

        leaf receive-bit-rate  {
            type  yang:counter64;
            config false;
            description "This Object describes Recived BitRate";
        } // END of receive-bit-rate definition.

        leaf send-pkt-rate  {
            type  yang:counter64;
            config false;
            description "This Object describes Transmitted packet Rate";
        } // END of send-pkt-rate definition.

        leaf send-bit-rate  {
            type  yang:counter64;
            config false;
            description "This Object describes Transmitted BitRate";
        } // END of send-bit-rate definition.

    } // END of extended-ethernet-counters-state definition.
    grouping subif-split-horizon-config {
        description
            "Grouping for Sub-interface split-horizon configurations";
        leaf split-horizon-group  {
            // when " !ipi-if-extended:extended/config/protected-port ";
            type  ipi-if-types:if_split_horizon_t;
            description "This attribute is used to configure the split-horizon";
        } // END of split-horizon-group definition.

    } // END of subif-split-horizon-config definition.
    grouping port-group-config {
        description
            "Grouping for port-group speed configurations";
        leaf group-index  {
            type  uint8 {
                 range "1..64"  {
                    description "1..64: Supported range 1 - 64";
                 }
            }
            description "This attribute specifies the port group number";
        } // END of group-index definition.

        leaf group-speed  {
            if-feature feature-list:HAVE_HAL;
            if-feature feature-list:NOT_HAVE_SWFWDR;
            type  ipi-if-types:if_port_group_speed_t;
            mandatory true;
            description "This attribute specifies the speed mode of the port.";
        } // END of group-speed definition.

    } // END of port-group-config definition.
    grouping interface-counters-extended {
        description
            "Grouping for Interface-index state details";
        leaf error-disable-reason  {
            type  ipi-if-types:if_errdisable_state_t;
            description "This attribute specifies the event that caused the interface to be
                        error-disabled. If interface is error-disabled because of
                        lag-mismatch, value of this object is 1. If interface is
                        error-disabled because of stp-bpdu-guard, value of this object is 2.
                        If interface is error-disabled because of link-flap, value of this
                        object is 4. If interface is error-disabled because of storm-control,
                        value of this object is 32.";
        } // END of error-disable-reason definition.

    } // END of interface-counters-extended definition.
    grouping link-scan-timer-config {
        description
            "Grouping for link-scan-timer.";
        leaf link-scan-timer  {
            type  uint16 {
                 range "50..1000"  {
                    description "50..1000: Supported range 50 - 1000";
                 }
            }
            description "Link timer value at which device scans its network links to check
                        their status";
        } // END of link-scan-timer definition.

        leaf snmp-lower-layer  {
            type  empty;
            description "Use this attribute to set the lower layer down";
        } // END of snmp-lower-layer definition.

    } // END of link-scan-timer-config definition.
    grouping global-port-interval-config {
        description
            "Grouping for global configuration of port-interval";
        leaf load-interval  {
            if-feature feature-list:HAVE_BROADCOM_OR_HAVE_MARVELL;
            type  uint16 {
                 range "30..300"  {
                    description "30..300: Supported range 30 - 300";
                 }
            }
            default "300";
            description "This attribute is used to configure load interval on all interfaces
                        and its set period in multiples of 30 seconds";
        } // END of load-interval definition.

    } // END of global-port-interval-config definition.
    grouping error-disable-state {
        description
            "Grouping for error-disable state";
        leaf default-link-flap-count  {
            type  uint32;
            description "This attribute specifies allowed flap count to detect link-flap
                        error-disable";
        } // END of default-link-flap-count definition.

        leaf default-link-flap-timer-interval  {
            type  uint32;
            units "seconds";
            description "This attribute specifies the timer interval for link-flap timer";
        } // END of default-link-flap-timer-interval definition.

        leaf default-storm-control-max-count  {
            if-feature feature-list:HAVE_RATE_LIMIT;
            type  uint32;
            description "This attribute specifies allowed threshold hit count to detect
                        storm-control error-disable";
        } // END of default-storm-control-max-count definition.

        leaf default-storm-control-timer-interval  {
            if-feature feature-list:HAVE_RATE_LIMIT;
            type  uint32;
            units "seconds";
            description "This attribute specifies timer interval for storm-control timer";
        } // END of default-storm-control-timer-interval definition.

        leaf link-flap-status  {
            type  ipi-if-types:if_errdis_status_t;
            description "This attribute specifies the link flap status is enabled or disabled";
        } // END of link-flap-status definition.

        leaf storm-control-status  {
            type  ipi-if-types:if_errdis_status_t;
            description "This attribute specifies the link flap status is enabled or disabled";
        } // END of storm-control-status definition.

        leaf lag-mismatch-status  {
            type  ipi-if-types:if_errdis_status_t;
            description "This attribute specifies the link flap status is enabled or disabled";
        } // END of lag-mismatch-status definition.

        leaf stp-bpdu-guard-status  {
            type  ipi-if-types:if_errdis_status_t;
            description "This attribute specifies the link flap status is enabled or disabled";
        } // END of stp-bpdu-guard-status definition.

        leaf mac-move-limit-status  {
            type  ipi-if-types:if_errdis_status_t;
            description "This attribute specifies the link flap status is enabled or disabled";
        } // END of mac-move-limit-status definition.

    } // END of error-disable-state definition.
    grouping error-disable-config {
        description
            "Grouping for error-disable config";
        leaf reason  {
            type  ipi-if-types:if_err_reason_t;
            description "This object is to enable various error-disable reasons like
                        lag-mismatch, stp-bpdu-guard, link-flap and loopback-detection. As the
                        datatype is BITS, 0th bit corresponds to lag-mismatch, 1st bit
                        corresponds to stp-bpdu-guard, 2nd bit corresponds to link-flap";
        } // END of reason definition.

        leaf error-disable-stp-bpdu-guard  {
            type  boolean;
            description "This object is used to configure error disable STP BPDU Guard";
        } // END of error-disable-stp-bpdu-guard definition.

        leaf timeout-interval  {
            if-feature feature-list:HAVE_L2;
            type  uint32 {
                 range "0..1000000"  {
                    description "0..1000000: Supported range 0 - 1000000";
                 }
            }
            default "0";
            description "This object is to configure timeout for error-disable automatic
                        recovery timer";
        } // END of timeout-interval definition.

        leaf link-flap-max-count  {
            // when " ../reason >= '4' ";
            if-feature feature-list:HAVE_L2;
            type  uint32 {
                 range "1..100"  {
                    description "1..100: Supported range 1 - 100";
                 }
            }
            description "This object is to configure allowed flap count to detect link-flap
                        error-disable";
        } // END of link-flap-max-count definition.

        leaf link-flap-timer-interval  {
            // when " ../reason >= '4' ";
            if-feature feature-list:HAVE_L2;
            type  uint32 {
                 range "1..1800"  {
                    description "1..1800: Supported range 1 - 1800";
                 }
            }
            units "seconds";
            description "This object is configure timer interval for link-flap timer";
        } // END of link-flap-timer-interval definition.

        leaf mac-move-limit  {
            // when " ../reason >= '8' ";
            if-feature feature-list:HAVE_L2;
            type  uint32 {
                 range "1..1000"  {
                    description "1..1000: Supported range 1 - 1000";
                 }
            }
            units "seconds";
            default "100";
            description "This object configures threshold for mac movement";
        } // END of mac-move-limit definition.

        leaf storm-control-max-count  {
            // when " ../reason >= '32' ";
            if-feature feature-list:HAVE_RATE_LIMIT;
            type  uint32 {
                 range "1..100"  {
                    description "1..100: Supported range 1 - 100";
                 }
            }
            description "This attribute is to configure allowed threshold hit count to detect
                        storm-control error-disable";
        } // END of storm-control-max-count definition.

        leaf storm-control-timer-interval  {
            // when " ../reason >= '32' ";
            if-feature feature-list:HAVE_RATE_LIMIT;
            type  uint32 {
                 range "1..1800"  {
                    description "1..1800: Supported range 1 - 1800";
                 }
            }
            units "seconds";
            description "This attribute is configure timer interval for storm-control timer";
        } // END of storm-control-timer-interval definition.

    } // END of error-disable-config definition.
    grouping switchport-allowed-ether-types-config {
        description
            "Grouping for switchport-allowed-ether-types config data";
        leaf arp  {
            type  boolean;
            description "This attribute is used to allow ARP traffic";
        } // END of arp definition.

        leaf ipv4  {
            type  boolean;
            description "This attribute is used to allow IPv4 traffic";
        } // END of ipv4 definition.

        leaf ipv6  {
            type  boolean;
            description "This attribute is used to allow IPv6 traffic";
        } // END of ipv6 definition.

        leaf mpls  {
            type  boolean;
            description "This attribute is used to allow MPLS traffic";
        } // END of mpls definition.

        leaf-list ether-type-value  {
            type  string {
                length "1..1965";
                pattern "0x[0-9a-fA-F]+";
            }
            description "This attribute is used to allow traffic of any Ethertype value (0x600
                        - 0xFFFF)";
        } // END of ether-type-value definition.

        leaf log  {
            type  boolean;
            description "This attribute is used to log unwanted ethertype packets";
        } // END of log definition.

    } // END of switchport-allowed-ether-types-config definition.
    grouping switchport-allowed-ether-types-stats {
        description
            "Grouping for switchport-allowed-ether-types statistics";
        leaf ether-type  {
            type  string {
                length "1..1965";
            }
            description "This attribute is used to specify the ethertype of packet";
        } // END of ether-type definition.

        leaf packets  {
            type  yang:counter64;
            description "This attribute is used to specify Packets count";
        } // END of packets definition.

        leaf bytes  {
            type  yang:counter64;
            description "This attribute is used to specify Bytes count";
        } // END of bytes definition.

    } // END of switchport-allowed-ether-types-stats definition.
    grouping subif-encapsulation-single-tag-config {
        description
            "Grouping for single tagged encapsulation data";
        leaf encapsulation-type  {
            type  ipi-if-types:if_subif_encap_type_t;
            description "This attribute is used to configure the encapsulation type
                        (dot1q/dot1ad).";
        } // END of encapsulation-type definition.

        leaf outer-vlan-id  {
            type  cml-data-types:cml_range_t;
            mandatory true;
            description "This attribute is used to configure the outer VLAN tag";
        } // END of outer-vlan-id definition.

    } // END of subif-encapsulation-single-tag-config definition.
    grouping subif-encapsulation-double-tag-config {
        description
            "Grouping for double tagged encapsulation data";
        leaf encap-type  {
            type  ipi-if-types:if_subif_encap_type_t;
            description "This attribute is used to configure the encapsulation type
                        (dot1q/dot1ad).";
        } // END of encap-type definition.

        leaf outer-vlan-id  {
            type  string {
                length "1..4094";
                pattern "[^?' =>]+";
            }
            description "This attribute is used to configure the outer VLAN tag as a single
                        value alone";
        } // END of outer-vlan-id definition.

        leaf-list inner-vlan-id  {
            type  string {
                length "1..4094";
                pattern "[^?' =,>]+";
            }
            description "This attribute is used to configure the inner VLAN tag as a single
                        value 2-4094 or a range 2-5COMMA10 or 2-5COMMA7-19";
        } // END of inner-vlan-id definition.

    } // END of subif-encapsulation-double-tag-config definition.
    grouping subif-encapsulation-single-tag-top {
        description
            "Top level groupig for single tagged encapsulations";
        container single-tag-vlan-matches {
            description
                "Container for VLAN service matches for single tagged";

            list single-tag-vlan-match {
            // when " ../single-tag-vlan-match/config/outer-vlan-id ";
                key "encapsulation-type";
                description
                    "Single tagged VLAN service match configuration";
                leaf encapsulation-type  {
                    type  leafref {
                        path  "../config/encapsulation-type";
                    }
                    description "This attribute is used to configure the encapsulation
                                type(dot1q/dot1ad).";
                } // END of encapsulation-type definition.

                container config {
                    description
                        "Configuration data for single tagged encapsulation";
                    uses subif-encapsulation-single-tag-config;
                } // END of config-container definition.
                container state {
                    config false;
                    description
                        "Operational state data for dot1q and dot1ad encapsulation";
                    uses subif-encapsulation-single-tag-config;
                } // END of state-container definition.
            } // End of single-tag-vlan-match-list
        } // END of single-tag-vlan-matches-container definition.
    } // END of subif-encapsulation-single-tag-top definition.
    grouping subif-service-queue-config {
        description
            "Configuration data for service queue";
        leaf subif-service-queue  {
            type  ipi-if-types:if_subif_sevice_queue_t;
            description "This attribute specifies the sub interface queue type";
        } // END of subif-service-queue definition.

    } // END of subif-service-queue-config definition.
    grouping aclif-interface-config {
        description
            "Configuration data for interface config";
        leaf aclif-type  {
            type  ipi-if-types:if_aclif_type_t;
            description "Use this attribute to set the Hardware timestamp";
        } // END of aclif-type definition.

    } // END of aclif-interface-config definition.
    grouping subif-encapsulation-double-tag-top {
        description
            "Top level groupig for double tagged encapsulations";
        container double-tag-vlan-matches {
            description
                "Container for VLAN service matches for double tagged";

            list double-tag-vlan-match {
            // when " ../double-tag-vlan-match/config/inner-vlan-id ";
                key "encap-type outer-vlan-id";
                description
                    "Double tagged VLAN service match configuration";
                leaf encap-type  {
                    type  leafref {
                        path  "../config/encap-type";
                    }
                    description "This attribute is used to configure the encapsulation type
                                (dot1q/dot1ad).";
                } // END of encap-type definition.

                leaf outer-vlan-id  {
                    type  leafref {
                        path  "../config/outer-vlan-id";
                    }
                    description "This attribute is used to configure the outer VLAN tag as a single
                                value alone";
                } // END of outer-vlan-id definition.

                container config {
                    description
                        "Configuration data for double tagged encapsulation";
                    uses subif-encapsulation-double-tag-config;
                } // END of config-container definition.
                container state {
                    config false;
                    description
                        "Operational state data for double tagged encapsulation";
                    uses subif-encapsulation-double-tag-config;
                } // END of state-container definition.
            } // End of double-tag-vlan-match-list
        } // END of double-tag-vlan-matches-container definition.
    } // END of subif-encapsulation-double-tag-top definition.
    grouping native-layer2-encapsulation-config {
        description
            "Grouping for default/untagged encapsulation data";
        leaf encap-default  {
            type  empty;
            description "Use this attribute to configure encapsulation as default";
        } // END of encap-default definition.

        leaf encap-untagged  {
            type  empty;
            description "Use this attribute to configure encapsulation as untagged";
        } // END of encap-untagged definition.

    } // END of native-layer2-encapsulation-config definition.
    grouping subif-rewrite-egress-config {
        description
            "Grouping for attributes that preserve bits in egress";
        leaf disable-egr-pcp  {
            if-feature feature-list:HAVE_DNX;
            type  empty;
            description "This attribute is used to preserve cos-dei bits at egress";
        } // END of disable-egr-pcp definition.

    } // END of subif-rewrite-egress-config definition.
    grouping subif-rewrite-config {
        description
            "Grouping for dot1q and dot1ad encapsulation data";
        leaf vlan-action  {
            // when " ../enable-pop or ../push-tpid or ../dot1q-dot1ad-tpid ";
            type  ipi-if-types:if_subif_l2_vlan_actiontype_t;
            mandatory true;
            description "This object is used to configure the rewrite action to push, pop or
                        translate the outer VLAN-id.
                        To change the rewrite config, delete and recreate the entire rewrite
                        config.";
        } // END of vlan-action definition.

        choice vlan-action-type {
            description
                "Vlan Action Types";
            case pop {

                description
                    "Pop the outer and inner vid";

                leaf enable-pop  {
                    // when " ../vlan-action='pop' ";
                    type  ipi-if-types:if_subif_rewrite_pop_type_t;
                    mandatory true;
                    description "This attribute is used to configure pop outer and inner tag.
                                To change the rewrite config, delete and recreate the entire rewrite
                                config.";
                } // END of enable-pop definition.

            }
            case push {

                description
                    "Push the outer and inner vid for a tpid";

                leaf push-tpid  {
                    // when " ../vlan-action='push' and ../push-outer-vlan-id ";
                    type  ipi-if-types:cml_outer_tpid_type_t;
                    mandatory true;
                    description "This attribute is used to configure the tpid value for the interface
                                in the format 0xhhhh. Currently supported values are 0x8100 or 0x88a8
                                or 0x9100 or 0x9200.To change the rewrite config, delete and recreate
                                the entire rewrite config.";
                } // END of push-tpid definition.

                leaf push-outer-vlan-id  {
                    // when " ../vlan-action='push' and ../push-tpid ";
                    type  uint16 {
                         range "1..4094"  {
                            description "1..4094: Supported range 1 - 4094";
                         }
                    }
                    mandatory true;
                    description "This Object is used to configure outer VLAN ID range for rewrite.
                                To change the rewrite config, delete and recreate the entire rewrite
                                config.";
                } // END of push-outer-vlan-id definition.

                leaf push-inner-vlan-id  {
                    type  uint16 {
                         range "1..4094"  {
                            description "1..4094: Supported range 1 - 4094";
                         }
                    }
                    description "This Object is used to configure the inner VLAN ID for rewrite.
                                To change the rewrite config, delete and recreate the entire rewrite
                                config.";
                } // END of push-inner-vlan-id definition.

            }
            case translate {

                description
                    "Translate the outer vid for a tpid";

                leaf rewrite-translate-action  {
                    type  ipi-if-types:if_subif_l2_rewrite_actiontype_t;
                    mandatory true;
                    description "This object is used to configure the rewrite translate action the
                                outer VLAN-id.
                                To change the rewrite config, delete and recreate the entire rewrite
                                config.";
                } // END of rewrite-translate-action definition.

                leaf dot1q-dot1ad-tpid  {
                    // when " ../vlan-action='translate' and ../outer-vlan-id ";
                    type  ipi-if-types:cml_outer_tpid_type_t;
                    mandatory true;
                    description "This Object is used to configure outer VLAN ID range for rewrite.
                                To change the rewrite config, delete and recreate the entire rewrite
                                config.";
                } // END of dot1q-dot1ad-tpid definition.

                leaf outer-vlan-id  {
                    // when " ../vlan-action='translate' and ../dot1q-dot1ad-tpid ";
                    type  uint16 {
                         range "0..4094"  {
                            description "0..4094: Supported range 0 - 4094";
                         }
                    }
                    mandatory true;
                    description "This Object is used to configure VLAN ID range for rewrite.
                                To change the rewrite config, delete and recreate the entire rewrite
                                config.";
                } // END of outer-vlan-id definition.

                leaf i-dot1q-dot1ad-tpid  {
                    // when " ../vlan-action='translate' and ../inner-vlan-id ";
                    type  ipi-if-types:cml_inner_tpid_type_t;
                    mandatory true;
                    description "This Object is used to configure outer VLAN ID range for rewrite.
                                To change the rewrite config, delete and recreate the entire rewrite
                                config.";
                } // END of i-dot1q-dot1ad-tpid definition.

                leaf inner-vlan-id  {
                    // when " ../vlan-action='translate' and ../i-dot1q-dot1ad-tpid ";
                    type  uint16 {
                         range "1..4094"  {
                            description "1..4094: Supported range 1 - 4094";
                         }
                    }
                    mandatory true;
                    description "This Object is used to configure VLAN ID range for rewrite.
                                To change the rewrite config, delete and recreate the entire rewrite
                                config.";
                } // END of inner-vlan-id definition.

            }
        } // END of vlan-action-type-choice definition.
    } // END of subif-rewrite-config definition.
    grouping l2cp-config-global {
        description
            "Grouping for Layer2 Control Protocol configurations";
        leaf l2cp-type  {
            type  ipi-if-types:if_l2cp_t;
            description "This attribute is used to configure the layer2 control-protocol type";
        } // END of l2cp-type definition.

        leaf tunnel-vlan  {
            if-feature feature-list:HAVE_SWFWDR;
            type  int32 {
                 range "2..4094"  {
                    description "2..4094: Supported range 2 - 4094";
                 }
            }
            description "This attribute is used to configure the layer2 control-protocol type
                        tunnel VLAN";
        } // END of tunnel-vlan definition.

        leaf protocol-process  {
            type  ipi-if-types:if_l2cp_process_t;
            mandatory true;
            description "This attribute is used to change the process of protocol to
                        peer/discard/tunnel";
        } // END of protocol-process definition.

    } // END of l2cp-config-global definition.
    grouping l2cp-config {
        description
            "Grouping for Layer2 Control Protocol configurations";
        leaf l2cp-type  {
            type  ipi-if-types:if_l2cp_t;
            description "This attribute is used to configure the layer2 control-protocol type";
        } // END of l2cp-type definition.

        leaf tunnel-vlan  {
            when " /ipi-interface:interfaces/ipi-interface:interface/ipi-port-vlan:port-vlan/ipi-port-vlan:switched-vlans/ipi-port-vlan:switched-vlan/ipi-port-vlan:config/ipi-port-vlan:interface-mode = 'customer-edge-access' ";
            if-feature feature-list:HAVE_SWFWDR;
            type  int32 {
                 range "2..4094"  {
                    description "2..4094: Supported range 2 - 4094";
                 }
            }
            description "This attribute is used to configure the layer2 control-protocol type
                        tunnel VLAN";
        } // END of tunnel-vlan definition.

        leaf protocol-process  {
            type  ipi-if-types:if_l2cp_process_t;
            mandatory true;
            description "This attribute is used to change the process of protocol to
                        peer/discard/tunnel";
        } // END of protocol-process definition.

    } // END of l2cp-config definition.
    grouping tdm-config {
        description
            "Grouping for TDM interface configurations";
        leaf jitter-buffer  {
            if-feature feature-list:HAVE_TDM_VC;
            type  uint16 {
                 range "1..500"  {
                    description "1..500: Supported range 1 - 500";
                 }
            }
            default "500";
            description "This attribute is used to configure jitter-buffer-size";
        } // END of jitter-buffer definition.

        leaf payload-bytes  {
            if-feature feature-list:HAVE_TDM_VC;
            type  uint32 {
                 range "0..32768"  {
                    description "0..32768: Supported range 0 - 32768";
                 }
            }
            default "0";
            description "This attribute is used to configure tdm payload-bytes";
        } // END of payload-bytes definition.

        leaf rtp-header  {
            if-feature feature-list:HAVE_TDM_VC;
            type  empty;
            description "This attribute is used to configure rtp-header";
        } // END of rtp-header definition.

    } // END of tdm-config definition.
    grouping tdm-error-set-config {
        description
            "Grouping for TDM interface error-set configurations";
        leaf error-type  {
            type  ipi-if-types:if_error_set_type_t;
            description "This attribute is used to configure the error-set type";
        } // END of error-type definition.

        leaf error-period  {
            type  uint32 {
                 range "2000..10000"  {
                    description "2000..10000: Supported range 2000 - 10000";
                 }
            }
            mandatory true;
            description "This attribute describes the range for setting the error-set period in
                        millisec";
        } // END of error-period definition.

    } // END of tdm-error-set-config definition.
    grouping tdm-error-clear-config {
        description
            "Grouping for TDM interface error-clear configurations";
        leaf error-clear-type  {
            type  ipi-if-types:if_error_clear_type_t;
            description "This attribute is used to configure the error-clear";
        } // END of error-clear-type definition.

        leaf error-clear-period  {
            type  uint32 {
                 range "2000..10000"  {
                    description "2000..10000: Supported range 2000 - 10000";
                 }
            }
            mandatory true;
            description "This attribute describes the range for setting the error-clear period
                        in millisec";
        } // END of error-clear-period definition.

    } // END of tdm-error-clear-config definition.
    grouping tunnel-config {
        description
            "Grouping for tunnel interface configurations";
        leaf mode  {
            type  ipi-if-types:if_tunnel_mode_t;
            default "vxlan";
            description "This attribute is used to unset the tunnel mode";
        } // END of mode definition.

        leaf src  {
            type  inet:ipv4-address;
            description "This attribute is used to set tunnel source";
        } // END of src definition.

        leaf multicast-interface  {
            if-feature feature-list:HAVE_VXLAN;
            type  string {
                length "1..1965";
                pattern "[^?' =,>|]+";
            }
            description "This attribute is used to configure egress multicast interface for
                        tunnel";
        } // END of multicast-interface definition.

        leaf dst  {
            type  inet:ipv4-address;
            description "This attribute is used to set destination of tunnel packets";
        } // END of dst definition.

        leaf checksum-enable  {
            type  empty;
            description "This attribute is used to enable end to end checksumming of packets";
        } // END of checksum-enable definition.

        leaf tos-byte  {
            type  uint16 {
                 range "0..255"  {
                    description "0..255: Supported range 0 - 255";
                 }
            }
            description "This attribute is used to set type of service byte";
        } // END of tos-byte definition.

        leaf ttl  {
            type  uint16 {
                 range "1..255"  {
                    description "1..255: Supported range 1 - 255";
                 }
            }
            description "This attribute is used to set time to live";
        } // END of ttl definition.

        leaf path-mtu-enable  {
            type  empty;
            description "This attribute is used to enable Path MTU Discovery on tunnel";
        } // END of path-mtu-enable definition.

        leaf dst-mac-address  {
            if-feature feature-list:HAVE_USER_HSL;
            type  string {
                length "1..1965";
                pattern "[^?' =,>|]+";
            }
            description "This attribute is used to set next Hop Destination MAC Address of
                        Tunnel Packets";
        } // END of dst-mac-address definition.

        leaf gre-key  {
            if-feature feature-list:HAVE_GRE_KEY;
            type  ipi-if-types:if_tunnel_key_t;
            description "This attribute is used to set the gre-key for tunnel";
        } // END of gre-key definition.

    } // END of tunnel-config definition.
    grouping protocol-pkt-statistics {
        description
            "Grouping for interface protocol packets statistics";
        leaf in-bgp-pkts  {
            type  yang:counter32;
            description "bgp protocol packets received on the interface";
        } // END of in-bgp-pkts definition.

        leaf in-ospf-pkts  {
            type  yang:counter32;
            description "ospf protocol packets received on the interface";
        } // END of in-ospf-pkts definition.

        leaf in-isis-pkts  {
            type  yang:counter32;
            description "isis protocol packets received on the interface";
        } // END of in-isis-pkts definition.

        leaf in-ldp-rsvp-pkts  {
            type  yang:counter32;
            description "ldp_rsvp protocol packets received on the interface";
        } // END of in-ldp-rsvp-pkts definition.

        leaf in-arp-pkts  {
            type  yang:counter32;
            description "arp protocol packets received on the interface";
        } // END of in-arp-pkts definition.

        leaf in-evpn-pkts  {
            type  yang:counter32;
            description "evpn protocol packets received on the interface";
        } // END of in-evpn-pkts definition.

        leaf in-igmp-pkts  {
            type  yang:counter32;
            description "igmp protocol packets received on the interface";
        } // END of in-igmp-pkts definition.

        leaf in-pim-pkts  {
            type  yang:counter32;
            description "pim protocol packets received on the interface";
        } // END of in-pim-pkts definition.

        leaf in-bpdu-pkts  {
            if-feature feature-list:HAVE_DUNE;
            type  yang:counter32;
            description "bpdu protocol packets received on the interface";
        } // END of in-bpdu-pkts definition.

        leaf in-oamp-pkts  {
            if-feature feature-list:HAVE_DUNE;
            type  yang:counter32;
            description "oamp protocol packets received on the interface";
        } // END of in-oamp-pkts definition.

        leaf in-bfd-pkts  {
            if-feature feature-list:HAVE_DUNE;
            type  yang:counter32;
            description "bfd protocol packets received on the interface";
        } // END of in-bfd-pkts definition.

        leaf in-vrrp-rip-dhcp-pkts  {
            if-feature feature-list:HAVE_DUNE;
            type  yang:counter32;
            description "vrrp-rip-dhcp protocol packets received on the interface";
        } // END of in-vrrp-rip-dhcp-pkts definition.

        leaf in-rsvd-mc-pkts  {
            if-feature feature-list:HAVE_DUNE;
            type  yang:counter32;
            description "rsvd-mc protocol packets received on the interface";
        } // END of in-rsvd-mc-pkts definition.

        leaf in-link-local-pkts  {
            if-feature feature-list:HAVE_DUNE;
            type  yang:counter32;
            description "link-local protocol packets received on the interface";
        } // END of in-link-local-pkts definition.

        leaf in-icmp-pkts  {
            if-feature feature-list:HAVE_DUNE;
            type  yang:counter32;
            description "icmp protocol packets received on the interface";
        } // END of in-icmp-pkts definition.

        leaf in-icmp-redirect-pkts  {
            if-feature feature-list:HAVE_DUNE;
            type  yang:counter32;
            description "icmp-redirect protocol packets received on the interface";
        } // END of in-icmp-redirect-pkts definition.

        leaf in-misc-pkts  {
            if-feature feature-list:HAVE_DUNE;
            type  yang:counter32;
            description "misc protocol packets received on the interface";
        } // END of in-misc-pkts definition.

        leaf in-total-pkts  {
            type  yang:counter32;
            description "total protocol packets received on the interface";
        } // END of in-total-pkts definition.

    } // END of protocol-pkt-statistics definition.
    grouping bandwidth-operational-state {
        description
            "Grouping for Extended Bandwidth operational data";
        leaf current-bandwidth  {
            type  uint64;
            units "kbps";
            description "Current Bandwidth in kbps";
        } // END of current-bandwidth definition.

    } // END of bandwidth-operational-state definition.
    grouping lbg-counters-state {
        description
            "Operational data representing LB counters";
        leaf in-errors  {
            type  yang:counter64;
            description "The number of discard segments received per LBG";
        } // END of in-errors definition.

    } // END of lbg-counters-state definition.
    grouping lb-modem-counters-state {
        description
            "Operational data representing LB modem counters";
        leaf out-segments  {
            type  yang:counter64;
            description "The number of Modem segments transmitted";
        } // END of out-segments definition.

        leaf out-segment-bytes  {
            type  yang:counter64;
            description "The number of Modem bytes transmitted";
        } // END of out-segment-bytes definition.

        leaf in-segments  {
            type  yang:counter64;
            description "The number of Modem Segments received";
        } // END of in-segments definition.

        leaf in-segment-bytes  {
            type  yang:counter64;
            description "The number of Modem bytes received";
        } // END of in-segment-bytes definition.

    } // END of lb-modem-counters-state definition.
    grouping obm-total-count-stats {
        description
            "Grouping for HAL interface OBM drop reason total statistics";
        leaf high-priority-drops  {
            type  yang:counter64;
            description "Packets dropped because of high priority over subscription";
        } // END of high-priority-drops definition.

        leaf low-priority-drops  {
            type  yang:counter64;
            description "Packets dropped because of low priority over subscription";
        } // END of low-priority-drops definition.

        leaf lossless0-drops  {
            type  yang:counter64;
            description "Packets dropped because of Lossless0 over subscription";
        } // END of lossless0-drops definition.

        leaf lossless1-drops  {
            type  yang:counter64;
            description "Packets dropped because of Lossless1 over subscription";
        } // END of lossless1-drops definition.

        leaf total-obm-drops  {
            type  yang:counter64;
            description "Total packets dropped because of over subscription";
        } // END of total-obm-drops definition.

    } // END of obm-total-count-stats definition.
    grouping obm-last-increment-count-stats {
        description
            "Grouping for HAL interface OBM Drop last-incremented statistics";
        leaf high-priority-drops  {
            type  yang:counter64;
            description "Last number of Packets dropped because of high priority over
                        subscription
                        This is Updated at every 5sec interval.";
        } // END of high-priority-drops definition.

        leaf low-priority-drops  {
            type  yang:counter64;
            description "Last number of Packets dropped because of low priority over
                        subscription
                        This is Updated at every 5sec interval.";
        } // END of low-priority-drops definition.

        leaf lossless0-drops  {
            type  yang:counter64;
            description "Last number of Packets dropped because of lossless0 over subscription
                        This is Updated at every 5sec interval.";
        } // END of lossless0-drops definition.

        leaf lossless1-drops  {
            type  yang:counter64;
            description "Last number of Packets dropped because of lossless1 over subscription
                        This is Updated at every 5sec interval.";
        } // END of lossless1-drops definition.

        leaf total-obm-drops  {
            type  yang:counter64;
            description "Total last number of packets dropped because of over subscription
                        This is Updated at every 5sec interval.";
        } // END of total-obm-drops definition.

    } // END of obm-last-increment-count-stats definition.
    grouping obm-last-increment-time-stats {
        description
            "Grouping for obm-OBM Drop statistics last-incremented timestamp";
        leaf high-priority-drops  {
            type  yang:date-and-time {
                pattern "\\d{4}-\\d{2}-\\d{2}T\\d{2}:\\d{2}:\\d{2}(\\.\\d+)?(Z|[\\+\\-]\\d{2}:\\d{2})";
                }
                description "Last increment time of OBM high priority dropped packets.
                            This is Updated at every 5sec interval.";
            } // END of high-priority-drops definition.

            leaf low-priority-drops  {
                type  yang:date-and-time {
                    pattern "\\d{4}-\\d{2}-\\d{2}T\\d{2}:\\d{2}:\\d{2}(\\.\\d+)?(Z|[\\+\\-]\\d{2}:\\d{2})";
                    }
                    description "Last increment time of OBM low priority dropped packets.
                                This is Updated at every 5sec interval.";
                } // END of low-priority-drops definition.

                leaf lossless0-drops  {
                    type  yang:date-and-time {
                        pattern "\\d{4}-\\d{2}-\\d{2}T\\d{2}:\\d{2}:\\d{2}(\\.\\d+)?(Z|[\\+\\-]\\d{2}:\\d{2})";
                        }
                        description "Last increment time of OBM lossless0 dropped packets.
                                    This is Updated at every 5sec interval.";
                    } // END of lossless0-drops definition.

                    leaf lossless1-drops  {
                        type  yang:date-and-time {
                            pattern "\\d{4}-\\d{2}-\\d{2}T\\d{2}:\\d{2}:\\d{2}(\\.\\d+)?(Z|[\\+\\-]\\d{2}:\\d{2})";
                            }
                            description "Last increment time of OBM lossless1 dropped packets.
                                        This is Updated at every 5sec interval.";
                        } // END of lossless1-drops definition.

                        leaf total-obm-drops  {
                            type  yang:date-and-time {
                                pattern "\\d{4}-\\d{2}-\\d{2}T\\d{2}:\\d{2}:\\d{2}(\\.\\d+)?(Z|[\\+\\-]\\d{2}:\\d{2})";
                                }
                                description "Total last increment time of OBM dropped packets.
                                            This is Updated at every 5sec interval.";
                            } // END of total-obm-drops definition.

    } // END of obm-last-increment-time-stats definition.
    grouping error-discard-statistics {
        description
            "Grouping for error_counters and discard_counters";
    } // END of error-discard-statistics definition.
    grouping queue-statistics {
        description
            "Grouping for CPU queue statistics";

        list queue-stats {
            if-feature feature-list:HAVE_HAL;
            if-feature feature-list:HAVE_BROADCOM;
            if-feature feature-list:NOT_HAVE_DUNE;
            key "queue-id";
            config false;
            description
                "CPU cos queue statistics";
            leaf queue-id  {
                type  uint8;
                description "This is a unique number representing each queue in CPU";
            } // END of queue-id definition.

            leaf queue-name  {
                type  string {
                    length "1..1965";
                    pattern "[^?' =,>|]+";
                }
                description "Queue Name corresponding to the Queue Id.";
            } // END of queue-name definition.

            leaf out-pkts  {
                type  yang:counter64;
                description "The number of outbound packets that are transmitted through the queue";
            } // END of out-pkts definition.

            leaf out-octets  {
                type  yang:counter64;
                description "The number of outbound bytes that are transmitted through the queue";
            } // END of out-octets definition.

            leaf out-dropped-pkts  {
                type  yang:counter64;
                description "The number of outbound packets that are dropped in the queue.";
            } // END of out-dropped-pkts definition.

            leaf out-dropped-octets  {
                type  yang:counter64;
                description "The number of outbound bytes that are dropped in the queue";
            } // END of out-dropped-octets definition.

            leaf queue-size-in-octets  {
                type  yang:counter64;
                description "The size of the queue, referred by the  queue Id";
            } // END of queue-size-in-octets definition.

            container cos-rate-stats {
                if-feature feature-list:HAVE_HAL;
                if-feature feature-list:HAVE_BROADCOM;
                if-feature feature-list:NOT_HAVE_DUNE;
                config false;
                description
                    "cpu cosq rate stats";
                leaf tx-pkt-rate  {
                    type  yang:counter32;
                    description "The number of outbound packets transmitted from the corresponding CPU
                                queue.";
                } // END of tx-pkt-rate definition.

                leaf tx-bit-rate  {
                    type  yang:counter32;
                    description "The number of outbound bytes transmitted from the corresponding CPU
                                queue.";
                } // END of tx-bit-rate definition.

                leaf rate-percent  {
                    type  int8;
                    description "Percentage of control packets transmitted in the CPU queue.
                                Value of -1 indicates rate percentage is not applicable.";
                } // END of rate-percent definition.

                leaf last-increment-count  {
                    type  yang:counter64;
                    description "The number of Last Dropped Pkts in the corresponding CPU queue.
                                This is Updated at every 5sec interval.";
                } // END of last-increment-count definition.

                leaf last-increment-time  {
                    type  yang:date-and-time {
                        pattern "\\d{4}-\\d{2}-\\d{2}T\\d{2}:\\d{2}:\\d{2}(\\.\\d+)?(Z|[\\+\\-]\\d{2}:\\d{2})";
                        }
                        description "Last increment time of Tx Dropped Packets in CPU Queue.
                                    This is Updated at every 5sec interval.";
                    } // END of last-increment-time definition.

            } // END of cos-rate-stats-container definition.
        } // End of queue-stats-list
    } // END of queue-statistics definition.
    grouping broadcast-config {
        description
            "Grouping for configurations";
        leaf bcast-value  {
            when " /ipi-interface:interfaces/ipi-interface:interface/ipi-interface:config/ipi-interface:enable-switchport ";
            type  ipi-if-types:if_rate_limit_t;
            mandatory true;
            description "This attribute is used to set the storm control configuration, Set
                        Broadcast Rate Limiting of layer2 Interface";
        } // END of bcast-value definition.

        leaf bcast-rate-limit-format  {
            type  ipi-if-types:if_rate_limit_type;
            mandatory true;
            description "This attribute is used to set the storm control configuration, Set the
                        format for units in kbps|mbps|gbps or level for threshold percentage";
        } // END of bcast-rate-limit-format definition.

        leaf bcast-burst-value  {
            type  uint32;
            mandatory true;
            description "This attribute is used to set the broadcast storm control burst
                        configuration";
        } // END of bcast-burst-value definition.

    } // END of broadcast-config definition.
    grouping broadcast-state {
        description
            "Grouping for  state attributes";
        leaf bcast-discards  {
            if-feature feature-list:HAVE_HAL;
            if-feature feature-list:NOT_HAVE_BROADCOM;
            type  int32;
            config false;
            description "This attribute is used to denote the broadcast Storm Discards";
        } // END of bcast-discards definition.

        leaf hardware-applied-bcast-value  {
            if-feature feature-list:HAVE_BROADCOM;
            if-feature feature-list:HAVE_RATE_LIMIT;
            type  decimal64 {
                 fraction-digits 3;            }
            config false;
            description "This attribute is used to denote the hardware applied storm control
                        broadcast value when rate format is not set as level";
        } // END of hardware-applied-bcast-value definition.

    } // END of broadcast-state definition.
    grouping multicast-config {
        description
            "Grouping for configurations";
        leaf mcast-value  {
            when " /ipi-interface:interfaces/ipi-interface:interface/ipi-interface:config/ipi-interface:enable-switchport ";
            type  ipi-if-types:if_rate_limit_t;
            mandatory true;
            description "This attribute is used to set the storm control configuration,Set
                        Multicast Rate Limiting of layer2 Interface";
        } // END of mcast-value definition.

        leaf mcast-rate-limit-format  {
            type  ipi-if-types:if_rate_limit_type;
            mandatory true;
            description "This attribute is used to set the storm control configuration, Set the
                        format for units in kbps|mbps|gbps or level for threshold percentage";
        } // END of mcast-rate-limit-format definition.

        leaf mcast-burst-value  {
            type  uint32;
            mandatory true;
            description "This attribute is used to set the multicast storm control burst
                        configuration";
        } // END of mcast-burst-value definition.

    } // END of multicast-config definition.
    grouping multicast-state {
        description
            "Grouping for  state attributes";
        leaf mcast-discards  {
            if-feature feature-list:HAVE_HAL;
            if-feature feature-list:NOT_HAVE_BROADCOM;
            type  int32;
            config false;
            description "This attribute is used to denote Multicast Storm Discards";
        } // END of mcast-discards definition.

        leaf hardware-applied-mcast-value  {
            if-feature feature-list:HAVE_BROADCOM;
            if-feature feature-list:HAVE_RATE_LIMIT;
            type  decimal64 {
                 fraction-digits 3;            }
            config false;
            description "This attribute is used to denote the hardware applied storm control
                        multicast value when rate format is not set as level";
        } // END of hardware-applied-mcast-value definition.

    } // END of multicast-state definition.
    grouping dlf-broadcast-config {
        description
            "Grouping for configurations";
        leaf dlf-bcast-value  {
            when " /ipi-interface:interfaces/ipi-interface:interface/ipi-interface:config/ipi-interface:enable-switchport ";
            type  ipi-if-types:if_rate_limit_t;
            mandatory true;
            description "This attribute is used to set the storm control configuration,Set DLF
                        Broadcast Rate Limiting of layer2 Interface";
        } // END of dlf-bcast-value definition.

        leaf dlf-bcast-rate-limit-format  {
            type  ipi-if-types:if_rate_limit_type;
            mandatory true;
            description "This attribute is used to set the storm control configuration, Set the
                        format for units in kbps|mbps|gbps or level for threshold percentage";
        } // END of dlf-bcast-rate-limit-format definition.

        leaf dlf-bcast-burst-value  {
            type  uint32;
            mandatory true;
            description "This attribute is used to set the dlf storm control burst
                        configuration";
        } // END of dlf-bcast-burst-value definition.

    } // END of dlf-broadcast-config definition.
    grouping dlf-broadcast-state {
        description
            "Grouping for  state attributes";
        leaf dlf-bcast-discards  {
            if-feature feature-list:HAVE_HAL;
            if-feature feature-list:NOT_HAVE_BROADCOM;
            type  uint32;
            config false;
            description "This attribute is used to denote the DLF Bcast Storm Discards";
        } // END of dlf-bcast-discards definition.

        leaf hardware-applied-dlf-bcast-value  {
            if-feature feature-list:HAVE_BROADCOM;
            if-feature feature-list:HAVE_RATE_LIMIT;
            type  decimal64 {
                 fraction-digits 3;            }
            config false;
            description "This attribute is used to denote the hardware applied storm control
                        dlf broadcast value when rate format is not set as level";
        } // END of hardware-applied-dlf-bcast-value definition.

    } // END of dlf-broadcast-state definition.
    grouping if-arbiter-config {
        description
            "Grouping for interface Arbiter global configuration";
        leaf if-arbiter  {
            type  uint32 {
                 range "1..65535"  {
                    description "1..65535: Supported range 1 - 65535";
                 }
            }
            default "20";
            description "Use this attribute to discover new interfaces recently added to the
                        kernel and add them to the OcNOS database.";
        } // END of if-arbiter definition.

    } // END of if-arbiter-config definition.
    grouping if-global-config {
        description
            "Grouping for interface global configuration";
        leaf if-type  {
            type  ipi-if-types:if_global_mtu_if_type_t;
            description "HW interface type";
        } // END of if-type definition.

        leaf mtu  {
            type  uint32 {
                 range "64..65535"  {
                    description "64..65535:Feature : HAVE_DNX or HAVE_MARVELL Supported range 64 -
                            65535Not Feature : HAVE_DUNE,HAVE_MARVELL  Supported range 64 -
                            65535Not Feature : HAVE_DNX,HAVE_MARVELL  Supported range 64 - 65535";
                 }
            }
            mandatory true;
            description "This attribute is used to set mtu value globally.The size of the
                        largest packet which can be sent/received on the interface, specified
                        in octets. For interfaces that are used for transmitting network
                        datagrams, this is the size of the largest network datagram that can
                        be sent on the interface.";
        } // END of mtu definition.

    } // END of if-global-config definition.
    grouping l2-protocol-config {
        description
            "Grouping for l2protocol learn-disable";
        leaf protocol-type  {
            type  ipi-if-types:if_l2_proto_type;
            description "Use this attribute to set the protocol type";
        } // END of protocol-type definition.

    } // END of l2-protocol-config definition.
    grouping mac-ageing-config {
        description
            "Top level grouping for mac ageing config";
        leaf hit-based-ageing  {
            if-feature feature-list:NOT_HAVE_DUNE;
            type  ipi-if-types:cml_mac_ageing_t;
            description "Use this attribute to set the mac ageing src or dst-src";
        } // END of hit-based-ageing definition.

    } // END of mac-ageing-config definition.

    grouping  extended-grouping {
    description
        "Top-level container for extended interface module";
    container extended {
        description
            "Top-level container for extended interface module";

        list l2-control-protocol {
            if-feature feature-list:HAVE_L2;
            key "l2cp-type";
            description
                "Layer2 Control Protocol";
            leaf l2cp-type  {
                type  leafref {
                    path  "../config/l2cp-type";
                }
                description "This attribute is used to configure the layer2 control-protocol type";
            } // END of l2cp-type definition.

            container config {
                description
                    "Configuration data for Layer2 Control Protocol";
                uses l2cp-config;
            } // END of config-container definition.
            container state {
                config false;
                description
                    "Operational data for Layer2 Control Protocol";
                uses l2cp-config;
            } // END of state-container definition.
        } // End of l2-control-protocol-list
        container config {
            description
                "Configuration data for extended interface module";
            uses ipi-interface-extended-config;
        } // END of config-container definition.
        container state {
            config false;
            description
                "Counters/State data for extended interface module";
            uses ipi-interface-extended-config;
            uses ipi-interface-extended-state;
        } // END of state-container definition.
        container bandwidth-management {
            description
                "Container for bandwidth management";
            container config {
                description
                    "Configuration data for bandwidth-management";
                leaf enable-re-routing  {
                    type  empty;
                    description "Enable re-routing when the bandwidth crosses down the minimum
                                bandwidth";
                } // END of enable-re-routing definition.

            } // END of config-container definition.
        } // END of bandwidth-management-container definition.
        container port-monitor {
            description
                "Container for Port-monitoring";
            container config {
                description
                    "Container for Port-monitor config";
                uses port-monitor-config;
            } // END of config-container definition.
            container state {
                config false;
                description
                    "State data for Port-monitoring";
                uses port-monitor-config;
            } // END of state-container definition.
            container port-monitor-threshold {
                description
                    "Container for Port-monitoring-threshold";
                container config {
                    presence "Port-monitor threshold config";
                    description
                        "Container for Port-monitor threshold config";
                    uses port-monitor-threshold-config;
                } // END of config-container definition.
                container state {
                    config false;
                    description
                        "State data for Port-monitoring";
                    uses port-monitor-threshold-config;
                } // END of state-container definition.
            } // END of port-monitor-threshold-container definition.
        } // END of port-monitor-container definition.
        container capabilities {
            if-feature feature-list:HAVE_HAL;
            config false;
            description
                "Container for physical interface capabilities";
            container state {
                config false;
                description
                    "Container for physical interface capabilities state";
                uses capabilities-state;
            } // END of state-container definition.
        } // END of capabilities-container definition.
        container service-queue {
            if-feature feature-list:HAVE_SUBINTERFACE;
            description
                "configure subinterface queue type";
            container config {
                description
                    "Configuration data for subinterface queue type";
                uses subif-service-queue-config;
            } // END of config-container definition.
            container state {
                config false;
                description
                    "Operational state data for subinterface queue type";
                uses subif-service-queue-config;
            } // END of state-container definition.
        } // END of service-queue-container definition.
        container aclif {
            description
                "Configure interface/subinterface for aclif failover and no-failover";
            container config {
                description
                    "Configuration data for interface/subinterface aclif";
                uses aclif-interface-config;
            } // END of config-container definition.
            container state {
                config false;
                description
                    "Operational state data for interface/subinterface for aclif";
                uses aclif-interface-config;
            } // END of state-container definition.
        } // END of aclif-container definition.
        container subinterface-encapsulation {
            if-feature feature-list:HAVE_SUBINTERFACE;
            description
                "Container for dot1q and dot1ad encapsulation data";
            container config {
                description
                    "Configuration data for native layer 2 encapsulations";
                uses native-layer2-encapsulation-config;
            } // END of config-container definition.
            container state {
                config false;
                description
                    "Operational state data for native layer 2 encapsulations";
                uses native-layer2-encapsulation-config;
            } // END of state-container definition.
            container rewrite {
                description
                    "Container for rewrite action to push or translate the outer VLAN-id";
                container config {
                    when " /ipi-interface:interfaces/ipi-interface:interface/ipi-interface:config/ipi-interface:enable-switchport and (/ipi-interface:interfaces/ipi-interface:interface/ipi-if-extended:extended/ipi-if-extended:subinterface-encapsulation/ipi-if-extended:single-tag-vlan-matches/ipi-if-extended:single-tag-vlan-match or /ipi-interface:interfaces/ipi-interface:interface/ipi-if-extended:extended/ipi-if-extended:subinterface-encapsulation/ipi-if-extended:double-tag-vlan-matches/ipi-if-extended:double-tag-vlan-match or /ipi-interface:interfaces/ipi-interface:interface/ipi-if-extended:extended/ipi-if-extended:subinterface-encapsulation/ipi-if-extended:config/ipi-if-extended:encap-default or /ipi-interface:interfaces/ipi-interface:interface/ipi-if-extended:extended/ipi-if-extended:subinterface-encapsulation/ipi-if-extended:config/ipi-if-extended:encap-untagged) ";
                    presence "Enable rewrite action to push or translate the outer VLAN-id";
                    description
                        "Configuration data for rewrite action to push or translate the outer
                                VLAN-id";
                    uses subif-rewrite-config;
                } // END of config-container definition.
                container state {
                    config false;
                    description
                        "Operational state data for rewrite action to push or translate the
                                outer VLAN-id";
                    uses subif-rewrite-config;
                } // END of state-container definition.
                container egress {
                    if-feature feature-list:HAVE_SUBINTERFACE;
                    if-feature feature-list:HAVE_DNX;
                    description
                        "Container for rewrite egress";
                    container config {
                        description
                            "Operational config data for rewrite egress";
                        uses subif-rewrite-egress-config;
                    } // END of config-container definition.
                    container state {
                        config false;
                        description
                            "Operational state data for rewrite egress";
                        uses subif-rewrite-egress-config;
                    } // END of state-container definition.
                } // END of egress-container definition.
            } // END of rewrite-container definition.
            uses subif-encapsulation-single-tag-top;
            uses subif-encapsulation-double-tag-top;
        } // END of subinterface-encapsulation-container definition.
        container subinterface-split-horizon {
            if-feature feature-list:HAVE_SUBINTERFACE;
            description
                "Global container for split-horizon in subinterface";
            container config {
                description
                    "Global configuration for split-horizon";
                uses subif-split-horizon-config;
            } // END of config-container definition.
            container state {
                config false;
                description
                    "Operational state data for split-horizon";
                uses subif-split-horizon-config;
            } // END of state-container definition.
        } // END of subinterface-split-horizon-container definition.
        container link-debounce-time {
            description
                "Link Debounce Time related commands";
            container config {
                presence "link debounce time config";
                description
                    "Container for link debounce time config";
                uses link-debounce-time-config;
            } // END of config-container definition.
            container state {
                config false;
                description
                    "Operational state data for link debounce time module";
                uses link-debounce-time-config;
            } // END of state-container definition.
        } // END of link-debounce-time-container definition.
        container minimum-bandwidth {
            if-feature feature-list:HAVE_TE;
            description
                "Configuration data for minimum-bandwidth";
            container config {
                presence "minimum-bandwidth config";
                description
                    "Configuration data for minimum-bandwidth";
                uses minimum-bandwidth-config;
            } // END of config-container definition.
            container state {
                config false;
                description
                    "Configuration data for minimum-bandwidth";
                uses minimum-bandwidth-config;
            } // END of state-container definition.
        } // END of minimum-bandwidth-container definition.
    } // END of extended-container definition.
    } // END of extended-grouping definition.

    grouping  extended-ethernet-grouping {
    description
        "Top-level container for ethernet extensions";
    container extended-ethernet {
        description
            "Top-level container for ethernet extensions";
        container config {
            description
                "Configuration data for ethernet extensions";
            uses extended-ethernet-config;
        } // END of config-container definition.
        container state {
            config false;
            description
                "Counters/State data for ethernet extensions";
            uses extended-ethernet-config;
            uses extended-ethernet-state;
        } // END of state-container definition.
        container switchport-allowed-ether-types {
            if-feature feature-list:HAVE_ALLOWED_ETHERTYPE;
            description
                "Switching characteristics of the Layer2 interface";
            container config {
                when " /ipi-interface:interfaces/ipi-interface:interface/ipi-interface:config/ipi-interface:enable-switchport ";
                description
                    "Configuration data for switching characteristics of the Layer2
                            interface";
                uses switchport-allowed-ether-types-config;
            } // END of config-container definition.
            container state {
                if-feature feature-list:HAVE_ALLOWED_ETHERTYPE;
                config false;
                description
                    "Operational state data for extended ethernet interface module";

                list statistics {
                    key "ether-type";
                    config false;
                    description
                        "Switchport statistics per ethertype";
                    uses switchport-allowed-ether-types-stats;
                } // End of statistics-list
                uses switchport-allowed-ether-types-config;
            } // END of state-container definition.
        } // END of switchport-allowed-ether-types-container definition.
    } // END of extended-ethernet-container definition.
    } // END of extended-ethernet-grouping definition.

    grouping  storm-control-grouping {
    description
        "Container for storm-control module";
    container storm-control {
        if-feature feature-list:HAVE_RATE_LIMIT;
        description
            "Container for storm-control module";
        container broadcast {
            // when " ipi-if-extended:storm-control/broadcast/config/bcast-value ";
            if-feature feature-list:HAVE_RATE_LIMIT;
            description
                "Storm-control Broadcast related commands";
            container config {
                if-feature feature-list:HAVE_RATE_LIMIT;
                presence "Enable Storm-control Broadcast";
                description
                    "Configuration data for Storm-control Broadcast module";
                uses broadcast-config;
            } // END of config-container definition.
            container state {
                if-feature feature-list:HAVE_RATE_LIMIT;
                config false;
                description
                    "Operational state data for Storm-control Broadcast module";
                uses broadcast-config;
                uses broadcast-state;
            } // END of state-container definition.
        } // END of broadcast-container definition.
        container multicast {
            // when " ipi-if-extended:storm-control/multicast/config/mcast-value ";
            if-feature feature-list:HAVE_RATE_LIMIT;
            description
                "Storm-control Multicast related commands";
            container config {
                if-feature feature-list:HAVE_RATE_LIMIT;
                presence "Enable Storm-control Multicast";
                description
                    "Configuration data for Storm-control Multicast module";
                uses multicast-config;
            } // END of config-container definition.
            container state {
                if-feature feature-list:HAVE_RATE_LIMIT;
                config false;
                description
                    "Operational state data for Storm-control Multicast module";
                uses multicast-config;
                uses multicast-state;
            } // END of state-container definition.
        } // END of multicast-container definition.
        container dlf-broadcast {
            // when " ipi-if-extended:storm-control/dlf-broadcast/config/dlf-bcast-value ";
            if-feature feature-list:HAVE_RATE_LIMIT;
            description
                "Storm-control DLF-Broadcast related commands";
            container config {
                if-feature feature-list:HAVE_RATE_LIMIT;
                presence "Enable Storm-control DLF-Broadcast";
                description
                    "Configuration data for Storm-control DLF-Broadcast module";
                uses dlf-broadcast-config;
            } // END of config-container definition.
            container state {
                if-feature feature-list:HAVE_RATE_LIMIT;
                config false;
                description
                    "Operational state data for Storm-control DLF-Broadcast module";
                uses dlf-broadcast-config;
                uses dlf-broadcast-state;
            } // END of state-container definition.
        } // END of dlf-broadcast-container definition.
    } // END of storm-control-container definition.
    } // END of storm-control-grouping definition.

    grouping  custom-state-grouping {
    description
        "Custom interface operational state";
    container custom-state {
        config false;
        description
            "Custom interface operational state";
        uses bandwidth-operational-state;
    } // END of custom-state-container definition.
    } // END of custom-state-grouping definition.

    grouping  extended-counters-grouping {
    description
        "A collection of extended interface-related statistics counters";
    container extended-counters {
        config false;
        description
            "A collection of extended interface-related statistics counters";
        container lbg-stats {
            if-feature feature-list:HAVE_HAL;
            if-feature feature-list:HAVE_BROADCOM;
            if-feature feature-list:HAVE_LINK_BONDING;
            config false;
            description
                "Statistics for Link-bonding Group interface";
            uses lbg-counters-state;
        } // END of lbg-stats-container definition.
        container lb-modem-stats {
            if-feature feature-list:HAVE_HAL;
            if-feature feature-list:HAVE_BROADCOM;
            if-feature feature-list:HAVE_LINK_BONDING;
            config false;
            description
                "Statistics for Link-bonding Modem interface";
            uses lb-modem-counters-state;
        } // END of lb-modem-stats-container definition.
        uses extended-counters-state;
        uses interface-counters-extended;
        uses error-discard-statistics;
    } // END of extended-counters-container definition.
    } // END of extended-counters-grouping definition.

    grouping  extended-ethernet-counters-grouping {
    description
        "A collection of extended interface-related ethernet counters";
    container extended-ethernet-counters {
        if-feature feature-list:HAVE_BROADCOM;
        if-feature feature-list:HAVE_HAL;
        if-feature feature-list:NOT_HAVE_SWFWDR;
        if-feature feature-list:NOT_HAVE_POND;
        config false;
        description
            "A collection of extended interface-related ethernet counters";
        container protocol-pkt-stats {
            if-feature feature-list:HAVE_HAL;
            if-feature feature-list:HAVE_BROADCOM;
            config false;
            description
                "Statistics for interface protocol packets";
            uses protocol-pkt-statistics;
        } // END of protocol-pkt-stats-container definition.
        uses extended-ethernet-counters-state;
    } // END of extended-ethernet-counters-container definition.
    } // END of extended-ethernet-counters-grouping definition.

    grouping  global-grouping {
    description
        "Top-level container for global interface-related module";
    container global {
        description
            "Top-level container for global interface-related module";
        container config {
            description
                "Global extended configuration parameters common for interfaces";
            uses global-port-interval-config;
        } // END of config-container definition.
        container state {
            config false;
            description
                "Global extended state parameters common for interfaces";
            uses global-port-interval-config;
        } // END of state-container definition.
        container error-disable {
            description
                "Global Error-Disable objects";
            container config {
                description
                    "Global error-disable configuration parameters for the router";
                uses error-disable-config;
            } // END of config-container definition.
            container state {
                config false;
                description
                    "State data for global error-disable";
                uses error-disable-config;
                uses error-disable-state;
            } // END of state-container definition.
        } // END of error-disable-container definition.
        container l2-control-protocols {
            if-feature feature-list:HAVE_L2;
            description
                "Layer2 Control Protocols";

            list l2-control-protocol {
                key "l2cp-type";
                description
                    "Layer2 Control Protocol";
                leaf l2cp-type  {
                    type  leafref {
                        path  "../config/l2cp-type";
                    }
                    description "This attribute is used to configure the layer2 control-protocol type";
                } // END of l2cp-type definition.

                container config {
                    description
                        "Configuration data for Layer2 Control Protocol";
                    uses l2cp-config-global;
                } // END of config-container definition.
                container state {
                    config false;
                    description
                        "Operational data for Layer2 Control Protocol";
                    uses l2cp-config-global;
                } // END of state-container definition.
            } // End of l2-control-protocol-list
        } // END of l2-control-protocols-container definition.
        container mtus {
            description
                "Enclosing container for global MTU list";

            list mtu {
                key "if-type";
                description
                    "List of MTUs per interface-type";
                leaf if-type  {
                    type  leafref {
                        path  "../config/if-type";
                    }
                    description "Use this attribute to set the hardware interface type";
                } // END of if-type definition.

                container config {
                    description
                        "Global interfaces configuration data";
                    uses if-global-config;
                } // END of config-container definition.
                container state {
                    config false;
                    description
                        "Global interfaces operational data";
                    uses if-global-config;
                } // END of state-container definition.
            } // End of mtu-list
        } // END of mtus-container definition.
    } // END of global-container definition.
    } // END of global-grouping definition.

    grouping  tunnel-grouping {
    description
        "Interface tunnel related data";
    container tunnel {
        if-feature feature-list:HAVE_TUNNEL;
        description
            "Interface tunnel related data";
        container config {
            description
                "Configuration data for tunnel interface";
            uses tunnel-config;
        } // END of config-container definition.
        container state {
            config false;
            description
                "Operational state data for tunnel interface";
            uses tunnel-config;
        } // END of state-container definition.
    } // END of tunnel-container definition.
    } // END of tunnel-grouping definition.

    grouping  link-scan-grouping {
    description
        "Link Scan Timer related commands";
    container link-scan {
        description
            "Link Scan Timer related commands";
        container config {
            description
                "Container for link scan timer config";
            uses link-scan-timer-config;
        } // END of config-container definition.
        container state {
            config false;
            description
                "Operational state data for link scan timer module";
            uses link-scan-timer-config;
        } // END of state-container definition.
    } // END of link-scan-container definition.
    } // END of link-scan-grouping definition.

    grouping  l2-protocol-grouping {
    description
        "Container for L2 protocol learn-disable";
    container l2-protocol {
        description
            "Container for L2 protocol learn-disable";
        container config {
            description
                "Container for L2 protocol learn-disable";
            uses l2-protocol-config;
        } // END of config-container definition.
        container state {
            config false;
            description
                "Operational state data";
            uses l2-protocol-config;
        } // END of state-container definition.
    } // END of l2-protocol-container definition.
    } // END of l2-protocol-grouping definition.

    grouping  mac-ageing-grouping {
    description
        "Container for mac-ageing";
    container mac-ageing {
        description
            "Container for mac-ageing";
        container config {
            description
                "Container for mac-ageing config";
            uses mac-ageing-config;
        } // END of config-container definition.
        container state {
            config false;
            description
                "Operational state data for mac-ageing command";
            uses mac-ageing-config;
        } // END of state-container definition.
    } // END of mac-ageing-container definition.
    } // END of mac-ageing-grouping definition.

    augment /ipi-interface:interfaces/ipi-interface:interface {
    when " /ipi-interface:interfaces/ipi-interface:interface ";
        description
            "Top-level container for extended interface module";
        uses extended-grouping;
    }

    augment /ipi-interface:interfaces/ipi-interface:interface/ipi-if-ethernet:ethernet {
        description
            "Top-level container for ethernet extensions";
        uses extended-ethernet-grouping;
    }

    augment /ipi-interface:interfaces/ipi-interface:interface/ipi-if-ethernet:ethernet {
    when " /ipi-interface:interfaces/ipi-interface:interface/ipi-interface:config/ipi-interface:enable-switchport ";
        description
            "Container for storm-control module";
        uses storm-control-grouping;
    }

    augment /ipi-interface:interfaces/ipi-interface:interface/ipi-interface:state {
        description
            "Custom interface operational state";
        uses custom-state-grouping;
    }

    augment /ipi-interface:interfaces/ipi-interface:interface/ipi-interface:state/ipi-interface:counters {
        description
            "A collection of extended interface-related statistics counters";
        uses extended-counters-grouping;
    }

    augment /ipi-interface:interfaces/ipi-interface:interface/ipi-if-ethernet:ethernet/ipi-if-ethernet:state/ipi-if-ethernet:counters {
        description
            "A collection of extended interface-related ethernet counters";
        uses extended-ethernet-counters-grouping;
    }

    augment /ipi-interface:interfaces {
        description
            "Top-level container for global interface-related module";
        uses global-grouping;
    }

    augment /ipi-interface:interfaces/ipi-interface:interface {
        description
            "Interface tunnel related data";
        uses tunnel-grouping;
    }

    uses link-scan-grouping;
    uses l2-protocol-grouping;
    uses mac-ageing-grouping;
    augment /ipi-interface:interfaces {
        description
            "Global configuration for Port-group";
        uses port-group-speed-map-grouping;
    }


    rpc clear-interface-forward-error-correction-counters {
        description "Use this RPC to clear interface forward error correction counters.";
        input  {
            leaf if-name  {
                type string;
                mandatory true;
                description "Name of the interface to clear counters for. Specify NULL to clear
                            counters for all interfaces";
            }
        }
    }

    rpc clear-interface-error-disable {
        description "Use this RPC to clear interface error disable counters.";
        input  {
            leaf if-name  {
                type string;
                mandatory true;
                description "Name of the interface to clear counters for. Specify NULL to clear
                            counters for all interfaces";
            }
        }
    }

    rpc interface-sniff-enable {
        if-feature feature-list:HAVE_SNIFF_INTF;
        description "use this command to enable sniff on port to capture packets on sniff
                    port";
        input  {
            leaf interface-name  {
                type string;
                mandatory true;
                description "interface name";
            }
            leaf sniffTime  {
                type uint8 {
                    range "0..60";
                }
                mandatory true;
                description "time in minutes to sniff packets";
            }
            leaf sniffAction  {
                type ipi-if-types:if_sniff_action_t;
                mandatory true;
                description "sniff direction.";
            }
            leaf sniff1  {
                type boolean;
                mandatory true;
                description "sniff packets to sniff1 interface. Default sniff0";
            }
        }
    }

    rpc interface-sniff-disable {
        if-feature feature-list:HAVE_SNIFF_INTF;
        description "use this command to disable sniff on port to capture packets on sniff
                    port";
        input  {
            leaf interface-name  {
                type string;
                mandatory true;
                description "interface name";
            }
        }
    }

    notification interface-error-disable-notification {

        description "The interface-Errdis-Notif/interfaceErrdisNotif is generated when an interface is error-disabled(error-disable-reason will have non-zero value) and when it recovers from errdisabled state (error-disable-reason will have '0'). Severity level is CRITICAL for interface going down and MINOR for interface moving to UP state when it recovers from errdisabled state..";

        leaf severity {
            type cml-data-types:cml_notif_severity_t;
            description "Notification severity level";
        }

        leaf eventClass {
            type cml-data-types:cml_notif_class_t;
            description "Notification event class (value: STATE)";
        }

        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf error-disable-reason {
            type ipi-if-types:if_errdisable_state_t;
        description
            "This attribute specifies the event that caused the interface to be
                    error-disabled. If interface is error-disabled because of
                    lag-mismatch, value of this object is 1. If interface is
                    error-disabled because of stp-bpdu-guard, value of this object is 2.
                    If interface is error-disabled because of link-flap, value of this
                    object is 4. If interface is error-disabled because of storm-control,
                    value of this object is 32.";
        }
    }

    notification interface-bandwidth-start {

        description "Interface shaper is open.";

        leaf severity {
            type cml-data-types:cml_notif_severity_t;
            description "Notification severity level (value: INFO)";
        }

        leaf eventClass {
            type cml-data-types:cml_notif_class_t;
            description "Notification event class (value: STATE)";
        }

        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf current-bandwidth {
            type  uint64;
        description
            "Current Bandwidth in kbps";
        }
    }

    notification interface-bandwidth-upgrade {

        description "Interface bandwidth is upgraded.";

        leaf severity {
            type cml-data-types:cml_notif_severity_t;
            description "Notification severity level (value: INFO)";
        }

        leaf eventClass {
            type cml-data-types:cml_notif_class_t;
            description "Notification event class (value: STATE)";
        }

        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf current-bandwidth {
            type  uint64;
        description
            "Current Bandwidth in kbps";
        }
    }

    notification interface-bandwidth-downgrade {

        description "Interface bandwidth is downgraded.";

        leaf severity {
            type cml-data-types:cml_notif_severity_t;
            description "Notification severity level (value: WARNING)";
        }

        leaf eventClass {
            type cml-data-types:cml_notif_class_t;
            description "Notification event class (value: STATE)";
        }

        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf current-bandwidth {
            type  uint64;
        description
            "Current Bandwidth in kbps";
        }
    }

    notification interface-bandwidth-close {

        description "Interface bandwidth is 0.";

        leaf severity {
            type cml-data-types:cml_notif_severity_t;
            description "Notification severity level (value: WARNING)";
        }

        leaf eventClass {
            type cml-data-types:cml_notif_class_t;
            description "Notification event class (value: STATE)";
        }

        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf current-bandwidth {
            type  uint64;
        description
            "Current Bandwidth in kbps";
        }
    }

}
