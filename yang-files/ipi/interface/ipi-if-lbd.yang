/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-if-lbd.yang
*
*/

module ipi-if-lbd {

    yang-version 1.1;

    namespace   "http://www.ipinfusion.com/yang/ocnos/ipi-if-lbd";

    prefix "ipi-if-lbd";

    import cml-data-types {
        prefix cml-data-types;
        revision-date 2026-05-15;
    }

    import ipi-interface {
        prefix ipi-interface;
        revision-date 2026-03-10;
    }

    import ipi-if-types {
        prefix ipi-if-types;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for IPI looback-detection module";


    revision "2026-03-10" {
        description "Added the datatype for media-type attribute";
        reference " 0.14.0.";
    }

    revision "2025-09-24" {
        description "Changed the datatype for ether-type attribute";
        reference " 0.13.3.";
    }

    revision "2025-08-22" {
        description "Changed error disable type from bits to enum";
        reference " 0.13.2.";
    }

    revision "2025-06-27" {
        description "New cmd added - l2protocol all learn-disable";
        reference " 0.13.1.";
    }

    revision "2025-06-25" {
        description "Updated datatype 'IF_ERRDISABLE_STATE_T 'values";
        reference " 0.13.0.";
    }

    revision "2025-06-03" {
        description "Added port dfe and unreliable-los support";
        reference " 0.12.20.";
    }

    revision "2025-03-17" {
        description "Revert of EFM flag for l2pt efm CLI";
        reference " 0.12.19.";
    }

    revision "2024-11-18" {
        description "Added new datatype IF_ERRDIS_STATUS";
        reference " 0.12.18.";
    }

    revision "2024-10-29" {
        description "Add subtypes for global mtu configuration";
        reference " 0.12.17.";
    }

    revision "2024-10-17" {
        description "Added missing interface types for IF_HW_TYPE_T";
        reference " 0.12.16.";
    }

    revision "2024-10-03" {
        description "Added support to 400G and 200G in interface negotiated-port-speed";
        reference " 0.12.15.";
    }

    revision "2024-09-19" {
        description "Modified cli helpstring for mac ageing mode";
        reference " 0.2.10.";
    }

    revision "2024-09-03" {
        description "CL108 FEC config support";
        reference " 0.2.9.";
    }

    revision "2024-08-21" {
        description "Added CML_MAC_AGEING_T ";
        reference " 0.2.8.";
    }

    revision "2024-08-19" {
        description "Added global mtu configuration support";
        reference " 0.2.7.";
    }

    revision "2024-08-12" {
        description "Added global l2protocol configuration";
        reference " 0.2.6.";
    }

    revision "2024-07-26" {
        description "Make previous revision tag consistent";
        reference " 0.2.5.";
    }

    revision "2024-07-25" {
        description "Added UCMP CLI option";
        reference " 0.2.4.";
    }

    revision "2024-06-18" {
        description "Added BVI element in hardware type datatype";
        reference " 0.2.3.";
    }

    revision "2024-03-27" {
        description "Added limited autonegotiation support";
        reference " 0.2.2.";
    }

    revision "2024-01-24" {
        description "If Type data-model revision has higher date";
        reference " 0.2.1.";
    }

    revision "2024-01-06" {
        description "Added storm-control errdisable";
        reference " 0.2.0.";
    }

    revision "2023-12-20" {
        description "Added a new datatype IF_RAON_AODU_STATE";
        reference " 0.1.9.";
    }

    revision "2023-10-10" {
        description "Change storm-control maximum level to 99%";
        reference " 0.1.8.";
    }

    revision "2023-08-23" {
        description "Added datatype IF_ACLIF_TYPE_T";
        reference " 0.1.7.";
    }

    revision "2023-08-18" {
        description "Added pattern tag for the datatype IF_SUBIF_OUTER_TPID_T";
        reference " 0.1.6.";
    }

    revision "2023-05-26" {
        description "Added element types for FEC type configuration support";
        reference " 0.1.5.";
    }

    revision "2023-04-28" {
        description "Removed HARDWARE_PORT_MODE data type";
        reference " 0.1.4.";
    }

    revision "2023-03-03" {
        description "Added datatype for split-horizon";
        reference " 0.1.3.";
    }

    revision "2022-12-06" {
        description "Enclosed the objectlist with container";
        reference " 0.1.2.";
    }

    revision "2022-11-14" {
        description "Added support for Storm-control by Frame per second";
        reference " 0.1.1.";
    }

    revision "2022-09-27" {
        description "Loopback-detection module intial version";
        reference " 0.1.0.";
    }

    grouping loopback-detection-vlan-encap-config {
        description
            "loopback detection vlan encap config grouping";
        leaf encap-type  {
            type  ipi-if-types:if_subif_encap_type_t;
            description "enable tagged port";
        } // END of encap-type definition.

        leaf vlan-id  {
            type  cml-data-types:cml_range_t;
            mandatory true;
            description "Use this attribute to create a single/range of VLANs on the VLAN aware
                        bridges";
        } // END of vlan-id definition.

    } // END of loopback-detection-vlan-encap-config definition.
    grouping loopback-detection-global-config {
        description
            "loopback detection Detection Global config grouping";
        leaf detection-interval  {
            type  uint16 {
                 range "1..60"  {
                    description "1..60: Supported range 1 - 60";
                 }
            }
            units "seconds";
            default "30";
            description "Use this attribute to set the loopback-detection interval timer.";
        } // END of detection-interval definition.

        leaf enable-untagged  {
            type  empty;
            description "Use this attribute to configure encapsulation as untagged";
        } // END of enable-untagged definition.

    } // END of loopback-detection-global-config definition.

    grouping  loopback-detection-grouping {
    description
        "loopback detction cntr of this module";
    container loopback-detection {
        if-feature feature-list:HAVE_LBD;
        description
            "loopback detction cntr of this module";
        container config {
            if-feature feature-list:HAVE_LBD;
            description
                "Configuration data for loopback detection module";
            uses loopback-detection-global-config;
        } // END of config-container definition.
        container state {
            config false;
            description
                "data for LBD module";
            uses loopback-detection-global-config;
        } // END of state-container definition.
        container vlan-encapsulations {
            description
                "Loop back detection enables name configuration";

            list vlan-encapsulation {
                key "encap-type";
                description
                    "Loop back detection name configuration";
                leaf encap-type  {
                    type  leafref {
                        path  "../config/encap-type";
                    }
                    description "Attribute associated with this instance";
                } // END of encap-type definition.

                container config {
                    description
                        "This container defines LBD tagged configs";
                    uses loopback-detection-vlan-encap-config;
                } // END of config-container definition.
                container state {
                    config false;
                    description
                        "Operational state data for system";
                    uses loopback-detection-vlan-encap-config;
                } // END of state-container definition.
            } // End of vlan-encapsulation-list
        } // END of vlan-encapsulations-container definition.
    } // END of loopback-detection-container definition.
    } // END of loopback-detection-grouping definition.

    augment /ipi-interface:interfaces/ipi-interface:interface {
        description
            "loopback detction cntr of this module";
        uses loopback-detection-grouping;
    }


}
