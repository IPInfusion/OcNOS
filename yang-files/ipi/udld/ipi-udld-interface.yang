/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-udld-interface.yang
*
*/

submodule ipi-udld-interface {

    yang-version 1.1;

    belongs-to  ipi-udld { prefix ipi-udld; }

    import cml-data-types {
        prefix cml-data-types;
        revision-date 2026-05-15;
    }

    import ipi-interface {
        prefix ipi-interface;
        revision-date 2026-03-10;
    }

    import ipi-udld-types {
        prefix ipi-udld-types;
        revision-date 2023-04-05;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Layer-2 UnDirectional Link Detection Interfaces";


    revision "2026-01-29" {
        description "removed udld configs when switchport enabled/disbaled for L2/L3 aggregator interface";
        reference " 0.5.0.";
    }

    revision "2024-05-02" {
        description "removed udld configs when switchport enabled/disbaled for L2/L3 interface";
        reference " 0.4.0.";
    }

    revision "2024-01-18" {
        description "Handled switchport enabled disbaled for L2/L3 interface";
        reference " 0.3.0.";
    }

    revision "2022-06-01" {
        description "Updated the yang file with feature";
        reference " 0.2.0.";
    }

    revision "2021-10-25" {
        description "Restructured UDLD module in accordance with OpenConfig style";
        reference " 0.1.0.";
    }

    revision "2018-06-21" {
        description "Initial Version";
        reference "Initial Version";
    }

    grouping udld-interface-state {
        description
            "Grouping for UDLD Interface operational state data";
        leaf link-state  {
            type  ipi-udld-types:udld_link_state_type_t;
            description "Use this attribute to get the interface operational state";
        } // END of link-state definition.

    } // END of udld-interface-state definition.
    grouping udld-interface-config {
        description
            "Grouping for UDLD Interface configuration data";
        leaf name  {
            type  leafref {
                path  "/ipi-interface:interfaces/ipi-interface:interface/ipi-interface:name";
            }
            description "Use this attribute to configure UDLD for an interface.";
        } // END of name definition.

        leaf mode  {
            type  ipi-udld-types:udld_mode_type_t;
            description "Use this attribute to configure UDLD mode for an interface";
        } // END of mode definition.

        leaf administrative-state  {
            type  cml-data-types:cml_enable_disable_t;
            description "Use this attribute configure UDLD administrative state for an
                        interface";
        } // END of administrative-state definition.

    } // END of udld-interface-config definition.
    grouping udld-interface-top {
        description
            "Grouping for UDLD Interface";
        container interfaces {
            description
                "Container for UDLD Interface configuration";

            list interface {
            // when " ipi-udld:udld/global/config/enable ";
                key "name";
                description
                    "List of interfaces on which udld will be configured";
                leaf name  {
                    type  leafref {
                        path  "../config/name";
                    }
                    description "Use this attribute to configure UDLD for an interface.";
                } // END of name definition.

                container config {
                    description
                        "Configuration data for UDLD Interface";
                    uses udld-interface-config;
                } // END of config-container definition.
                container state {
                    config false;
                    description
                        "Operational state data for UDLD Interface";
                    uses udld-interface-config;
                    uses udld-interface-state;
                } // END of state-container definition.
            } // End of interface-list
        } // END of interfaces-container definition.
    } // END of udld-interface-top definition.


}
