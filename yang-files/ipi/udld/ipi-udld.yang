/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-udld.yang
*
*/

module ipi-udld {

    yang-version 1.1;

    namespace   "http://www.ipinfusion.com/yang/ocnos/ipi-udld";

    prefix "ipi-udld";

    import ipi-udld-types {
        prefix ipi-udld-types;
        revision-date 2023-04-05;
    }

    import feature-list {
        prefix feature-list;
        revision-date 2026-09-15;
    }

    include ipi-udld-interface { revision-date 2026-01-29;}
    organization
        "IP Infusion Inc.";

    contact
        "Address: 3965 Freedom Circle, Suite 200, Santa Clara, CA 95054
         Phone: +1 408-400-1900
         E-mail: support@ipinfusion.com
         Web: http://www.ipinfusion.com/";

    description
        "Datamodel for Layer-2 UnDirectional Link Detection";


    revision "2026-01-29" {
        description "removed udld configs when switchport enabled/disbaled for L2/L3 aggregator interface";
        reference " 0.6.0.";
    }

    revision "2024-05-02" {
        description "Removed udld configs when switchport enabled/disbaled for L2/L3 interface";
        reference " 0.5.0.";
    }

    revision "2024-01-18" {
        description "Handled switchport enabled disbaled for L2/L3 interface";
        reference " 0.4.0.";
    }

    revision "2023-04-05" {
        description "Added support for UDLD debug configuration";
        reference " 0.3.0.";
    }

    revision "2022-06-01" {
        description "Updated the yang file with feature";
        reference " 0.2.0.";
    }

    revision "2021-10-25" {
        description "Restructured UDLD module in accordance with OpenConfig style";
        reference " 0.1.0.";
    }

    revision "2018-06-21" {
        description "Initial Version";
        reference "Initial Version";
    }

    grouping udld-global-config {
        description
            "Grouping for UDLD Global configuration data";
        leaf enable  {
            type  empty;
            description "Use this attribute to enable UDLD";
        } // END of enable definition.

        leaf message-time  {
            type  uint8 {
                 range "7..90"  {
                    description "7..90: Supported range 7 - 90";
                 }
            }
            description "Use this attribute to set UDLD message interval value";
        } // END of message-time definition.

    } // END of udld-global-config definition.
    grouping udld-debug-config {
        description
            "UDLD debug level information grouping";
        leaf options  {
            type  ipi-udld-types:udld_debug_t;
            description "Use this attribute to enable or disable UDLD debugging at various
                        levels";
        } // END of options definition.

    } // END of udld-debug-config definition.
    grouping udld-terminal-debug-state {
        description
            "UDLD terminal debug grouping";
        leaf terminal-debug-status  {
            type  ipi-udld-types:udld_debug_t;
            description "This attribute returns the terminal debug options which are enabled";
        } // END of terminal-debug-status definition.

    } // END of udld-terminal-debug-state definition.
    grouping udld-debug-top {
        description
            "Grouping for UDLD debug";
        container debug {
            description
                "Container for UDLD debugging functions";
            container config {
                description
                    "Configuration data for UDLD debug";
                uses udld-debug-config;
            } // END of config-container definition.
            container state {
                config false;
                description
                    "Operational state data for UDLD debug";
                uses udld-debug-config;
                uses udld-terminal-debug-state;
            } // END of state-container definition.
        } // END of debug-container definition.
    } // END of udld-debug-top definition.
    grouping udld-global-top {
        description
            "Grouping for UDLD Global";
        container global {
            description
                "Container for UDLD Global configuration";
            container config {
                description
                    "Configuration data for UDLD Global";
                uses udld-global-config;
            } // END of config-container definition.
            container state {
                config false;
                description
                    "Operational state data for UDLD Global";
                uses udld-global-config;
            } // END of state-container definition.
        } // END of global-container definition.
    } // END of udld-global-top definition.

    grouping  udld-grouping {
    description
        "UniDirectional Link Detection (UDLD) data model";
    container udld {
        if-feature feature-list:HAVE_UDLD;
        description
            "UniDirectional Link Detection (UDLD) data model";
        uses udld-global-top;
        uses udld-debug-top;
        uses udld-interface-top;
    } // END of udld-container definition.
    } // END of udld-grouping definition.

    uses udld-grouping;

    rpc udld-terminal-debug-on {
        if-feature feature-list:HAVE_UDLD;
        description "Use this RPC to enable UDLD terminal debug options";
        input  {
            leaf terminal-debug-options  {
                type ipi-udld-types:udld_debug_t;
                mandatory true;
                description "This attribute specifies the type of debug configured";
            }
        }
    }

    rpc udld-terminal-debug-off {
        if-feature feature-list:HAVE_UDLD;
        description "Use this RPC to disable UDLD terminal debug options";
        input  {
            leaf terminal-debug-options  {
                type ipi-udld-types:udld_debug_t;
                mandatory true;
                description "This attribute specifies the type of debug configured";
            }
        }
    }

}
