/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ntp.yang
*
*/

module ipi-ntp {

    yang-version 1.1;

    namespace   "http://www.ipinfusion.com/yang/ocnos/ipi-ntp";

    prefix "ipi-ntp";

    import ietf-inet-types {
        prefix inet;
        revision-date 2013-07-15;
    }

    import cml-data-types {
        prefix cml-data-types;
        revision-date 2026-05-15;
    }

    import ipi-network-instance {
        prefix ipi-network-instance;
        revision-date 2026-08-12;
    }

    import ipi-vrf {
        prefix ipi-vrf;
        revision-date 2026-08-12;
    }

    import ipi-ntp-types {
        prefix ipi-ntp-types;
        revision-date 2025-12-22;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for NTP configurations";


    revision "2026-08-14" {
        description "added the autopopulate tag to populate vrf";
        reference " 0.15.0.";
    }

    revision "2025-12-25" {
        description "Removed ntp-clear-statistics cli since it's not supported in debian12";
        reference " 0.14.4.";
    }

    revision "2025-10-07" {
        description "Added feature-enable condition in when tag";
        reference " 0.14.3.";
    }

    revision "2025-08-07" {
        description "Updated when tag to delete the vrf, when there is no child";
        reference " 0.14.2.";
    }

    revision "2025-08-05" {
        description "Added dependentObject for deletion to handle dependeny issue";
        reference " 0.14.1.";
    }

    revision "2025-07-03" {
        description "Added disable-default attribute to resolve show running-config issue";
        reference " 0.14.0.";
    }

    revision "2024-09-10" {
        description "Added implicite-delete tag for ntp discard minimum";
        reference " 0.12.2.";
    }

    revision "2024-08-23" {
        description "Behavior modified when vrf is deleted and used in ntp";
        reference " 0.12.1.";
    }

    revision "2024-06-10" {
        description "Support to user vrf added";
        reference " 0.12.0.";
    }

    revision "2024-02-05" {
        description "Added flag in when tag to handle dependency issue";
        reference " 0.13.1.";
    }

    revision "2023-08-14" {
        description "Adding max-element for vrf ntp";
        reference " 0.11.0.";
    }

    revision "2023-07-07" {
        description "Removed cml_initialized flag from ntp";
        reference " 0.10.0.";
    }

    revision "2023-05-29" {
        description "Added When tag for no-debug-all command";
        reference " 0.10.0.";
    }

    revision "2022-11-28" {
        description "Removed source-interface cli from ntp";
        reference " 0.9.1.";
    }

    revision "2022-11-16" {
        description "Updated missing cliprependstr tags";
        reference " 0.9.0.";
    }

    revision "2022-08-10" {
        description "Debug hierarchy change";
        reference " 0.8.0.";
    }

    revision "2022-06-01" {
        description "Updated the yang file with feature";
        reference " 0.7.0.";
    }

    revision "2022-04-27" {
        description "Added Netconf Get support for runtime info for NTP servers/peers ";
        reference " 0.6.0.";
    }

    revision "2022-02-16" {
        description "Introduced requestkey attribute to support nomodify option";
        reference " 0.5.0.";
    }

    revision "2021-10-08" {
        description "Updated dependencies for ntp global configurations";
        reference " 0.4.0.";
    }

    revision "2021-09-30" {
        description "Added validation utils function for peer-address attribute";
        reference " 0.3.0.";
    }

    revision "2021-09-06" {
        description "Added changes to make NTP feature disable persistent across device reloads";
        reference " 0.2.0.";
    }

    revision "2021-06-25" {
        description "Initial Version";
        reference " 0.1.0.";
    }

    grouping ntp-vrf-config {
        description
            "ntp vrf configuration";
        leaf vrf-name  {
            type  leafref {
                path  "/ipi-network-instance:network-instances/ipi-network-instance:network-instance/ipi-vrf:vrf/ipi-vrf:config/ipi-vrf:vrf-name";
            }
            description "Use this attribute to specify the vrf for which ntp feature is enabled";
        } // END of vrf-name definition.

        leaf feature-enable  {
            type  empty;
            description "Use this attribute to enable or disable NTP feature.";
        } // END of feature-enable definition.

        leaf disable-ntp  {
            type  empty;
            description "Use this attribute to enable or disable NTP server";
        } // END of disable-ntp definition.

        leaf enable-logging  {
            type  empty;
            description "Use this attribute to log NTP events.";
        } // END of enable-logging definition.

    } // END of ntp-vrf-config definition.
    grouping ntp-ref-clock-master-config {
        description
            "ntp master clock  configuration";
        leaf enable-local-master  {
            type  empty;
            mandatory true;
            description "Use this attribute to configure the device as an NTP server.";
        } // END of enable-local-master definition.

        leaf local-stratum  {
            // when " ipi-ntp:ntp/vrfs/vrf/ref-clock-master/config/enable-local-master ";
            type  uint8 {
                 range "1..15"  {
                    description "1..15: Supported range 1 - 15";
                 }
            }
            description "Use this attribute to configure stratum level for a NTP server.";
        } // END of local-stratum definition.

    } // END of ntp-ref-clock-master-config definition.
    grouping ntp-auth-config {
        description
            "ntp authentication  configuration";
        leaf enable-ntp-auth  {
            type  empty;
            description "Use this attribute to enable NTP authentication.";
        } // END of enable-ntp-auth definition.

        leaf-list ntp-trusted-keys  {
            type  uint32 {
                 range "1..65535"  {
                    description "1..65535: Supported range 1 - 65535";
                 }
            }
            description "Use this attribute to configure one or more trusted authentication
                        keys. If a key is trusted, the device will synchronize with a system
                        that specifies this key in its NTP packets";
        } // END of ntp-trusted-keys definition.

        leaf ntp-request-key  {
            // when " ipi-ntp:ntp/vrfs/vrf/authentication/config/ntp-trusted-keys ";
            type  uint32 {
                 range "1..65534"  {
                    description "1..65534: Supported range 1 - 65534";
                 }
            }
            description "Use this to attribute to configure request key which shall be used as
                        password for ntpdc utility.";
        } // END of ntp-request-key definition.

    } // END of ntp-auth-config definition.
    grouping ntp-auth-key-config {
        description
            "ntp authentication keys configuration";
        leaf key-id  {
            type  uint32 {
                 range "1..65535"  {
                    description "1..65535: Supported range 1 - 65535";
                 }
            }
            description "Use this attribute to set an NTP authentication key id.";
        } // END of key-id definition.

        leaf key-value  {
            type  string {
                length "1..1965";
                pattern "[^?' =,>|]+";
            }
            mandatory true;
            description "Use this attribute to set an NTP authentication key value.";
        } // END of key-value definition.

        leaf key-type  {
            type  ipi-ntp-types:ntp_hostp_key_type_t;
            mandatory true;
            description "Use this attribute to set the NTP authentication key type.";
        } // END of key-type definition.

    } // END of ntp-auth-key-config definition.
    grouping ntp-server-config {
        description
            "ntp server configuration";
        leaf server-address  {
            type  string {
                length "1..63";
                pattern "[^?' =,>|]+";
            }
            description "Use this attribute to set the NTP server IP address or hostname";
        } // END of server-address definition.

    } // END of ntp-server-config definition.
    grouping ntp-peer-config {
        description
            "ntp server configuration";
        leaf peer-address  {
            type  string {
                length "1..63";
                pattern "[^?' =,>|]+";
            }
            description "Use this attribute to set the NTP peer IP address or hostname";
        } // END of peer-address definition.

    } // END of ntp-peer-config definition.
    grouping ntp-server-peer-common-config {
        description
            "common attributes for ntp server and peer configuration";
        leaf prefer  {
            type  empty;
            description "preferred NTP server/peer";
        } // END of prefer definition.

        leaf auth-key  {
            type  uint32 {
                 range "1..65535"  {
                    description "1..65535: Supported range 1 - 65535";
                 }
            }
            default "65535";
            description "Use this attribute to set the keyid to be used while communicating to
                        this server";
        } // END of auth-key definition.

        leaf minpoll  {
            type  uint16 {
                 range "4..16"  {
                    description "4..16: Supported range 4 - 16";
                 }
            }
            default "4";
            description "Use this attribute to set the minimum poll interval for NTP messages";
        } // END of minpoll definition.

        leaf maxpoll  {
            type  uint16 {
                 range "4..16"  {
                    description "4..16: Supported range 4 - 16";
                 }
            }
            default "6";
            description "Use this attribute to set the maximum poll interval for NTP messages";
        } // END of maxpoll definition.

    } // END of ntp-server-peer-common-config definition.
    grouping ntp-acl-config {
        description
            "NTP acl configuration";
        leaf client-ip-address  {
            type  inet:ip-address;
            description "use this attribute to specify the allowed NTP client IP address";
        } // END of client-ip-address definition.

        leaf netmask  {
            type  ipi-ntp-types:ntp_client_ip_net_mask_t;
            description "use this attribute to specify the allowed NTP client IP network mask";
        } // END of netmask definition.

        leaf access-options  {
            type  ipi-ntp-types:ntp_acl_options_t;
            description "use this attribute to specify the allowed access options for NTP
                        client";
        } // END of access-options definition.

    } // END of ntp-acl-config definition.
    grouping ntp-global-debug-config {
        description
            "NTP debug configuration";
        leaf enable  {
            type  empty;
            description "Use this attribute to enable NTP debug logs";
        } // END of enable definition.

    } // END of ntp-global-debug-config definition.
    grouping ntp-global-debug-state {
        description
            "NTP terminal debugging status";
        leaf terminal-debug-status  {
            type  cml-data-types:cml_on_off_t;
            description "This attribute contains the NTP terminal debug status";
        } // END of terminal-debug-status definition.

    } // END of ntp-global-debug-state definition.
    grouping ntp-rate-limiting-config {
        description
            "NTP ACL discard options";
        leaf minimum-pkt-spacing  {
            type  uint16 {
                 range "1..65535"  {
                    description "1..65535: Supported range 1 - 65535";
                 }
            }
            description "Use this attribute to specify the minimum packet spacing to be
                        permitted";
        } // END of minimum-pkt-spacing definition.

    } // END of ntp-rate-limiting-config definition.
    grouping ntp-vrfs-top {
        description
            "Top level grouping for NTP VRF configuration and data";
        container vrfs {
            description
                "container for vrf level NTP configuration and state information";

            list vrf {
                key "vrf-name";
                max-elements 1;
                description
                    "VRF level NTP configuration and state information";
                leaf vrf-name  {
                    type  leafref {
                        path  "../config/vrf-name";
                    }
                    description "Use this attribute to specify the vrf for which ntp feature is enabled";
                } // END of vrf-name definition.

                container config {
                    description
                        "NTP vrf configuration information";
                    uses ntp-vrf-config;
                } // END of config-container definition.
                container state {
                    config false;
                    description
                        "NTP vrf state information";
                    uses ntp-vrf-config;
                } // END of state-container definition.
                uses ntp-ref-clock-master-top;
                uses ntp-authentication-top;
                uses ntp-servers-top;
                uses ntp-peers-top;
                uses ntp-rate-limiting-top;
                uses ntp-access-control-entries-top;
            } // End of vrf-list
        } // END of vrfs-container definition.
    } // END of ntp-vrfs-top definition.
    grouping ntp-ref-clock-master-top {
        description
            "Top level grouping for NTP clock master configuration and state data";
        container ref-clock-master {
            description
                "NTP clock master configuration and state data";
            container config {
                presence "Configure the device as an NTP server";
                description
                    "NTP clock master configuration";
                uses ntp-ref-clock-master-config;
            } // END of config-container definition.
            container state {
                config false;
                description
                    "NTP clock master state data";
                uses ntp-ref-clock-master-config;
            } // END of state-container definition.
        } // END of ref-clock-master-container definition.
    } // END of ntp-ref-clock-master-top definition.
    grouping ntp-authentication-top {
        description
            "Top level grouping for NTP authentication configuration and state data";
        container authentication {
            description
                "NTP authentication configuration and state data";
            container config {
                description
                    "NTP authentication configuration";
                uses ntp-auth-config;
            } // END of config-container definition.
            container state {
                config false;
                description
                    "NTP authentication state data";
                uses ntp-auth-config;
            } // END of state-container definition.
            uses ntp-authentication-keys-top;
        } // END of authentication-container definition.
    } // END of ntp-authentication-top definition.
    grouping ntp-authentication-keys-top {
        description
            "Top level grouping for NTP authentication key configuration and state
                        data";
        container ntp-keys {
            description
                "NTP authentication key configuration and state data";

            list ntp-key {
                key "key-id";
                description
                    "NTP authentication key list";
                leaf key-id  {
                    type  leafref {
                        path  "../config/key-id";
                    }
                    description "Use this attribute to set an NTP authentication key.";
                } // END of key-id definition.

                container config {
                    description
                        "NTP authentication configuration";
                    uses ntp-auth-key-config;
                } // END of config-container definition.
                container state {
                    config false;
                    description
                        "NTP authentication state data";
                    uses ntp-auth-key-config;
                } // END of state-container definition.
            } // End of ntp-key-list
        } // END of ntp-keys-container definition.
    } // END of ntp-authentication-keys-top definition.
    grouping ntp-servers-top {
        description
            "Top level grouping for NTP server configuration and state data";
        container servers {
            description
                "Top level container for NTP server configuration and state data";

            list server {
                key "server-address";
                description
                    "NTP servers configuration and state data";
                leaf server-address  {
                    type  leafref {
                        path  "../config/server-address";
                    }
                    description "Use this attribute to set the NTP server IP address or hostname";
                } // END of server-address definition.

                container config {
                    description
                        "NTP authentication configuration";
                    uses ntp-server-config;
                    uses ntp-server-peer-common-config;
                } // END of config-container definition.
                container state {
                    config false;
                    description
                        "NTP authentication state data";
                    uses ntp-server-config;
                    uses ntp-server-peer-common-config;
                } // END of state-container definition.
            } // End of server-list
        } // END of servers-container definition.
    } // END of ntp-servers-top definition.
    grouping ntp-peers-top {
        description
            "Top level grouping for NTP peer configuration and state data";
        container peers {
            description
                "Top level container for NTP peer configuration and state data";

            list peer {
                key "peer-address";
                description
                    "NTP peers configuration and state data";
                leaf peer-address  {
                    type  leafref {
                        path  "../config/peer-address";
                    }
                    description "Use this attribute to set the NTP peer IP address or hostname";
                } // END of peer-address definition.

                container config {
                    description
                        "NTP authentication configuration";
                    uses ntp-peer-config;
                    uses ntp-server-peer-common-config;
                } // END of config-container definition.
                container state {
                    config false;
                    description
                        "NTP authentication state data";
                    uses ntp-peer-config;
                    uses ntp-server-peer-common-config;
                } // END of state-container definition.
            } // End of peer-list
        } // END of peers-container definition.
    } // END of ntp-peers-top definition.
    grouping ntp-rate-limiting-top {
        description
            "Top level grouping for NTP rate limit options";
        container rate-limiting {
            when " /ipi-ntp:ntp/ipi-ntp:vrfs/ipi-ntp:vrf/ipi-ntp:ref-clock-master/ipi-ntp:config/ipi-ntp:enable-local-master ";
            description
                "NTP rate limit options";
            container config {
                description
                    "NTP rate limiting options configuration";
                uses ntp-rate-limiting-config;
            } // END of config-container definition.
            container state {
                config false;
                description
                    "NTP authentication state data";
                uses ntp-rate-limiting-config;
            } // END of state-container definition.
        } // END of rate-limiting-container definition.
    } // END of ntp-rate-limiting-top definition.
    grouping ntp-access-control-entries-top {
        description
            "Top level grouping for NTP access control configuration and state data";
        container access-control-entries {
            when " /ipi-ntp:ntp/ipi-ntp:vrfs/ipi-ntp:vrf/ipi-ntp:ref-clock-master/ipi-ntp:config/ipi-ntp:enable-local-master ";
            description
                "NTP access control configuration and state data";

            list access-control-entry {
                key "client-ip-address";
                description
                    "NTP access control list";
                leaf client-ip-address  {
                    type  leafref {
                        path  "../config/client-ip-address";
                    }
                    description "use this attribute to specify the allowed NTP client IP address";
                } // END of client-ip-address definition.

                container config {
                    description
                        "NTP access control configuration";
                    uses ntp-acl-config;
                } // END of config-container definition.
                container state {
                    config false;
                    description
                        "NTP access control state data";
                    uses ntp-acl-config;
                } // END of state-container definition.
            } // End of access-control-entry-list
        } // END of access-control-entries-container definition.
    } // END of ntp-access-control-entries-top definition.
    grouping ntp-debug-top {
        description
            "Top level grouping for NTP debug configuration and state data";
        container debug {
            description
                "NTP debug configuration and state data";
            container config {
                description
                    "NTP debug configuration";
                uses ntp-global-debug-config;
            } // END of config-container definition.
            container state {
                config false;
                description
                    "NTP access control state data";
                uses ntp-global-debug-config;
                uses ntp-global-debug-state;
            } // END of state-container definition.
        } // END of debug-container definition.
    } // END of ntp-debug-top definition.
    grouping ntp-peer-state {
        description
            "Operational attributes for NTP peer related information";
        leaf peer-address  {
            type  cml-data-types:cml_hostname_t;
            description "This attribute returns the NTP peer IP address or hostname";
        } // END of peer-address definition.

        leaf stratum  {
            type  uint8;
            description "This attribute indicates the level of the server/peer in the NTP
                        hierarchy. As stratum number increases, the accuracy is degraded.
                        Primary NTP servers are stratum 1 while a maximum value of 16
                        indicates unsynchronized.";
        } // END of stratum definition.

        leaf poll-interval  {
            type  uint32;
            units "seconds";
            description "This attribute indicates the polling interval of the NTP peer or
                        server";
        } // END of poll-interval definition.

        leaf reach-value  {
            type  uint16;
            description "The reach value contains the results of the most recent eight NTP
                        update packets to the peer/server displayed in octal format.
                        If all eight are successful, this attribute value will read 377. If
                        the reach value is non-zero, the server is reachable otherwise, it is
                        non-reachable.";
        } // END of reach-value definition.

        leaf root-delay  {
            type  decimal64 {
                 fraction-digits 3;            }
            units "milliseconds";
            description "The round-trip delay to the peer";
        } // END of root-delay definition.

        leaf offset  {
            type  decimal64 {
                 fraction-digits 3;            }
            units "milliseconds";
            description "Estimate of the current time offset from the peer. This is the time
                        difference between the local and peer reference clock";
        } // END of offset definition.

    } // END of ntp-peer-state definition.
    grouping ntp-peer-info-top {
        description
            "Top level grouping for NTP peers operational information";
        container peer-info {
            config false;
            description
                "Top level container for runtime info on NTP peers";
            container peers {
                config false;
                description
                    "NTP peers";

                list peer {
                    key "peer-address";
                    config false;
                    description
                        "List of NTP peers connected";
                    leaf peer-address  {
                        type  leafref {
                            path  "../state/peer-address";
                        }
                        description "This attribute returns the NTP peer IP address or hostname";
                    } // END of peer-address definition.

                    container state {
                        config false;
                        description
                            "Operational container for NTP peer information";
                        uses ntp-peer-state;
                    } // END of state-container definition.
                } // End of peer-list
            } // END of peers-container definition.
        } // END of peer-info-container definition.
    } // END of ntp-peer-info-top definition.
    grouping ntp-default-config {
        description
            "ntp disable default configuration";
        leaf disable-default-instance  {
            type  empty;
            description "Use this attribute to prevent default ntp config from being enabled at
                        start up";
        } // END of disable-default-instance definition.

    } // END of ntp-default-config definition.
    grouping ntp-default-top {
        description
            "ntp disable default configuration";
        container default-instance {
            description
                "ntp default container configuration";
            container config {
                description
                    "Configuration data for ntp configuration";
                uses ntp-default-config;
            } // END of config-container definition.
            container state {
                config false;
                description
                    "Operational state data for ntp configuration";
                uses ntp-default-config;
            } // END of state-container definition.
        } // END of default-instance-container definition.
    } // END of ntp-default-top definition.

    grouping  ntp-grouping {
    description
        "Top level container for NTP, including configuration and state data";
    container ntp {
        if-feature feature-list:HAVE_HOSTPD;
        if-feature feature-list:HAVE_HOSTP_NTP;
        description
            "Top level container for NTP, including configuration and state data";
        uses ntp-vrfs-top;
        uses ntp-debug-top;
        uses ntp-peer-info-top;
        uses ntp-default-top;
    } // END of ntp-container definition.
    } // END of ntp-grouping definition.

    uses ntp-grouping;

    rpc ntp-retry-server-synchronization {
        if-feature feature-list:HAVE_HOSTPD;
        if-feature feature-list:HAVE_HOSTP_NTP;
        description "Use this RPC to retry synchronization with the configured NTP servers";
        input  {
            leaf vrf-name  {
                type string;
                mandatory true;
                description "Use this attribute to specify the vrf name on which the
                            synchronization should be retried";
            }
        }
    }

    rpc ntp-terminal-debug-on {
        if-feature feature-list:HAVE_HOSTPD;
        if-feature feature-list:HAVE_HOSTP_NTP;
        description "Use this RPC to enable terminal NTP debugs";
    }

    rpc ntp-terminal-debug-off {
        if-feature feature-list:HAVE_HOSTPD;
        if-feature feature-list:HAVE_HOSTP_NTP;
        description "Use this RPC to disable terminal NTP debugs";
    }

}
