/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-role-based-access-control-types.yang
*
*/

module ipi-role-based-access-control-types {

    yang-version 1.1;

    namespace   "http://www.ipinfusion.com/yang/ocnos/ipi-role-based-access-control-types";

    prefix "ipi-role-based-access-control-types";

    organization
        "IP Infusion Inc.";

    contact
        "Address: 3965 Freedom Circle, Suite 200, Santa Clara, CA 95054
         Phone: +1 408-400-1900
         E-mail: support@ipinfusion.com
         Web: http://www.ipinfusion.com/";

    description
        "Data types for ipi-role-based-access-control";


    revision "2022-06-01" {
        description "Updated the yang file with feature";
        reference " 0.2.0.";
    }

    revision "2022-01-28" {
        description "Initial Version";
        reference " 0.1.0.";
    }



    typedef  rbac_rule_type_t {
        type enumeration {
            enum deny {
                value 0;
                description "Remove rule from policy";
            }
            enum permit {
                value 1;
                description "Add rule to policy";
            }
        }
        description "type definition for RBAC_RULE_TYPE_T";
    }

    typedef  rbac_default_rule_type_t {
        type enumeration {
            enum deny-all {
                value 0;
                description "Set default rule as deny-all";
            }
            enum permit-all {
                value 1;
                description "Set default rule as permit-all";
            }
        }
        description "type definition for RBAC_DEFAULT_RULE_TYPE_T";
    }

}
