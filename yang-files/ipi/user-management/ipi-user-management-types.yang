/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-user-management-types.yang
*
*/

module ipi-user-management-types {

    yang-version 1.1;

    namespace   "http://www.ipinfusion.com/yang/ocnos/ipi-user-management-types";

    prefix "ipi-user-management-types";

    organization
        "IP Infusion Inc.";

    contact
        "Address: 3965 Freedom Circle, Suite 200, Santa Clara, CA 95054
         Phone: +1 408-400-1900
         E-mail: support@ipinfusion.com
         Web: http://www.ipinfusion.com/";

    description
        "User-Management data types";


    revision "2024-09-29" {
        description "Added support to choose hash algorithm for user password";
        reference " 0.4.0.";
    }

    revision "2022-06-25" {
        description "Kept different attribute for rbac-role";
        reference " 0.3.0.";
    }

    revision "2022-06-01" {
        description "Updated the yang file with feature";
        reference " 0.3.0.";
    }

    revision "2021-09-03" {
        description "Update descriptions of attribute";
        reference " 0.2.0.";
    }

    revision "2021-06-07" {
        description "Initial Version";
        reference " 0.1.0.";
    }



    typedef  user_mgmt_role_types_t {
        type enumeration {
            enum network-admin {
                value 1;
                description "Enter the rolename - Network Administrator - Have all permissions";
            }
            enum network-engineer {
                value 2;
                description "Enter the rolename - Network Engineer - Can save configuration";
            }
            enum network-operator {
                value 3;
                description "Enter the rolename - Network Operator - Can not save configuration";
            }
            enum network-user {
                value 4;
                description "Enter the rolename - Network User - Can not change configuration";
            }
        }
        description "type definition for USER_MGMT_ROLE_TYPES_T";
    }

    typedef  user_mgmt_rbac_role_t {
        type string;
        description "type definition for USER_MGMT_RBAC_ROLE_T";
    }

    typedef  user_mgmt_hashing_algorithm_t {
        type enumeration {
            enum md5 {
                value 1;
                description "Select MD5 as hash algorithm for username";
            }
            enum sha-256 {
                value 5;
                description "Select SHA-256 as hash algorithm for username";
            }
            enum sha-512 {
                value 6;
                description "Select SHA-512 as hash algorithm for username";
            }
        }
        description "type definition for USER_MGMT_HASHING_ALGORITHM_T";
    }

}
