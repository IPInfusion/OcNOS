/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-keychain.yang
*
*/

module ipi-keychain {

    yang-version 1.1;

    namespace   "http://www.ipinfusion.com/yang/ocnos/ipi-keychain";

    prefix "ipi-keychain";

    organization
        "IP Infusion Inc.";

    contact
        "Address: 3965 Freedom Circle, Suite 200, Santa Clara, CA 95054
         Phone: +1 408-400-1900
         E-mail: support@ipinfusion.com
         Web: http://www.ipinfusion.com/";

    description
        "Datamodel for Key-Chain configurations for routing protocol
                authentication";


    revision "2025-03-06" {
        description "Changed the encrypted key length";
        reference " 0.4.4.";
    }

    revision "2022-07-26" {
        description "Corrected RIP datamodel as per Open Config style";
        reference " 0.4.3.";
    }

    revision "2022-07-11" {
        description "Changing the Key mode CLI due to conflict between sub CLI in key mode";
        reference " 0.4.2.";
    }

    revision "2022-06-29" {
        description "Added implicit delete tag for key-chains container";
        reference " 0.4.1.";
    }

    revision "2022-06-01" {
        description "Updated the yang file with feature";
        reference " 0.4.0.";
    }

    revision "2021-06-01" {
        description "Changed when statement for start-date-time-for-accept and start-date-time-for-send";
        reference " 0.3.3.";
    }

    revision "2021-05-07" {
        description "Fixed the strings displayed for accept-lifetime and send-lifetime commands.";
        reference " 0.3.2.";
    }

    revision "2021-05-05" {
        description "Fixed auto-generated documentation. Change in key-string encrypted parameter length/range";
        reference " 0.3.1.";
    }

    revision "2021-03-16" {
        description "Change attribute name from hexadecimal-string to encrypted";
        reference " 0.3.0.";
    }

    revision "2021-01-08" {
        description "Restructured module as per open-config style";
        reference " 0.2.0.";
    }

    revision "2018-06-21" {
        description "Initial Version";
        reference " 0.1.0.";
    }



    typedef  keychain_hex_string_t {
        type string {
            pattern "0x([0-9a-fA-F]{2})+";
        }
        description "type definition for KEYCHAIN_HEX_STRING_T";
    }

    typedef  keychain_date_time_t {
        type string {
            pattern "([0-9]|[01][0-9]|2[0123]):([0-9]|[012345][0-9]):([0-9]|[012345][0-9]) ([A-Z]([a-z]){2,8}) (([12][0-9])|(3[01])|([0][1-9])) ((199[3-9])|(20[012][0-9])|(203[0-5]))";
        }
        description "type definition for KEYCHAIN_DATE_TIME_T";
    }    grouping key-chain-config {
        description
            "Grouping for key-chain configuration name";
        leaf name  {
            type  string {
                length "1..1965";
                pattern "[^?' =,>|]+";
            }
            description "Use this attribute to configure a key chain with a key chain name";
        } // END of name definition.

    } // END of key-chain-config definition.
    grouping key-chain-key-config {
        description
            "Grouping for key-style parameters configuration";
        leaf key-id  {
            type  uint32 {
                 range "0..2147483647"  {
                    description "0..2147483647: Supported range 0 - 2147483647";
                 }
            }
            description "Use this attribute to manageCOMMA add or delete authentication keys in
                        a key-chain";
        } // END of key-id definition.

        choice key-style {
            description
                "Key string styles";
            case key-string {

                description
                    "Key string in ASCII format";

                leaf key-string  {
                    type  string {
                        length "1..80";
                        pattern "[^?' =,>|]+";
                    }
                    description "Use this attribute to define a password to be used by a key";
                } // END of key-string definition.

            }
            case hexadecimal {

                description
                    "Key in hexadecimal string format";

                leaf encrypted  {
                    type  keychain_hex_string_t {
                        length "18..218";
                    }
                    description "Use this attribute to pass the key string in hexadecimal string format";
                } // END of encrypted definition.

            }
        } // END of key-style-choice definition.
    } // END of key-chain-key-config definition.
    grouping key-chain-key-lifetime-for-accept {
        description
            "Grouping for configuring key lifetime";
        leaf start-date-time-for-accept  {
            // when " ipi-keychain:key-chains/key-chain/keys/key-list/accept-lifetime/config/end-date-time-for-accept + ipi-keychain:key-chains/key-chain/keys/key-list/accept-lifetime/config/infinite-for-accept + ipi-keychain:key-chains/key-chain/keys/key-list/accept-lifetime/config/duration-for-accept ";
            type  keychain_date_time_t {
                length "1..1965";
            }
            description "Configure the start date-time of the key for accept-lifetime";
        } // END of start-date-time-for-accept definition.

        choice end-time {
            description
                "Choice for selecting the end time";
            case end-time {

                description
                    "End time setting";

                leaf end-date-time-for-accept  {
                    // when " ../start-date-time-for-accept ";
                    type  keychain_date_time_t {
                        length "1..1965";
                    }
                    description "Configure the end date-time of the key for accept-lifetime";
                } // END of end-date-time-for-accept definition.

            }
            case infinite {

                description
                    "The key end-life-time is infinite";

                leaf infinite-for-accept  {
                    // when " ../start-date-time-for-accept ";
                    type  empty;
                    description "Configure the end date-time of the key for accept-lifetime to be
                                infinite";
                } // END of infinite-for-accept definition.

            }
            case duration {

                description
                    "Duration in seconds";

                leaf duration-for-accept  {
                    // when " ../start-date-time-for-accept ";
                    type  uint32 {
                         range "1..2147483646"  {
                            description "1..2147483646: Supported range 1 - 2147483646";
                         }
                    }
                    description "Configure the duration of the key for accept-lifetime";
                } // END of duration-for-accept definition.

            }
        } // END of end-time-choice definition.
    } // END of key-chain-key-lifetime-for-accept definition.
    grouping key-chain-key-lifetime-for-send {
        description
            "Grouping for configuring key lifetime";
        leaf start-date-time-for-send  {
            // when " ipi-keychain:key-chains/key-chain/keys/key-list/send-lifetime/config/end-date-time-for-send + ipi-keychain:key-chains/key-chain/keys/key-list/send-lifetime/config/infinite-for-send + ipi-keychain:key-chains/key-chain/keys/key-list/send-lifetime/config/duration-for-send ";
            type  keychain_date_time_t {
                length "1..1965";
            }
            description "Configure the start date-time of the key for send-lifetime";
        } // END of start-date-time-for-send definition.

        choice end-time {
            description
                "Choice for selecting the end time";
            case end-time {

                description
                    "End time setting";

                leaf end-date-time-for-send  {
                    // when " ../start-date-time-for-send ";
                    type  keychain_date_time_t {
                        length "1..1965";
                    }
                    description "Configure the end date-time of the key for send-lifetime";
                } // END of end-date-time-for-send definition.

            }
            case infinite {

                description
                    "The key end-life-time is infinite";

                leaf infinite-for-send  {
                    // when " ../start-date-time-for-send ";
                    type  empty;
                    description "Configure the end date-time of the key for send-lifetime to be
                                infinite";
                } // END of infinite-for-send definition.

            }
            case duration {

                description
                    "Duration in seconds";

                leaf duration-for-send  {
                    // when " ../start-date-time-for-send ";
                    type  uint32 {
                         range "1..2147483646"  {
                            description "1..2147483646: Supported range 1 - 2147483646";
                         }
                    }
                    description "Configure the duration of the key for send-lifetime";
                } // END of duration-for-send definition.

            }
        } // END of end-time-choice definition.
    } // END of key-chain-key-lifetime-for-send definition.

    grouping  key-chains-grouping {
    description
        "All configured key-chains on the device";
    container key-chains {
        description
            "All configured key-chains on the device";

        list key-chain {
            key "name";
            description
                "List of key-chains";
            leaf name  {
                type  leafref {
                    path  "../config/name";
                }
                description "key-chain name";
            } // END of name definition.

            container config {
                description
                    "Configuration parameters for Key-chain";
                uses key-chain-config;
            } // END of config-container definition.
            container state {
                config false;
                description
                    "Operational state parameters for Key-chain";
                uses key-chain-config;
            } // END of state-container definition.
            container keys {
                description
                    "Configuration parameters for the specified keys";

                list key-list {
                    key "key-id";
                    description
                        "Single key in key chain";
                    leaf key-id  {
                        type  leafref {
                            path  "../config/key-id";
                        }
                        description "Use this attribute to manageCOMMA add or delete authentication keys in
                                    a key-chain";
                    } // END of key-id definition.

                    container config {
                        description
                            "Configuration parameters for a specific key-id";
                        uses key-chain-key-config;
                    } // END of config-container definition.
                    container state {
                        config false;
                        description
                            "Operational state parameters for the specified key";
                        uses key-chain-key-config;
                    } // END of state-container definition.
                    container accept-lifetime {
                        description
                            "Lifetime specification for accept-lifetime";
                        container config {
                            description
                                "Configure the accept-lifetime";
                            uses key-chain-key-lifetime-for-accept;
                        } // END of config-container definition.
                        container state {
                            config false;
                            description
                                "Operational state parameters for accept-lifetime";
                            uses key-chain-key-lifetime-for-accept;
                        } // END of state-container definition.
                    } // END of accept-lifetime-container definition.
                    container send-lifetime {
                        description
                            "Lifetime specification for send-lifetime";
                        container config {
                            description
                                "Configure the send-lifetime";
                            uses key-chain-key-lifetime-for-send;
                        } // END of config-container definition.
                        container state {
                            config false;
                            description
                                "Operational state parameters for send-lifetime";
                            uses key-chain-key-lifetime-for-send;
                        } // END of state-container definition.
                    } // END of send-lifetime-container definition.
                } // End of key-list-list
            } // END of keys-container definition.
        } // End of key-chain-list
    } // END of key-chains-container definition.
    } // END of key-chains-grouping definition.

    uses key-chains-grouping;

}
