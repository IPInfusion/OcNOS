/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pcep-lsp.yang
*
*/

submodule ipi-pcep-lsp {

    yang-version 1.1;

    belongs-to  ipi-pcep { prefix ipi-pcep; }

    import feature-list {
        prefix feature-list;
        revision-date 2026-09-15;
    }

    import ipi-pcep-types {
        prefix ipi-pcep-types;
        revision-date 2024-09-05;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for PCEP Entity LSP";


    revision "2023-08-04" {
        description "Added drop-attr-name tag at lsp-database container";
        reference " 0.3.0.";
    }

    revision "2021-09-03" {
        description "Update descriptions of attribute";
        reference " 0.2.0.";
    }

    revision "2021-03-02" {
        description "Initial version of PCEP LSP datamodel";
        reference " 0.1.0.";
    }

    grouping pcep-lsp-state {
        description
            "Operation data related to LSP identification";
        leaf lsp-id  {
            type  uint32;
            description "Identifier in the SENDER_TEMPLATE and the FILTER_SPEC that
                        can be changed to allow a sender to share resources with itself.";
        } // END of lsp-id definition.

        leaf operational-state  {
            type  ipi-pcep-types:pcep_lsp_oper_status_t;
            description "Operational status of the LSP.";
        } // END of operational-state definition.

        leaf last-lsp-error  {
            type  ipi-pcep-types:pcep_lsp_error_t;
            description "Last error for the LSP.";
        } // END of last-lsp-error definition.

    } // END of pcep-lsp-state definition.
    grouping pcep-tunnel-state {
        description
            "Operational data of PCEP LSP database";
        leaf plsp-id  {
            type  uint32;
            description "PCEP-specific identifier for the LSP.";
        } // END of plsp-id definition.

        leaf tunnel-id  {
            type  uint32;
            description "Tunnel identifier used in the session that remains constant
                        over the life of the tunnel.";
        } // END of tunnel-id definition.

        leaf candidate-path-id  {
            if-feature feature-list:HAVE_PCEP_SR;
            type  uint32;
            description "Segment routing candidate path identifier.";
        } // END of candidate-path-id definition.

        leaf source  {
            type  inet:ipv4-address;
            description "Tunnel sender address extracted from SENDER_TEMPLATE object.";
        } // END of source definition.

        leaf destination  {
            type  inet:ipv4-address;
            description "Tunnel endpoint address extracted from SESSION object.";
        } // END of destination definition.

        leaf extended-tunnel-id  {
            type  inet:ipv4-address;
            description "Extended tunnel ID of the LSP.";
        } // END of extended-tunnel-id definition.

        leaf admin-state  {
            type  boolean;
            description "Set to true, if desired operational state is active.";
        } // END of admin-state definition.

        leaf symbolic-name  {
            type  string {
                length "1..1965";
                pattern "[^?' =,>|]+";
            }
            description "Symbolic path name associated with the LSP.";
        } // END of symbolic-name definition.

        leaf tunnel-name  {
            type  string {
                length "1..1965";
                pattern "[^?' =,>|]+";
            }
            description "Tunnel name of the LSP.";
        } // END of tunnel-name definition.

        leaf setup-type  {
            type  ipi-pcep-types:pcep_lsp_setup_type_t;
            description "Path Setup Type.";
        } // END of setup-type definition.

        leaf local-policy-active  {
            type  empty;
            description "If set, Tunnel Local Policy is in effect";
        } // END of local-policy-active definition.

        leaf request-id  {
            type  uint32;
            description "Path request identification of the tunnel.";
        } // END of request-id definition.

        leaf request-state  {
            type  ipi-pcep-types:pcep_tunnel_request_state_t;
            description "Path request state.";
        } // END of request-state definition.

        leaf request-flags  {
            type  ipi-pcep-types:pcep_tunnel_request_flags_t;
            description "Path request information.";
        } // END of request-flags definition.

        leaf error-flags  {
            type  ipi-pcep-types:pcep_tunnel_err_flags_t;
            description "Path request error information.";
        } // END of error-flags definition.

        leaf recent-lsp-id  {
            if-feature feature-list:HAVE_PCEP_RSVP;
            type  uint32;
            description "Recent lsp-id of tunnel with TE metric configured.";
        } // END of recent-lsp-id definition.

        leaf pending-updates  {
            type  empty;
            description "If set, pending updates are available to for this tunnel.";
        } // END of pending-updates definition.

        leaf last-event  {
            type  ipi-pcep-types:pcep_tunnel_recent_event_t;
            description "Tunnel FSM Recent Event.";
        } // END of last-event definition.

    } // END of pcep-tunnel-state definition.
    grouping pcep-lsp-delegation-state {
        description
            "Operational data corresponds to LSPs delegation";
        leaf enabled  {
            type  empty;
            description "Whether the LSP is delegated or not.";
        } // END of enabled definition.

        leaf address  {
            type  inet:ipv4-address;
            description "The PCC, the reference to the PCEP peer to which LSP is
                        delegated; at the PCE, the reference to the PCEP peer
                        which delegated this LSP.";
        } // END of address definition.

        leaf stateful-request-parameter-id  {
            type  uint32;
            description "Last SRP-ID-number associated with this LSP.";
        } // END of stateful-request-parameter-id definition.

    } // END of pcep-lsp-delegation-state definition.
    grouping pcep-lsp-initiation-state {
        description
            "pcep-lsp-initiation-state";
        leaf enabled  {
            type  empty;
            description "Set to true if this LSP is initiated by a PCE.";
        } // END of enabled definition.

        leaf address  {
            type  inet:ipv4-address;
            description "The PCC, the reference to the PCEP peer that initiated
                        this LSP; at the PCE, the reference to the PCEP peer
                        where the LSP is initiated.";
        } // END of address definition.

    } // END of pcep-lsp-initiation-state definition.
    grouping pcep-lsp-binding-state {
        description
            "pcep-lsp-binding-state";
        leaf label-value  {
            type  uint32;
            description "LSP binding label value.";
        } // END of label-value definition.

        leaf allocation-mode  {
            type  ipi-pcep-types:pcep_binding_alloc_mode_t;
            description "Binding label identifier allocation mode.";
        } // END of allocation-mode definition.

    } // END of pcep-lsp-binding-state definition.
    grouping pcep-lsp-database {
        description
            "PCEP entity LSP databse grouping";
        container lsp-database {
            description
                "PCEP entity lsp database";

            list ingress-tunnel {
                key "plsp-id";
                config false;
                description
                    "List of all operational ingress LSP in the association";
                leaf plsp-id  {
                    type  leafref {
                        path  "../state/plsp-id";
                    }
                    description "PCEP-specific identifier for the LSP.";
                } // END of plsp-id definition.


                list lsp {
                    key "lsp-id";
                    config false;
                    description
                        "This container defines the LSP specific information";
                    leaf lsp-id  {
                        type  leafref {
                            path  "../state/lsp-id";
                        }
                        description "Identifier for the LSP.";
                    } // END of lsp-id definition.

                    container state {
                        config false;
                        description
                            "This container defined the LSP specific state";
                        uses pcep-lsp-state;
                    } // END of state-container definition.
                    container binding-label-status {
                        config false;
                        description
                            "This container defines the Binding Label details for the LSP";
                        container state {
                            config false;
                            description
                                "This container defined the Binding label details for the computated
                                        LSP state";
                            uses pcep-lsp-binding-state;
                        } // END of state-container definition.
                    } // END of binding-label-status-container definition.
                } // End of lsp-list
                container state {
                    config false;
                    description
                        "Operational state data";
                    uses pcep-tunnel-state;
                } // END of state-container definition.
                container pce-delegation {
                    config false;
                    description
                        "The delegation related parameters";
                    container state {
                        config false;
                        description
                            "Operational state data";
                        uses pcep-lsp-delegation-state;
                    } // END of state-container definition.
                } // END of pce-delegation-container definition.
                container initiation {
                    config false;
                    description
                        "The PCE initiation related parameters";
                    container state {
                        config false;
                        description
                            "Operational state data";
                        uses pcep-lsp-initiation-state;
                    } // END of state-container definition.
                } // END of initiation-container definition.
            } // End of ingress-tunnel-list
        } // END of lsp-database-container definition.
    } // END of pcep-lsp-database definition.


}
