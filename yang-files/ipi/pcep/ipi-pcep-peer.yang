/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pcep-peer.yang
*
*/

submodule ipi-pcep-peer {

    yang-version 1.1;

    belongs-to  ipi-pcep { prefix ipi-pcep; }

    import feature-list {
        prefix feature-list;
        revision-date 2026-09-15;
    }

    import ipi-pcep-types {
        prefix ipi-pcep-types;
        revision-date 2024-09-05;
    }

    import ietf-yang-types {
        prefix yang;
        revision-date 2013-07-15;
    }

    include ipi-pcep-stats { revision-date 2021-09-03;}
    organization
        "IP Infusion Inc.";

    contact
        "Address: 3965 Freedom Circle, Suite 200, Santa Clara, CA 95054
         Phone: +1 408-400-1900
         E-mail: support@ipinfusion.com
         Web: http://www.ipinfusion.com/";

    description
        "Datamodel for PCEP Peer";


    revision "2024-09-05" {
        description "Changed the description of ISIS TRAP nofication";
        reference " 0.6.0.";
    }

    revision "2023-08-04" {
        description "Removed cliprendstr for pce and added for *";
        reference " 0.5.1.";
    }

    revision "2023-07-18" {
        description "Added enclosing container for peer objectlist";
        reference " 0.5.0.";
    }

    revision "2021-09-03" {
        description "Update descriptions of attribute";
        reference " 0.4.0.";
    }

    revision "2021-03-02" {
        description "Change to have new datatype for couple of atributes";
        reference " 0.3.0.";
    }

    revision "2020-12-15" {
        description "Change to have data-types in lower case instead of camel case";
        reference " 0.2.0.";
    }

    revision "2018-06-21" {
        description "Initial version of PCEP Peer datamodel";
        reference " 0.1.0.";
    }

    grouping pcep-peer-config {
        description
            "Configuration data related to the PCEP peer";
        leaf address  {
            type  ipi-pcep-types:pcep_ip_addr_t;
            description "The local Internet address of this PCEP peer.";
        } // END of address definition.

        leaf delegation-preference  {
            type  uint32 {
                 range "1..65535"  {
                    description "1..65535: Supported range 1 - 65535";
                 }
            }
            description "The PCE peer delegation preference.";
        } // END of delegation-preference definition.

        leaf authentication-key  {
            if-feature feature-list:HAVE_TCP_MD5SIG;
            type  string {
                length "1..1965";
                pattern "[^?' =,>|]+";
            }
            description "The authentication option.";
        } // END of authentication-key definition.

    } // END of pcep-peer-config definition.
    grouping pcep-peer-state {
        description
            "Operation data related to PCEP peer";
        leaf role  {
            type  ipi-pcep-types:pcep_role_t;
            description "The role of the PCEP Peer.
                        Takes one of the following values.
                        - unknown(0): this PCEP peer role is not known.
                        - pcc(1): this PCEP peer is a PCC.
                        - pce(2): this PCEP peer is a PCE.
                        - pcc-and-pce(3): this PCEP peer
                        is both a PCC and a PCE.";
        } // END of role definition.

        leaf session-exists  {
            type  empty;
            description "Indicates whether a session with this peer currently exists.";
        } // END of session-exists definition.

        leaf session-up-time  {
            type  yang:timestamp;
            description "The timestamp value of the last time a
                        session with this peer was successfully
                        established.";
        } // END of session-up-time definition.

        leaf session-fail-time  {
            type  yang:timestamp;
            description "The timestamp value of the last time a
                        session with this peer failed to be established.";
        } // END of session-fail-time definition.

    } // END of pcep-peer-state definition.
    grouping pcep-peer-session-state {
        description
            "Operation data related to PCC peers session.";
        leaf initiator  {
            type  ipi-pcep-types:pcep_initiator_t;
            description "Initiator of the session,that is,
                        whether the TCP connection was initiated by the
                        local PCEP entity or the peer.";
        } // END of initiator definition.

        leaf state  {
            type  ipi-pcep-types:pcep_session_state_t;
            description "The current state of the session.
                        The set of possible states excludes the
                        idle state since entries do not exist
                        in the idle state.";
        } // END of state definition.

        leaf state-changes  {
            type  uint32;
            description "The number of times session state change happended.";
        } // END of state-changes definition.

        leaf state-last-change  {
            type  yang:timestamp;
            description "The timestamp value at the time this session entered its current state
                        as
                        denoted by the state leaf.";
        } // END of state-last-change definition.

        leaf creation-time  {
            type  yang:timestamp;
            description "Timestamp value at the time this session was created.";
        } // END of creation-time definition.

        leaf connect-retry  {
            type  yang:counter32;
            description "The number of times that the local PCEP
                        entity has attempted to establish a TCP
                        connection for this session without
                        success. The PCEP entity gives up when
                        this reaches connect-max-retry.";
        } // END of connect-retry definition.

        leaf open-retry  {
            type  uint8;
            description "The number of times that the local PCEP entity has attempted to send
                        open message
                        for this session without success.";
        } // END of open-retry definition.

        leaf local-id  {
            type  uint8;
            description "The value of the PCEP session ID used by
                        the local PCEP entity in the Open message
                        for this session. If state is tcp-pending
                        then this is the session ID that will be
                        used in the Open message. Otherwise, this
                        is the session ID that was sent in the
                        Open message.";
        } // END of local-id definition.

        leaf remote-id  {
            type  uint8;
            description "The value of the PCEP session ID used by the
                        peer in its Open message for this session.";
        } // END of remote-id definition.

        leaf peer-overloaded  {
            type  boolean;
            description "If the peer has informed the local PCEP entity
                        that it is currently overloaded, then this is
                        set to true. Otherwise, it is set to false.";
        } // END of peer-overloaded definition.

        leaf peer-overload-time  {
            type  uint32;
            units "seconds";
            description "The interval of time that is remaining until
                        the peer will cease to be overloaded.  If it
                        is not known how long the peer will stay in
                        overloaded state, this leaf is set to zero.";
        } // END of peer-overload-time definition.

        leaf keepalive-timer  {
            type  uint8;
            units "seconds";
            description "The agreed maximum interval at which the local
                        PCEP entity transmits PCEP messages on this PCEP
                        session.  Zero means that the local PCEP entity
                        never sends Keepalives on this session.";
        } // END of keepalive-timer definition.

        leaf peer-keepalive-timer  {
            type  uint8;
            units "seconds";
            description "The agreed maximum interval at which the peer
                        transmits PCEP messages on this PCEP session.
                        Zero means that the peer never sends Keepalives
                        on this session.";
        } // END of peer-keepalive-timer definition.

        leaf dead-timer  {
            type  uint8;
            units "seconds";
            description "Dead timer interval for this PCEP session.";
        } // END of dead-timer definition.

        leaf peer-dead-timer  {
            type  uint8;
            units "seconds";
            description "The peer's dead-timer interval
                        for this PCEP session.";
        } // END of peer-dead-timer definition.

        leaf keepalive-hold-timer-remain  {
            type  uint8;
            units "seconds";
            description "The keep alive hold time remaining for this session.";
        } // END of keepalive-hold-timer-remain definition.

        leaf max-unknown-message  {
            type  uint32;
            description "Maximum number of unknown messages that any session
                        on this PCEP entity is willing to accept per minute.";
        } // END of max-unknown-message definition.

    } // END of pcep-peer-session-state definition.
    grouping pcep-peer-capability-state {
        description
            "Peer Capability information state";
        leaf pce-instantiate  {
            type  empty;
            description "PCE-initiated LSP capability.";
        } // END of pce-instantiate definition.

        leaf segment-routing  {
            if-feature feature-list:HAVE_PCEP_SR;
            type  empty;
            description "PCE segment-routing capability.";
        } // END of segment-routing definition.

        leaf lsp-update  {
            type  empty;
            description "PCE Update capability.";
        } // END of lsp-update definition.

    } // END of pcep-peer-capability-state definition.
    grouping pcep-peer-capability {
        description
            "Peer Capability information grouping";
        container capability {
            config false;
            description
                "Peer capability information";
            container state {
                config false;
                description
                    "Peer Capability state data";
                uses pcep-peer-capability-state;
            } // END of state-container definition.
        } // END of capability-container definition.
    } // END of pcep-peer-capability definition.
    grouping pcep-peer-session {
        description
            "Peer session information";
        container session {
            config false;
            description
                "The entry represents a single PCEP         session in which the local
                        PCEP entity participates.";
            container state {
                config false;
                description
                    "Peer Session state data";
                uses pcep-peer-session-state;
            } // END of state-container definition.
        } // END of session-container definition.
    } // END of pcep-peer-session definition.

    grouping  peers-grouping {
    description
        "Top level container for PCEP peers";
    container peers {
        if-feature feature-list:HAVE_PCEP;
        description
            "Top level container for PCEP peers";

        list peer {
            key "address";
            description
                "The list of configured peers for the entity (remote PCE)";
            leaf address  {
                type  leafref {
                    path  "../config/address";
                }
                description "The local Internet address of this PCEP peer.";
            } // END of address definition.

            container config {
                description
                    "Configuration data of the peer";
                uses pcep-peer-config;
            } // END of config-container definition.
            container state {
                config false;
                description
                    "Operational state data";
                uses pcep-peer-config;
                uses pcep-peer-state;
                uses pcep-peer-counters;
            } // END of state-container definition.
            uses pcep-peer-capability;
            uses pcep-peer-session;
        } // End of peer-list
    } // END of peers-container definition.
    } // END of peers-grouping definition.


}
