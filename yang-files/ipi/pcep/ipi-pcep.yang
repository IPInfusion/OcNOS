/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pcep.yang
*
*/

module ipi-pcep {

    yang-version 1.1;

    namespace   "http://www.ipinfusion.com/yang/ocnos/ipi-pcep";

    prefix "ipi-pcep";

    import ipi-pcep-types {
        prefix ipi-pcep-types;
        revision-date 2024-09-05;
    }

    import ietf-yang-types {
        prefix yang;
        revision-date 2013-07-15;
    }

    import ietf-inet-types {
        prefix inet;
        revision-date 2013-07-15;
    }

    import cml-data-types {
        prefix cml-data-types;
        revision-date 2026-05-15;
    }

    import feature-list {
        prefix feature-list;
        revision-date 2026-09-15;
    }

    include ipi-pcep-lsp { revision-date 2023-08-04;}
    include ipi-pcep-peer { revision-date 2024-09-05;}
    include ipi-pcep-stats { revision-date 2021-09-03;}
    organization
        "IP Infusion Inc.";

    contact
        "Address: 3965 Freedom Circle, Suite 200, Santa Clara, CA 95054
         Phone: +1 408-400-1900
         E-mail: support@ipinfusion.com
         Web: http://www.ipinfusion.com/";

    description
        "Datamodel for PCEP Entity";


    revision "2024-09-05" {
        description "Changed the description of ISIS TRAP nofication";
        reference " 0.9.0.";
    }

    revision "2024-03-26" {
        description "Removal of default trigger for pce instantiation";
        reference " 0.8.1.";
    }

    revision "2024-02-15" {
        description "Added implicit delete tag for config container of srv6-spirent-comp";
        reference " 0.8.0.";
    }

    revision "2023-08-04" {
        description "Removed cliprependstr for peer";
        reference " 0.7.1.";
    }

    revision "2023-07-18" {
        description "Added enclosing container for entity and peer objectlists";
        reference " 0.7.0.";
    }

    revision "2023-02-24" {
        description "Added When tag for no-debug-all command";
        reference " 0.6.0.";
    }

    revision "2022-09-30" {
        description "Import cml-data-types used by notifications";
        reference " 0.4.3.";
    }

    revision "2022-08-10" {
        description "Debug hierarchy change";
        reference " 0.5.1.";
    }

    revision "2022-08-09" {
        description "Updation of pcep srv6 hidden-cli helpstring";
        reference " 0.4.2.";
    }

    revision "2022-07-30" {
        description "Update db triggers";
        reference " 0.5.0.";
    }

    revision "2021-09-03" {
        description "Update descriptions of attribute";
        reference " 0.4.0.";
    }

    revision "2021-03-02" {
        description "Addition of new attrs in lsp-datbase and moved lsp operational data to a new lsp subbmodule";
        reference " 0.3.0.";
    }

    revision "2020-12-15" {
        description "Change to have data-types in lower case instead of camel case";
        reference " 0.2.0.";
    }

    revision "2018-06-21" {
        description "Initial version of PCEP datamodel";
        reference " 0.1.0.";
    }

    grouping pcep-entity-config {
        description
            "Configuration data for pcep entity";
        leaf entity-id  {
            type  uint32 {
                 range "1..255"  {
                    description "1..255: Supported range 1 - 255";
                 }
            }
            description "This attribute is used to configure PCEP Entity.";
        } // END of entity-id definition.

        leaf keep-alive-interval  {
            type  uint8 {
                 range "0..255"  {
                    description "0..255: Supported range 0 - 255";
                 }
            }
            units "seconds";
            default "30";
            description "This attribute is used to set the keep alive transmission
                        timer that this PCEP entity will propose in the initial OPEN
                        message of each session it is involved in.  This is the
                        maximum time between two consecutive messages sent
                        to a peer. Zero means that the PCEP entity prefers
                        not to send Keepalives at all.";
        } // END of keep-alive-interval definition.

        leaf dead-interval  {
            type  uint8 {
                 range "1..255"  {
                    description "1..255: Supported range 1 - 255";
                 }
            }
            units "seconds";
            default "120";
            description "This attribute is used to set the dead timer
                        that this PCEP entity will propose
                        in the initial OPEN message of each session it is
                        involved in. This is the time after which a peer
                        should declare a session down if it does not
                        receive any PCEP messages.";
        } // END of dead-interval definition.

        leaf request-timeout  {
            type  uint16 {
                 range "1..20"  {
                    description "1..20: Supported range 1 - 20";
                 }
            }
            units "seconds";
            default "10";
            description "This attribute is used to set the maximum time
                        that the PCEP entity will wait for a response to a PCReq message.";
        } // END of request-timeout definition.

        leaf tolerance-keepalive  {
            type  uint32 {
                 range "1..255"  {
                    description "1..255: Supported range 1 - 255";
                 }
            }
            description "This attribute is used to set the tolerance value for keep-alive
                        timer.";
        } // END of tolerance-keepalive definition.

        leaf tolerance-dead-interval  {
            type  uint32 {
                 range "1..255"  {
                    description "1..255: Supported range 1 - 255";
                 }
            }
            description "This attribute is used to set the tolerance value for dead interval
                        timer.";
        } // END of tolerance-dead-interval definition.

        leaf cool-off-timeout  {
            type  int32 {
                 range "1..300"  {
                    description "1..300: Supported range 1 - 300";
                 }
            }
            description "This attribute is used to set Flap dampening time.";
        } // END of cool-off-timeout definition.

        leaf source-address  {
            type  inet:ip-address;
            description "This attribute is used to configure the local Internet address
                        of this PCEP entity.
                        If operating as a PCE server, the PCEP entity
                        listens on this address. If operating as a PCC,
                        the PCEP entity binds outgoing TCP connections
                        to this address. It is possible for the PCEP entity
                        to operate both as a PCC and a PCE Server, in which
                        case it uses this address both to listen for incoming
                        TCP connections and to bind outgoing TCP connections.";
        } // END of source-address definition.

        leaf recovery-policy  {
            type  ipi-pcep-types:pcep_dlg_recovery_type_t;
            default "removal";
            description "This attribute is used to configure delegation recovery policy.";
        } // END of recovery-policy definition.

    } // END of pcep-entity-config definition.
    grouping pcep-entity-state {
        description
            "Operational date related to pcep entity";
        leaf role  {
            type  ipi-pcep-types:pcep_role_t;
            description "The role that this entity can play.
                        Takes one of the following values.
                        - unknown(0): this PCEP Entity role is not known.
                        - pcc(1): this PCEP Entity is a PCC.
                        - pce(2): this PCEP Entity is a PCE.
                        - pcc-and-pce(3): this PCEP Entity is both
                        a PCC and a PCE.";
        } // END of role definition.

        leaf connect-timer  {
            type  uint32;
            units "seconds";
            description "The time in seconds that the PCEP entity will wait
                        to establish a TCP connection with a peer.  If a
                        TCP connection is not established within this time
                        then PCEP aborts the session setup attempt.";
        } // END of connect-timer definition.

        leaf connect-max-retry  {
            type  uint32;
            description "The maximum number of times the system tries to
                        establish a TCP connection to a peer before the
                        session with the peer transitions to the idle
                        state.";
        } // END of connect-max-retry definition.

        leaf init-backoff-timer  {
            type  uint32;
            units "seconds";
            description "The initial back-off time in seconds for retrying
                        a failed session setup attempt to a peer.
                        The back-off time increases for each failed
                        session setup attempt, until a maximum back-off
                        time is reached.  The maximum back-off time is
                        max-backoff-timer.";
        } // END of init-backoff-timer definition.

        leaf max-backoff-timer  {
            type  uint32;
            units "seconds";
            description "The maximum back-off time in seconds for retrying
                        a failed session setup attempt to a peer.
                        The back-off time increases for each failed session
                        setup attempt, until this maximum value is reached.
                        Session setup attempts then repeat periodically
                        without any further increase in back-off time.";
        } // END of max-backoff-timer definition.

        leaf open-wait-timer  {
            type  uint32;
            units "seconds";
            description "The time in seconds that the PCEP entity will wait
                        to receive an Open message from a peer after the
                        TCP connection has come up.
                        If no Open message is received within this time then
                        PCEP terminates the TCP connection and deletes the
                        associated sessions.";
        } // END of open-wait-timer definition.

        leaf keep-wait-timer  {
            type  uint32;
            units "seconds";
            description "The time in seconds that the PCEP entity will wait
                        to receive a Keepalive or PCErr message from a peer
                        during session initialization after receiving an
                        Open message.  If no Keepalive or PCErr message is
                        received within this time then PCEP terminates the
                        TCP connection and deletes the associated
                        sessions.";
        } // END of keep-wait-timer definition.

    } // END of pcep-entity-state definition.
    grouping pcep-entity-srv6-capability-config {
        description
            "Configuration data corresponds to PCE auto discovery information";
        leaf segment-routing-v6  {
            if-feature feature-list:HAVE_PCEP_SRV6;
            type  empty;
            description "This attribute is used to enable segment-routing ipv6 capability.";
        } // END of segment-routing-v6 definition.

    } // END of pcep-entity-srv6-capability-config definition.
    grouping pcep-entity-capability-config {
        description
            "Configuration data corresponds to PCE auto discovery information";
        leaf pce-instantiate  {
            type  empty;
            description "This attribute is used to enable PCE-initiated LSP
                        capability.";
        } // END of pce-instantiate definition.

        leaf segment-routing  {
            if-feature feature-list:HAVE_PCEP_SR;
            type  empty;
            description "This attribute is used to enable segment-routing capability.";
        } // END of segment-routing definition.

    } // END of pcep-entity-capability-config definition.
    grouping pcep-entity-capability {
        description
            "PCEP Entity capability grouping";
        container capability {
            description
                "The PCEP entity capability information of local PCEP entity";
            container config {
                description
                    "Configuration data relevant to PCE selection";
                uses pcep-entity-srv6-capability-config;
                uses pcep-entity-capability-config;
            } // END of config-container definition.
            container state {
                config false;
                description
                    "Operational state data of local PCEP entity";
                uses pcep-entity-srv6-capability-config;
                uses pcep-entity-capability-config;
            } // END of state-container definition.
        } // END of capability-container definition.
    } // END of pcep-entity-capability definition.
    grouping pcep-entity-flap-limit-config {
        description
            "Configurational data flap limitation";
        leaf flap-count  {
            // when " ../flap-interval ";
            type  int32 {
                 range "10..1000"  {
                    description "10..1000: Supported range 10 - 1000";
                 }
            }
            mandatory true;
            description "This attribute is used to set the number of flaps allowed.";
        } // END of flap-count definition.

        leaf flap-interval  {
            // when " ../flap-count ";
            type  int32 {
                 range "10..36000"  {
                    description "10..36000: Supported range 10 - 36000";
                 }
            }
            mandatory true;
            description "This attribute is used to set the flap interval time.";
        } // END of flap-interval definition.

    } // END of pcep-entity-flap-limit-config definition.
    grouping pcep-entity-flap-limit {
        description
            "PCEP entoty flap limit grouping";
        container flap-limit {
            description
                "Flap limit configuration";
            container config {
                presence "Configure flap-limit values";
                description
                    "Configuration data for flap-limit";
                uses pcep-entity-flap-limit-config;
            } // END of config-container definition.
            container state {
                config false;
                description
                    "Operational state data flap-limit";
                uses pcep-entity-flap-limit-config;
            } // END of state-container definition.
        } // END of flap-limit-container definition.
    } // END of pcep-entity-flap-limit definition.
    grouping pcep-entity-update-config {
        description
            "Configuration data related to update limitation";
        leaf count  {
            // when " ../interval ";
            type  int32 {
                 range "1..1000"  {
                    description "1..1000: Supported range 1 - 1000";
                 }
            }
            mandatory true;
            description "This attribute is used to set the number of allowed
                        updates.";
        } // END of count definition.

        leaf interval  {
            // when " ../count ";
            type  int32 {
                 range "10..36000"  {
                    description "10..36000: Supported range 10 - 36000";
                 }
            }
            mandatory true;
            description "This attribute is used to set time unit for updates
                        dampening.";
        } // END of interval definition.

    } // END of pcep-entity-update-config definition.
    grouping pcep-entity-update-limit {
        description
            "PCEP entity update limit grouping";
        container update-limit {
            description
                "Update limit configuration";
            container config {
                presence "Configure PCE update limit values";
                description
                    "Configuration data for update-limit";
                uses pcep-entity-update-config;
            } // END of config-container definition.
            container state {
                config false;
                description
                    "Operational state data of update-limit";
                uses pcep-entity-update-config;
            } // END of state-container definition.
        } // END of update-limit-container definition.
    } // END of pcep-entity-update-limit definition.
    grouping pcep-entity-stateful-config {
        description
            "Configuration data of stateful PCE parameters";
        leaf redelegation-timeout  {
            type  uint32 {
                 range "1..600"  {
                    description "1..600: Supported range 1 - 600";
                 }
            }
            units "seconds";
            default "60";
            description "This attribute is used to set the time period a PCC waits
                        before revoking LSP delegation to a PCE and attempting to
                        redelegate LSPs associated with the
                        terminated PCEP session to an alternate PCE.";
        } // END of redelegation-timeout definition.

        leaf lsp-state-timeout  {
            type  ipi-pcep-types:pcep_lsp_state_timeout_t;
            units "seconds";
            description "This attribute is used to set the time period a PCC waits
                        before flushing LSP state associated with the terminated PCEP
                        session and reverting to operator-defined default
                        parameters or behaviours.";
        } // END of lsp-state-timeout definition.

    } // END of pcep-entity-stateful-config definition.
    grouping pcep-entity-stateful {
        description
            "PCEP entoty stateful grouping";
        container stateful {
            description
                "The configured stateful PCE parameters";
            container config {
                description
                    "Configuration data for stateful PCE parameters";
                uses pcep-entity-stateful-config;
            } // END of config-container definition.
            container state {
                config false;
                description
                    "Operational state data for stateful PCE parameters";
                uses pcep-entity-stateful-config;
            } // END of state-container definition.
        } // END of stateful-container definition.
    } // END of pcep-entity-stateful definition.
    grouping pcep-init-lsp-config {
        description
            "Configuration data related to PCE init lsp limit";
        leaf lsp-limit  {
            type  uint32 {
                 range "1..1048575"  {
                    description "1..1048575: Supported range 1 - 1048575";
                 }
            }
            mandatory true;
            description "This attribute is used to set the starting Tunnel-id range
                        for the PCE initiated LSP.";
        } // END of lsp-limit definition.

    } // END of pcep-init-lsp-config definition.
    grouping pcep-init-lsp-top {
        description
            "PCEP init lsp limit grouping";
        container init-lsp-limit {
            description
                "LSP state associated with that PCEP session";
            container config {
                presence "Configure maximum allowed lsp limit value";
                description
                    "Configuration data with resect to PCE session";
                uses pcep-init-lsp-config;
            } // END of config-container definition.
            container state {
                config false;
                description
                    "Operational state data of LSP";
                uses pcep-init-lsp-config;
            } // END of state-container definition.
        } // END of init-lsp-limit-container definition.
    } // END of pcep-init-lsp-top definition.
    grouping pcep-debug-config {
        description
            "Configuration data related to pcep debugging options";
        leaf options  {
            type  ipi-pcep-types:pcep_debug_t;
            description "This attribute is used to enable/disable PCEP debug logs.";
        } // END of options definition.

    } // END of pcep-debug-config definition.
    grouping pcep-debug-state {
        description
            "Operational data related to pcep debugging options";
        leaf terminal-debug-status  {
            type  ipi-pcep-types:pcep_debug_t;
            description "PCEP terminal debug options.";
        } // END of terminal-debug-status definition.

    } // END of pcep-debug-state definition.
    grouping pcep-debug {
        description
            "PCEP debug grouping";
        container debug {
            description
                "PCEP debug information";
            container config {
                description
                    "Configuration data for debugging parameters";
                uses pcep-debug-config;
            } // END of config-container definition.
            container state {
                config false;
                description
                    "Operational data for debugging parameters";
                uses pcep-debug-config;
                uses pcep-debug-state;
            } // END of state-container definition.
        } // END of debug-container definition.
    } // END of pcep-debug definition.
    grouping pcep-srv6-spirent-comp-config {
        description
            "Configuration data related to pcep srv6 spirent compliance option";
        leaf srv6-spirent-comp  {
            type  empty;
            description "This attribute is used to enable/disable PCEP SRv6 spirent TLV value
                        compliance.";
        } // END of srv6-spirent-comp definition.

    } // END of pcep-srv6-spirent-comp-config definition.
    grouping pcep-srv6-spirent-comp {
        description
            "PCEP SRv6 spirent compliance grouping";
        container srv6-spirent-comp {
            description
                "PCEP SRv6 spirent compliance information";
            container config {
                description
                    "Configuration data for PCEP SRv6 spirent compliance parameters";
                uses pcep-srv6-spirent-comp-config;
            } // END of config-container definition.
            container state {
                config false;
                description
                    "Operational data for PCEP SRv6 spirent compliance parameters";
                uses pcep-srv6-spirent-comp-config;
            } // END of state-container definition.
        } // END of srv6-spirent-comp-container definition.
    } // END of pcep-srv6-spirent-comp definition.

    grouping  pcep-grouping {
    description
        "Generic configuration and operational model for PCEP entity";
    container pcep {
        if-feature feature-list:HAVE_PCEP;
        description
            "Generic configuration and operational model for PCEP entity";
        container entities {
            description
                "PCEP entity Element Configuration container";

            list entity {
                key "entity-id";
                description
                    "Path Computation Element Configurations";
                leaf entity-id  {
                    type  leafref {
                        path  "../config/entity-id";
                    }
                    description "PCEP Entity ID.";
                } // END of entity-id definition.

                container config {
                    description
                        "Configuration data of the PCEP entity on the device";
                    uses pcep-entity-config;
                } // END of config-container definition.
                container state {
                    config false;
                    description
                        "Operational state data of the PCEP entity on the device";
                    uses pcep-entity-config;
                    uses pcep-entity-state;
                } // END of state-container definition.
                uses pcep-entity-capability;
                uses pcep-entity-stateful;
                uses pcep-entity-flap-limit;
                uses pcep-entity-update-limit;
                uses pcep-lsp-database;
                uses peers-grouping;
            } // End of entity-list
        } // END of entities-container definition.
        uses pcep-init-lsp-top;
        uses pcep-debug;
        uses pcep-srv6-spirent-comp;
    } // END of pcep-container definition.
    } // END of pcep-grouping definition.

    uses pcep-grouping;

    rpc clear-pcep-peer-all {
        if-feature feature-list:HAVE_PCEP;
        description "Clear all PCEP Peer session";
    }

    rpc clear-pcep-peer {
        if-feature feature-list:HAVE_PCEP;
        description "Clear a PCEP peer session";
        input  {
            leaf address  {
                type inet:ip-address;
                mandatory true;
                description "The local Internet address of this PCEP peer.";
            }
        }
    }

    rpc clear-pcep-statistics {
        if-feature feature-list:HAVE_PCEP;
        description "Clear PCEP Peer statistics information";
    }

    rpc debug-pcep-all {
        if-feature feature-list:HAVE_PCEP;
        description "Enable all debugging functions of PCEP";
    }

    rpc pcep-terminal-debug-on {
        if-feature feature-list:HAVE_PCEP;
        description "Enable debugging functions of PCEP";
        input  {
            leaf terminal-debug-options  {
                type ipi-pcep-types:pcep_debug_t;
                mandatory true;
                description "PCEP terminal debug logs enabling options.";
            }
        }
    }

    rpc pcep-terminal-debug-off {
        if-feature feature-list:HAVE_PCEP;
        description "Disable debugging functions of PCEP";
        input  {
            leaf terminal-debug-options  {
                type ipi-pcep-types:pcep_debug_t;
                mandatory true;
                description "PCEP terminal debug logs disabling options.";
            }
        }
    }

    rpc clear-pcep-requests {
        if-feature feature-list:HAVE_PCEP;
        description "Clear PCEP request of a tunnel interface";
        input  {
            leaf tunnel-id  {
                type string;
                mandatory true;
                description "Tunnel identifier used in the session that remains constant over
                            the life of the tunnel.";
            }
        }
    }

    notification pcep-session-up {
        if-feature feature-list:HAVE_PCEP;

        description "This notification is sent when the pcep session comes up.";

        leaf severity {
            type cml-data-types:cml_notif_severity_t;
            description "Notification severity level (value: INFO)";
        }

        leaf eventClass {
            type cml-data-types:cml_notif_class_t;
            description "Notification event class (value: STATE)";
        }

        leaf address {
            type ipi-pcep-types:pcep_ip_addr_t;
        description
            "The local Internet address of this PCEP peer.";
        }

        leaf entity-id {
            type  uint32;
        description
            "PCEP Entity ID.";
        }

        leaf initiator {
            type ipi-pcep-types:pcep_initiator_t;
        description
            "Initiator of the session,that is,
                    whether the TCP connection was initiated by the
                    local PCEP entity or the peer.";
        }

        leaf state-last-change {
            type  yang:timestamp;
        description
            "The timestamp value at the time this session entered its current state
                    as
                    denoted by the state leaf.";
        }

        leaf state {
            type ipi-pcep-types:pcep_session_state_t;
        description
            "The current state of the session.
                    The set of possible states excludes the
                    idle state since entries do not exist
                    in the idle state.";
        }
    }

    notification pcep-session-down {
        if-feature feature-list:HAVE_PCEP;

        description "This notification is sent when the pcep session goes down.";

        leaf severity {
            type cml-data-types:cml_notif_severity_t;
            description "Notification severity level (value: CRITICAL)";
        }

        leaf eventClass {
            type cml-data-types:cml_notif_class_t;
            description "Notification event class (value: STATE)";
        }

        leaf address {
            type ipi-pcep-types:pcep_ip_addr_t;
        description
            "The local Internet address of this PCEP peer.";
        }

        leaf entity-id {
            type  uint32;
        description
            "PCEP Entity ID.";
        }

        leaf initiator {
            type ipi-pcep-types:pcep_initiator_t;
        description
            "Initiator of the session,that is,
                    whether the TCP connection was initiated by the
                    local PCEP entity or the peer.";
        }

        leaf state-last-change {
            type  yang:timestamp;
        description
            "The timestamp value at the time this session entered its current state
                    as
                    denoted by the state leaf.";
        }

        leaf state {
            type ipi-pcep-types:pcep_session_state_t;
        description
            "The current state of the session.
                    The set of possible states excludes the
                    idle state since entries do not exist
                    in the idle state.";
        }
    }

    notification pcep-session-peer-overload {
        if-feature feature-list:HAVE_PCEP;

        description "This notification is sent when a peer enters overload state.";

        leaf severity {
            type cml-data-types:cml_notif_severity_t;
            description "Notification severity level";
        }

        leaf eventClass {
            type cml-data-types:cml_notif_class_t;
            description "Notification event class (value: STATE)";
        }

        leaf address {
            type ipi-pcep-types:pcep_ip_addr_t;
        description
            "The local Internet address of this PCEP peer.";
        }

        leaf entity-id {
            type  uint32;
        description
            "PCEP Entity ID.";
        }

        leaf initiator {
            type ipi-pcep-types:pcep_initiator_t;
        description
            "Initiator of the session,that is,
                    whether the TCP connection was initiated by the
                    local PCEP entity or the peer.";
        }

        leaf peer-overloaded {
            type  boolean;
        description
            "If the peer has informed the local PCEP entity
                    that it is currently overloaded, then this is
                    set to true. Otherwise, it is set to false.";
        }

        leaf peer-overload-time {
            type  uint32;
        description
            "The interval of time that is remaining until
                    the peer will cease to be overloaded.  If it
                    is not known how long the peer will stay in
                    overloaded state, this leaf is set to zero.";
        }
    }

    notification pcep-session-peer-overload-clear {
        if-feature feature-list:HAVE_PCEP;

        description "This notification is sent when a peer leaves overload state.";

        leaf severity {
            type cml-data-types:cml_notif_severity_t;
            description "Notification severity level";
        }

        leaf eventClass {
            type cml-data-types:cml_notif_class_t;
            description "Notification event class (value: STATE)";
        }

        leaf address {
            type ipi-pcep-types:pcep_ip_addr_t;
        description
            "The local Internet address of this PCEP peer.";
        }

        leaf entity-id {
            type  uint32;
        description
            "PCEP Entity ID.";
        }

        leaf initiator {
            type ipi-pcep-types:pcep_initiator_t;
        description
            "Initiator of the session,that is,
                    whether the TCP connection was initiated by the
                    local PCEP entity or the peer.";
        }

        leaf peer-overloaded {
            type  boolean;
        description
            "If the peer has informed the local PCEP entity
                    that it is currently overloaded, then this is
                    set to true. Otherwise, it is set to false.";
        }
    }

}
