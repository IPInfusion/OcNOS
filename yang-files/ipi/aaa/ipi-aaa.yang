/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-aaa.yang
*
*/

module ipi-aaa {

    yang-version 1.1;

    namespace   "http://www.ipinfusion.com/yang/ocnos/ipi-aaa";

    prefix "ipi-aaa";

    import cml-data-types {
        prefix cml-data-types;
        revision-date 2026-05-15;
    }

    import ipi-aaa-types {
        prefix ipi-aaa-types;
        revision-date 2024-07-15;
    }

    import ipi-vrf {
        prefix ipi-vrf;
        revision-date 2026-08-12;
    }

    import ipi-network-instance {
        prefix ipi-network-instance;
        revision-date 2026-08-12;
    }

    import ipi-user-management-types {
        prefix ipi-user-management-types;
        revision-date 2024-09-29;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 aaa configurations";


    revision "2026-02-06" {
        description "Reverting aaa-method-rules to a separate container fix.";
        reference " 0.13.4.";
    }

    revision "2026-02-04" {
        description "Corrected xPathExpr for aaa server-group";
        reference " 0.13.3.";
    }

    revision "2026-02-03" {
        description "Moved aaa-method-rules to a separate container to keep the dependent object with the server group.";
        reference " 0.13.2.";
    }

    revision "2025-12-05" {
        description "Added 'skip-yang' flag to group-type when tag";
        reference " 0.13.1.";
    }

    revision "2025-11-26" {
        description "Removed enable-fallback attr from unset of fallback error local non-existent-user for login default and login console group to handle bulk commit issue.";
        reference " 0.13.0.";
    }

    revision "2025-11-13" {
        description "Added when tag to handle validation during commit dry-run.";
        reference " 0.12.2.";
    }

    revision "2025-09-25" {
        description "Fixed duplicate 'server' keyword in AAA group CLI by updating the CLI flags.";
        reference " 0.12.1.";
    }

    revision "2025-08-17" {
        description "Added dependentObject for user-expday and role_expday objectlist";
        reference " 0.12.0.";
    }

    revision "2025-08-13" {
        description "Updated when tag to delete TACACS-related server groups when the feature is disabled.";
        reference " 0.11.0.";
    }

    revision "2025-04-16" {
        description "Added CML_UNIQUE flag for server group name";
        reference " 0.10.0.";
    }

    revision "2025-02-12" {
        description "Added dependent object tags to handle unset of configs during rollback";
        reference " 0.9.4.";
    }

    revision "2024-12-07" {
        description "Added separate set/unset cli for default aaa authentication login fallback error local and updated the non-existent datatype to CML_EMPTY_T";
        reference " 0.9.3.";
    }

    revision "2024-11-22" {
        description "Updated the non-existent-user datatype to CML_EMPTY_T";
        reference " 0.9.2.";
    }

    revision "2024-11-15" {
        description "Added separate unset cli for default and console authentication/authorization/accounting";
        reference " 0.9.1.";
    }

    revision "2024-09-29" {
        description "Updated revision date due updates on import module ipi-user-management-types";
        reference " 0.9.0.";
    }

    revision "2024-08-20" {
        description "Added when tag for objectlist role-expday";
        reference " 0.8.2.";
    }

    revision "2024-07-25" {
        description "Update to support user-defined VRF";
        reference " 0.8.2.";
    }

    revision "2024-07-19" {
        description "Added new cli to config expiry for user/role";
        reference " 0.8.1.";
    }

    revision "2024-07-15" {
        description "Removed pattern tag validation from AAA group Server name";
        reference " 0.8.0.";
    }

    revision "2024-06-07" {
        description "Added when tag for attr disable-usercheck and modified autoPopulate-custom condition tag for /aaa/aaa-user/password-policy/config";
        reference " 0.7.4.";
    }

    revision "2024-05-28" {
        description "Added autoPopulate-custom condition tag for /aaa/aaa-user/password-policy/config";
        reference " 0.7.3.";
    }

    revision "2024-05-21" {
        description "Introduced new CLI to enable/disable password policy features";
        reference " 0.7.2.";
    }

    revision "2024-05-20" {
        description "Added trim whitespaces from group attr for authorization and accounting";
        reference " 0.7.0.";
    }

    revision "2024-05-08" {
        description "Added autoPopulate-custom tag for /aaa/aaa-user/password-policy/config";
        reference " 0.6.9.";
    }

    revision "2024-04-15" {
        description "Added pattern tag to resolve AAA group Server name";
        reference " 0.6.8.";
    }

    revision "2024-04-10" {
        description "Added trim whitespaces from group attr";
        reference " 0.6.7.";
    }

    revision "2024-02-28" {
        description "Introduced new CLIS to unconfigure the authentication local none";
        reference " 0.6.6.";
    }

    revision "2024-02-21" {
        description "Added role for clear-aaa-lockout cli";
        reference " 0.6.5.";
    }

    revision "2024-02-07" {
        description "Introduced new CLIS to support console authorization and accounting";
        reference " 0.6.4.";
    }

    revision "2023-11-29" {
        description "Introduced new CLI to configure password policy";
        reference " 0.6.3.";
    }

    revision "2023-10-10" {
        description "Added implicit delete tag to reslove db-sync issue";
        reference " 0.6.2.";
    }

    revision "2023-09-21" {
        description "Introduced new CLI for console auth fallback to local if user is not present in server";
        reference " 0.6.1.";
    }

    revision "2023-05-29" {
        description "Added When tag for no-debug-all command";
        reference " 0.6.0.";
    }

    revision "2023-04-13" {
        description "Intorduced new CLI to fallback to local if user is not present in server";
        reference " 0.5.9.";
    }

    revision "2023-03-27" {
        description "AAA console cli implementation";
        reference " 0.5.8.";
    }

    revision "2023-03-23" {
        description "Updated the username length from 15 to 32 characters";
        reference " 0.5.7.";
    }

    revision "2023-01-12" {
        description "Updated input for RDN attrs";
        reference " 0.5.6.";
    }

    revision "2022-11-22" {
        description "Updated container name of tacacs vrf list";
        reference " 0.5.5.";
    }

    revision "2022-11-16" {
        description "Updated missing cliprependstr tags";
        reference " 0.5.4.";
    }

    revision "2022-11-03" {
        description "Updated debug container description";
        reference " 0.5.3.";
    }

    revision "2022-08-23" {
        description "Added implicit_delete for aaa-user container";
        reference " 0.5.2.";
    }

    revision "2022-08-12" {
        description "Introduced attribute to provide Command level authorization feature support.";
        reference " 0.5.1.";
    }

    revision "2022-08-10" {
        description "Debug hierarchy change";
        reference " 0.5.0.";
    }

    revision "2022-07-21" {
        description "Removed the incorrect implicit_delete from datamodel";
        reference " 0.4.1.";
    }

    revision "2022-06-01" {
        description "Updated the yang file with feature";
        reference " 0.4.0.";
    }

    revision "2021-12-02" {
        description "Remodeled AAA Group Server list and added dependency constraints";
        reference " 0.3.0.";
    }

    revision "2021-09-21" {
        description "Updated length validation to AAA Group Name attribute";
        reference " 0.2.3.";
    }

    revision "2021-09-03" {
        description "Update descriptions of attribute";
        reference " 0.2.2.";
    }

    revision "2021-08-30" {
        description "Added RPC to unlock the user that is locked";
        reference " 0.2.1.";
    }

    revision "2021-07-16" {
        description "Restructured module as per open-config style";
        reference " 0.2.0.";
    }

    revision "2018-06-21" {
        description "Initial Version";
        reference " 0.1.0.";
    }

    grouping aaa-method-config {
        description
            "Configuration data for AAA method rules";
        leaf vrf-name  {
            type  leafref {
                path  "/ipi-network-instance:network-instances/ipi-network-instance:network-instance/ipi-vrf:vrf/ipi-vrf:config/ipi-vrf:vrf-name";
            }
            description "VRF Name associated with this instance";
        } // END of vrf-name definition.

        leaf authentication-method-rule  {
            type  cml-data-types:cml_line_t {
                length "1..1965";
            }
            description "Use this attribute to set AAA methods for authentication";
        } // END of authentication-method-rule definition.

        leaf accounting-method-rule  {
            type  cml-data-types:cml_line_t {
                length "1..1965";
            }
            description "Use this attribute to set AAA methods for accounting";
        } // END of accounting-method-rule definition.

        leaf authorization-method-rule  {
            type  cml-data-types:cml_line_t {
                length "1..1965";
            }
            description "Use this attribute to set AAA methods for authorization";
        } // END of authorization-method-rule definition.

        leaf enable-fallback  {
            type  empty;
            description "This is to enable fallback to local authentication if remote
                        authentication is configured and all AAA servers are unreachable";
        } // END of enable-fallback definition.

        leaf non-existent  {
            // when " ../enable-fallback ";
            type  empty;
            description "Fallback to local authentication if user non-existent in server";
        } // END of non-existent definition.

        leaf error-enable  {
            type  empty;
            description "This is to enable error message on login failures";
        } // END of error-enable definition.

    } // END of aaa-method-config definition.
    grouping aaa-group-config {
        description
            "Configuration data for AAA server groups";
        leaf group-type  {
            type  ipi-aaa-types:aaa_server_grp_type_t;
            description "This is use to specify server type either tacacs+ or radius";
        } // END of group-type definition.

        leaf group-name  {
            type  string {
                length "1..127";
                pattern "[^?' =,>|]+";
            }
            description "This is to create server group name";
        } // END of group-name definition.

    } // END of aaa-group-config definition.
    grouping aaa-console-config {
        description
            "Configuration data for AAA console rules";
        leaf authentication-method-rule  {
            type  cml-data-types:cml_line_t {
                length "1..1965";
            }
            description "Use this attribute to set AAA methods for authentication";
        } // END of authentication-method-rule definition.

        leaf enable-fallback  {
            type  boolean;
            description "This is to enable fallback to local authentication if remote
                        authentication is configured and all AAA servers are unreachable";
        } // END of enable-fallback definition.

        leaf authorization-method-rule  {
            type  cml-data-types:cml_line_t {
                length "1..1965";
            }
            description "Use this attribute to set AAA methods for console authorization";
        } // END of authorization-method-rule definition.

        leaf accounting-method-rule  {
            type  cml-data-types:cml_line_t {
                length "1..1965";
            }
            description "Use this attribute to set AAA methods for  console accounting";
        } // END of accounting-method-rule definition.

        leaf user-non-existent  {
            // when " ../enable-fallback ";
            type  empty;
            description "Fallback to local authentication if user non-existent in server";
        } // END of user-non-existent definition.

    } // END of aaa-console-config definition.
    grouping aaa-host-entry-config {
        description
            "AAA host address config";
        leaf host-address  {
            type  cml-data-types:cml_hostname_t;
            description "Use this attribute to add a host address to a server group";
        } // END of host-address definition.

    } // END of aaa-host-entry-config definition.
    grouping aaa-server-entries-top {
        description
            "Grouping of AAA Server Configuration";
        container server-addresses {
            description
                "Container for AAA Server address Entries";

            list server-address {
                key "host-address";
                description
                    "AAA server address entry list";
                leaf host-address  {
                    type  leafref {
                        path  "../config/host-address";
                    }
                    description "Use this attribute to add a host address to a server group";
                } // END of host-address definition.

                container config {
                    description
                        "Configurational data for server address entry";
                    uses aaa-host-entry-config;
                } // END of config-container definition.
                container state {
                    config false;
                    description
                        "Operational state data for server address entry";
                    uses aaa-host-entry-config;
                } // END of state-container definition.
            } // End of server-address-list
        } // END of server-addresses-container definition.
    } // END of aaa-server-entries-top definition.
    grouping aaa-user-config {
        description
            "Configuration data for AAA user authentication";
        leaf authentication-max-failure-attempts  {
            type  uint8 {
                 range "1..25"  {
                    description "1..25: Supported range 1 - 25";
                 }
            }
            description "Use this attribute to set the number of unsuccessful authentication
                        attempts before a user is locked out";
        } // END of authentication-max-failure-attempts definition.

        leaf local-user-unlock-timeout  {
            type  uint16 {
                 range "1..3600"  {
                    description "1..3600: Supported range 1 - 3600";
                 }
            }
            units "seconds";
            description "Use this attribute to set unlock timeout after local user/s locked out";
        } // END of local-user-unlock-timeout definition.

    } // END of aaa-user-config definition.
    grouping password-policy-config {
        description
            "Password policy parameters";
        leaf enable  {
            type  empty;
            description "Enable feature of applying policy to update password";
        } // END of enable definition.

        leaf numeric-count  {
            // when " ../enable ";
            type  uint8 {
                 range "1..32"  {
                    description "1..32: Supported range 1 - 32";
                 }
            }
            description "The minimum number of digits";
        } // END of numeric-count definition.

        leaf uppercase-count  {
            // when " ../enable ";
            type  uint8 {
                 range "1..32"  {
                    description "1..32: Supported range 1 - 32";
                 }
            }
            description "The minimum number of upper letters";
        } // END of uppercase-count definition.

        leaf lowercase-count  {
            // when " ../enable ";
            type  uint8 {
                 range "1..32"  {
                    description "1..32: Supported range 1 - 32";
                 }
            }
            description "The minimum number of lower letters";
        } // END of lowercase-count definition.

        leaf special-count  {
            // when " ../enable ";
            type  uint8 {
                 range "1..32"  {
                    description "1..32: Supported range 1 - 32";
                 }
            }
            description "The minimum number of special characters";
        } // END of special-count definition.

        leaf history  {
            // when " ../enable ";
            type  uint16 {
                 range "1..400"  {
                    description "1..400: Supported range 1 - 400";
                 }
            }
            description "history";
        } // END of history definition.

        leaf maxsequence  {
            // when " ../enable ";
            type  uint8 {
                 range "1..32"  {
                    description "1..32: Supported range 1 - 32";
                 }
            }
            description "The maximum number of monotonic character sequences to be accepted.";
        } // END of maxsequence definition.

        leaf disable-usercheck  {
            // when " ../enable ";
            type  empty;
            description "Disable the check if password contains username";
        } // END of disable-usercheck definition.

        leaf maxrepeat  {
            // when " ../enable ";
            type  uint8 {
                 range "1..32"  {
                    description "1..32: Supported range 1 - 32";
                 }
            }
            description "The maximum number of same consecutive characters to be accepted";
        } // END of maxrepeat definition.

        leaf min-length  {
            // when " ../enable ";
            type  uint8 {
                 range "8..32"  {
                    description "8..32: Supported range 8 - 32";
                 }
            }
            description "Minimum password length";
        } // END of min-length definition.

    } // END of password-policy-config definition.
    grouping password-expdays {
        description
            "Password expiration days";
        leaf expire  {
            type  uint16 {
                 range "0..1000"  {
                    description "0..1000: Supported range 0 - 1000";
                 }
            }
            description "use this attribute to set user/role level expiry days";
        } // END of expire definition.

        leaf role  {
            type  ipi-user-management-types:user_mgmt_role_types_t;
            description "use this attribute to set the role for password expiry";
        } // END of role definition.

        leaf user  {
            type  string {
                length "1..1965";
                pattern "[^?' =,>|]+";
            }
            description "use this attribute to set the username for password expiry";
        } // END of user definition.

    } // END of password-expdays definition.
    grouping aaa-debug-config {
        description
            "Configuration data for AAA debugging in Config Mode";
        leaf enable  {
            type  empty;
            description "Use this attribute to display AAA debugging information.";
        } // END of enable definition.

    } // END of aaa-debug-config definition.
    grouping aaa-debug-state {
        description
            "State data related to AAA debugging status";
        leaf terminal-debug-status  {
            type  cml-data-types:cml_on_off_t;
            description "Use this attribute to display AAA terminal debugging information.";
        } // END of terminal-debug-status definition.

    } // END of aaa-debug-state definition.

    grouping  aaa-grouping {
    description
        "AAA Top level container for configuration and operational data";
    container aaa {
        if-feature feature-list:HAVE_HOSTPD;
        if-feature feature-list:HAVE_AAA;
        description
            "AAA Top level container for configuration and operational data";
        container vrfs {
            description
                "This container defines AAA server vrf informations";

            list vrf {
                key "vrf-name";
                description
                    "AAA VRF Configuration";
                leaf vrf-name  {
                    type  leafref {
                        path  "../config/vrf-name";
                    }
                    description "VRF Name associated with this instance";
                } // END of vrf-name definition.

                container config {
                    description
                        "AAA VRF related operation";
                    uses aaa-method-config;
                } // END of config-container definition.
                container state {
                    config false;
                    description
                        "This container defines AAA VRF states.";
                    uses aaa-method-config;
                } // END of state-container definition.
                container server-groups {
                    description
                        "This container defines AAA server groups informations";

                    list server-group {
                    // when " ipi-aaa:aaa/vrfs/vrf/server-groups/server-group/config/group-type == 1 && ipi-tacacs:tacacs/vrfs/vrf/config/feature-enable || ipi-aaa:aaa/vrfs/vrf/server-groups/server-group/config/group-type == 2 ";
                        key "group-type group-name";
                        description
                            "This objectlist defines AAA server group list";
                        leaf group-type  {
                            type  leafref {
                                path  "../config/group-type";
                            }
                            description "This is to create server group type";
                        } // END of group-type definition.

                        leaf group-name  {
                            type  leafref {
                                path  "../config/group-name";
                            }
                            description "This is to create server group name";
                        } // END of group-name definition.

                        container config {
                            description
                                "configuration data for each server group";
                            uses aaa-group-config;
                        } // END of config-container definition.
                        container state {
                            config false;
                            description
                                "Operational state data of each server group";
                            uses aaa-group-config;
                        } // END of state-container definition.
                        uses aaa-server-entries-top;
                    } // End of server-group-list
                } // END of server-groups-container definition.
            } // End of vrf-list
        } // END of vrfs-container definition.
        container aaa-authentication-console {
            description
                "This container defines console authentication";
            container config {
                description
                    "Configuration for console login";
                uses aaa-console-config;
            } // END of config-container definition.
            container state {
                config false;
                description
                    "This containers defines AAA console config states";
                uses aaa-console-config;
            } // END of state-container definition.
        } // END of aaa-authentication-console-container definition.
        container aaa-user {
            description
                "This container defines a global admin data for AAA users";
            container config {
                description
                    "Configuration data for AAA users";
                uses aaa-user-config;
            } // END of config-container definition.
            container state {
                config false;
                description
                    "Operational state data for AAA users";
                uses aaa-user-config;
            } // END of state-container definition.
            container password-policy {
                description
                    "password policy parameters";
                container config {
                    description
                        "Configuration data for password policy";
                    uses password-policy-config;
                } // END of config-container definition.
                container state {
                    config false;
                    description
                        "Operational state data for password policy";
                    uses password-policy-config;
                } // END of state-container definition.
                container role-expdays {
                    description
                        "Defines password expiration days for roles";

                    list role-expday {
                    when " /ipi-aaa:aaa/ipi-aaa:aaa-user/ipi-aaa:password-policy/ipi-aaa:config/ipi-aaa:enable ";
                        key "role";
                        max-elements 4;
                        description
                            "Config password expiration days for each role";
                        leaf role  {
                            type  leafref {
                                path  "../config/role";
                            }
                            description "password expiration";
                        } // END of role definition.

                        container config {
                            description
                                "Config for password expiration of roles";
                            uses password-expdays;
                        } // END of config-container definition.
                        container state {
                            config false;
                            description
                                "state of password exp for role";
                            uses password-expdays;
                        } // END of state-container definition.
                    } // End of role-expday-list
                } // END of role-expdays-container definition.
                container user-expdays {
                    description
                        "Defines password expiration days for users";

                    list user-expday {
                        key "user";
                        max-elements 100;
                        description
                            "Config password expiration days for each user";
                        leaf user  {
                            type  leafref {
                                path  "../config/user";
                            }
                            description "password expiration";
                        } // END of user definition.

                        container config {
                            description
                                "password exp config for users";
                            uses password-expdays;
                        } // END of config-container definition.
                        container state {
                            config false;
                            description
                                "state exp for users";
                            uses password-expdays;
                        } // END of state-container definition.
                    } // End of user-expday-list
                } // END of user-expdays-container definition.
            } // END of password-policy-container definition.
        } // END of aaa-user-container definition.
        container debug {
            description
                "Debugging functions";
            container config {
                description
                    "This defines AAA Debug Configuration";
                uses aaa-debug-config;
            } // END of config-container definition.
            container state {
                config false;
                description
                    "This container defines AAA Debug state";
                uses aaa-debug-config;
                uses aaa-debug-state;
            } // END of state-container definition.
        } // END of debug-container definition.
    } // END of aaa-container definition.
    } // END of aaa-grouping definition.

    uses aaa-grouping;

    rpc aaa-terminal-debug-on {
        if-feature feature-list:HAVE_HOSTPD;
        if-feature feature-list:HAVE_AAA;
        description "Use this RPC to turn on AAA terminal debug logs";
    }

    rpc aaa-terminal-debug-off {
        if-feature feature-list:HAVE_HOSTPD;
        if-feature feature-list:HAVE_AAA;
        description "Use this RPC to turn off AAA terminal debug logs";
    }

    rpc aaa-clear-local-user-lockout {
        if-feature feature-list:HAVE_AAA;
        if-feature feature-list:HAVE_HOSTPD;
        description "This RPC is to clear the user lockout";
        input  {
            leaf username  {
                type string {
                    length "2..32";
                }
                mandatory true;
                description "Username of the user to be unlocked";
            }
        }
    }

}
