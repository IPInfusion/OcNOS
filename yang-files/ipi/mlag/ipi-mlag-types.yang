/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mlag-types.yang
*
*/

module ipi-mlag-types {

    yang-version 1.1;

    namespace   "http://www.ipinfusion.com/yang/ocnos/ipi-mlag-types";

    prefix "ipi-mlag-types";

    organization
        "IP Infusion Inc.";

    contact
        "Address: 3965 Freedom Circle, Suite 200, Santa Clara, CA 95054
         Phone: +1 408-400-1900
         E-mail: support@ipinfusion.com
         Web: http://www.ipinfusion.com/";

    description
        "MLAG data types";


    revision "2022-06-01" {
        description "Updated the yang file with feature";
        reference " 0.2.0.";
    }

    revision "2021-03-06" {
        description "Restructured module as per open-config";
        reference " 0.1.0.";
    }



    typedef  mlag_interface_flags_t {
        type bits {
            bit NSM_MLAG_PORT_STATE_FORWARD {
                position 0;
                description "Port State Forward";
            }
            bit NSM_MLAG_PORT_UP {
                position 1;
                description "MLAG Port UP";
            }
            bit NSM_MLAG_ROLE_MASTER {
                position 2;
                description "MLAG Role Master";
            }
            bit NSM_MLAG_NEIGH_MEM_IF_STATE_UP {
                position 3;
                description "MLAG Neighbor Mem Interface State UP";
            }
            bit LAG_FORCED_MLAG_UP {
                position 4;
                description "LAG Forced MLAG UP";
            }
        }
        description "type definition for MLAG_INTERFACE_FLAGS_T";
    }

    typedef  mlag_idp_interface_type_t {
        type enumeration {
            enum L3 {
                value 0;
                description "L3 Interface";
            }
            enum L2 {
                value 1;
                description "L2(switchport) Interface";
            }
        }
        description "type definition for MLAG_IDP_INTERFACE_TYPE_T";
    }

    typedef  mlag_stp_message_type_t {
        type bits {
            bit NSM_MCEC_STP_BRIDGE_PRIORITY {
                position 0;
                description "STP Bridge Priority";
            }
            bit NSM_MCEC_PATHCOST_METHOD {
                position 1;
                description "STP Path-Cost Method";
            }
            bit NSM_MCEC_STP_DOMAIN_DIGEST {
                position 2;
                description "STP Domain Digest";
            }
        }
        description "type definition for MLAG_STP_MESSAGE_TYPE_T";
    }

}
