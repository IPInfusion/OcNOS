/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mlag.yang
*
*/

module ipi-mlag {

    yang-version 1.1;

    namespace   "http://www.ipinfusion.com/yang/ocnos/ipi-mlag";

    prefix "ipi-mlag";

    import ipi-interface {
        prefix ipi-interface;
        revision-date 2026-03-10;
    }

    import ipi-mlag-types {
        prefix ipi-mlag-types;
        revision-date 2022-06-01;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "NSM Mlag configurations";


    revision "2025-11-05" {
        description "Added a dependentobject for EVPN system-mac and mlag";
        reference " 0.5.0.";
    }

    revision "2025-04-14" {
        description "Fix compilation warnings";
        reference " 0.4.5.";
    }

    revision "2025-03-12" {
        description "Removed unwanted import tags";
        reference " 0.4.4.";
    }

    revision "2024-11-12" {
        description "Added dependentObject tag inside config container of mlag aggregation top grouping";
        reference " 0.4.3.";
    }

    revision "2024-07-24" {
        description "Fixed circular dependencies";
        reference " 0.4.2.";
    }

    revision "2024-07-08" {
        description "Fixed port mirror / interface dependencies";
        reference " 0.4.1.";
    }

    revision "2023-04-23" {
        description "Added hidden RPC to save mcec info to disk before reload";
        reference " 0.4.0.";
    }

    revision "2022-12-01" {
        description "Updated when expressions";
        reference " 0.3.1.";
    }

    revision "2022-11-07" {
        description "Added enclosing container for MCEC interface object list";
        reference " 0.3.0.";
    }

    revision "2022-07-30" {
        description "Updated when expressions in yang";
        reference " 0.2.3.";
    }

    revision "2022-06-01" {
        description "Updated the yang file with feature";
        reference " 0.2.2.";
    }

    revision "2021-04-20" {
        description "Changed domain-digest and interface-digest attribute types to string";
        reference " 0.2.1.";
    }

    revision "2021-03-06" {
        description "Restructured module as per open-config";
        reference " 0.2.0.";
    }

    revision "2018-06-21" {
        description "Initial Version";
        reference " 0.1.0.";
    }

    grouping mlag-interface-top {
        description
            "Grouping for MLAG interface state";

        list mlag-interface {
            key "mlag-id";
            config false;
            description
                "List of MLAG interface ids";
            leaf mlag-id  {
                type  leafref {
                    path  "../state/mlag-id";
                }
                description "MLAG group number";
            } // END of mlag-id definition.

            container state {
                config false;
                description
                    "Operational state data";
                uses mlag-interface-state;
            } // END of state-container definition.
        } // End of mlag-interface-list
    } // END of mlag-interface-top definition.
    grouping mlag-intra-domain-port-top {
        description
            "Grouping for MLAG Inter-Domain-Port state";
        container intra-domain-port {
            config false;
            description
                "Inter-Domain-Port states";
            container state {
                config false;
                description
                    "Operational state data";
                uses mlag-intra-domain-port-state;
            } // END of state-container definition.
        } // END of intra-domain-port-container definition.
    } // END of mlag-intra-domain-port-top definition.
    grouping mlag-mstp-sync-info-top {
        description
            "Grouping for MLAG MSTP sync information states";
        container mstp-sync-info {
            config false;
            description
                "MSTP sync info states";
            container state {
                config false;
                description
                    "Operational state data";
                uses mlag-mstp-sync-info-state;
            } // END of state-container definition.
            uses interface-sync-info-top;
        } // END of mstp-sync-info-container definition.
    } // END of mlag-mstp-sync-info-top definition.
    grouping mlag-interface-state {
        description
            "Grouping for MLAG interface states";
        leaf mlag-id  {
            type  uint16;
            description "MLAG group number";
        } // END of mlag-id definition.

        leaf interface-flags  {
            type  ipi-mlag-types:mlag_interface_flags_t;
            description "MLAG and neighbor MLAG interface state flags";
        } // END of interface-flags definition.

        leaf bandwidth  {
            type  string {
                length "1..1965";
                pattern "[^?' =,>|]+";
            }
            description "Bandwidth of the MLAG";
        } // END of bandwidth definition.

    } // END of mlag-interface-state definition.
    grouping mlag-intra-domain-port-state {
        description
            "Grouping for MLAG intra-domain-port state";
        leaf interface-name  {
            type  string {
                length "1..1965";
                pattern "[^?' =,>|]+";
            }
            description "Inter-domain-port interface name";
        } // END of interface-name definition.

        leaf interface-index  {
            type  uint32;
            description "Inter-domain-port interface index";
        } // END of interface-index definition.

        leaf interface-type  {
            type  ipi-mlag-types:mlag_idp_interface_type_t;
            description "Configured interface type of the Intra-Domain-Link is L2(switchport)
                        or L3";
        } // END of interface-type definition.

        leaf bridge-name  {
            type  string {
                length "1..1965";
                pattern "[^?' =,>|]+";
            }
            description "Bridge name configured for the specified interface";
        } // END of bridge-name definition.

    } // END of mlag-intra-domain-port-state definition.
    grouping mlag-mstp-sync-info-state {
        description
            "Grouping for MLAG MSTP sync information states";
        leaf bridge-priority  {
            type  uint16;
            description "Bridge priority";
        } // END of bridge-priority definition.

        leaf path-cost-method  {
            type  uint8;
            description "Path cost method";
        } // END of path-cost-method definition.

        leaf num-of-interfaces  {
            type  uint16;
            description "Number of MLAG interfaces";
        } // END of num-of-interfaces definition.

        leaf-list domain-digest  {
            type  string {
                length "1..1965";
                pattern "[^?' =,>|]+";
            }
            description "Domain MD5 digest";
        } // END of domain-digest definition.

    } // END of mlag-mstp-sync-info-state definition.
    grouping interface-sync-info-top {
        description
            "Grouping for interface sync information states";

        list interface-sync-info {
            key "interface-mlag-id";
            config false;
            description
                "List of interface sync info for a given MLAG";
            leaf interface-mlag-id  {
                type  leafref {
                    path  "../state/interface-mlag-id";
                }
                description "MLAG group number";
            } // END of interface-mlag-id definition.

            container state {
                config false;
                description
                    "Operational state data";
                uses interface-sync-info-state;
            } // END of state-container definition.
        } // End of interface-sync-info-list
    } // END of interface-sync-info-top definition.
    grouping interface-sync-info-state {
        description
            "Grouping for interface sync info states";
        leaf interface-mlag-id  {
            type  uint16;
            description "MLAG group number";
        } // END of interface-mlag-id definition.

        leaf interface-priority  {
            type  uint16;
            description "Interface priority";
        } // END of interface-priority definition.

        leaf path-cost  {
            type  uint32;
            description "Path cost";
        } // END of path-cost definition.

        leaf-list interface-digest  {
            type  string {
                length "1..1965";
                pattern "[^?' =,>|]+";
            }
            description "Interface MD5 digest";
        } // END of interface-digest definition.

    } // END of interface-sync-info-state definition.
    grouping mlag-aggregation-top {
        description
            "Grouping for MLAG aggregation attributes";
        container config {
            presence "yes";
            description
                "Configuration data";
            uses mlag-aggregation-config;
        } // END of config-container definition.
        container state {
            config false;
            description
                "Operational state data";
            uses mlag-aggregation-config;
        } // END of state-container definition.
    } // END of mlag-aggregation-top definition.
    grouping mlag-aggregation-config {
        description
            "Grouping for MLAG aggregation attributes";
        leaf mlag-id  {
            type  uint16 {
                 range "1..255"  {
                    description "1..255: Supported range 1 - 255";
                 }
            }
            mandatory true;
            description "MLAG group number";
        } // END of mlag-id definition.

    } // END of mlag-aggregation-config definition.

    grouping  mlag-aggregation-grouping {
    description
        "MLAG aggregation config";
    container mlag-aggregation {
        if-feature feature-list:HAVE_MLAG;
        presence "yes";
        description
            "MLAG aggregation config";
        uses mlag-aggregation-top;
    } // END of mlag-aggregation-container definition.
    } // END of mlag-aggregation-grouping definition.

    grouping  mlag-grouping {
    description
        "NSM MLAG master";
    container mlag {
        if-feature feature-list:HAVE_MLAG;
        config false;
        description
            "NSM MLAG master";
        uses mlag-interface-top;
        uses mlag-intra-domain-port-top;
        uses mlag-mstp-sync-info-top;
    } // END of mlag-container definition.
    } // END of mlag-grouping definition.

    augment /ipi-interface:interfaces/ipi-interface:interface {
    // when " not(/ipi-interface:interfaces/ipi-interface:interface/ipi-if-aggregate:member-aggregation/ipi-if-aggregate:config) ";
        description
            "MLAG aggregation config";
        uses mlag-aggregation-grouping;
    }

    uses mlag-grouping;

}
