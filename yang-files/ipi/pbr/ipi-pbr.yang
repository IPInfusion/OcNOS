/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pbr.yang
*
*/

module ipi-pbr {

    yang-version 1.1;

    namespace   "http://www.ipinfusion.com/yang/ocnos/ipi-pbr";

    prefix "ipi-pbr";

    import ipi-interface {
        prefix ipi-interface;
        revision-date 2026-03-10;
    }

    import ipi-routemap {
        prefix ipi-routemap;
        revision-date 2026-07-16;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module provides Policy Based Routing configurations";


    revision "2026-05-14" {
        description "Added CML_SKIP_HITLESS_MERGE for route-map-v6-name attribute";
        reference " 0.6.2.";
    }

    revision "2026-05-11" {
        description "Added CML_SKIP_HITLESS_MERGE for route-map-name attribute";
        reference " 0.6.1.";
    }

    revision "2025-05-22" {
        description "Added leafref for 'route-map-name' and 'route-map-v6-name' attributes";
        reference " 0.5.4.";
    }

    revision "2025-04-22" {
        description "Added skip-dependency-validation when tag for pbr/interfaces/interface object-list for pbr-interface config";
        reference " 0.5.3.";
    }

    revision "2025-04-16" {
        description "Added delete-on-no-child when tag for pbr/interfaces/interface object-list for route-map";
        reference " 0.5.2.";
    }

    revision "2024-10-07" {
        description "Added skip-dependency for pbr/interfaces/interface object-list for route-map";
        reference " 0.5.0.";
    }

    revision "2024-06-28" {
        description "Added when tag to delete dependency for PBR Interface object in top level PBR config container";
        reference " 0.5.1.";
    }

    revision "2024-05-22" {
        description "Add 'cliprependstr' tag for 'pbr-statistics' to help it show a description string.";
        reference " 0.5.0.";
    }

    revision "2022-09-13" {
        description "Added delete dependency for PBR Interface object in top level PBR config container";
        reference " 0.4.0.";
    }

    revision "2022-06-01" {
        description "Updated the yang file with feature";
        reference " 0.3.0.";
    }

    revision "2021-11-16" {
        description "Module restructuring";
        reference " 0.2.0.";
    }

    revision "2018-06-21" {
        description "Initial Version";
        reference " 0.1.0.";
    }

    grouping pbr-interfaces-config {
        description
            "PBR interfaces configuration";
        leaf name  {
            type  leafref {
                path  "/ipi-interface:interfaces/ipi-interface:interface/ipi-interface:name";
            }
            description "Attribute to specify interface name";
        } // END of name definition.

        leaf route-map-name  {
            type  leafref {
                path  "/ipi-routemap:routemaps/ipi-routemap:routemap/ipi-routemap:routemap-name";
            }
            description "Use this attribute to set ip policy for route-map.";
        } // END of route-map-name definition.

        leaf route-map-v6-name  {
            if-feature feature-list:HAVE_IPV6;
            type  leafref {
                path  "/ipi-routemap:routemaps/ipi-routemap:routemap/ipi-routemap:routemap-name";
            }
            description "Use this attribute to set ipv6 policy for route-map.";
        } // END of route-map-v6-name definition.

    } // END of pbr-interfaces-config definition.
    grouping pbr-interfaces-top {
        description
            "PBR interfaces top level configuration";
        container interfaces {
            description
                "Containers that holds all interfaces configuration for pbr";

            list interface {
            when " /ipi-pbr:pbr/ipi-pbr:config/ipi-pbr:enabled ";
                key "name";
                description
                    "Interface list to hold pbr configuration";
                leaf name  {
                    type  leafref {
                        path  "../config/name";
                    }
                    description "Attribute to specify interface name";
                } // END of name definition.

                container config {
                    description
                        "Configuration data for pbr interface";
                    uses pbr-interfaces-config;
                } // END of config-container definition.
                container state {
                    config false;
                    description
                        "Operational state data for pbr interface";
                    uses pbr-interfaces-config;
                } // END of state-container definition.
            } // End of interface-list
        } // END of interfaces-container definition.
    } // END of pbr-interfaces-top definition.
    grouping pbr-config {
        description
            "PBR configuration";
        leaf enabled  {
            type  empty;
            description "Use this attribute to enable pbr support";
        } // END of enabled definition.

    } // END of pbr-config definition.

    grouping  pbr-grouping {
    description
        "Container for all Policy Based Routing configuration";
    container pbr {
        if-feature feature-list:HAVE_PBR;
        description
            "Container for all Policy Based Routing configuration";
        container config {
            description
                "Configuration data for pbr feature enable";
            uses pbr-config;
        } // END of config-container definition.
        container state {
            config false;
            description
                "Operational state data for pbr feature enable";
            uses pbr-config;
        } // END of state-container definition.
        uses pbr-interfaces-top;
    } // END of pbr-container definition.
    } // END of pbr-grouping definition.

    uses pbr-grouping;

    rpc clear-route-map-pbr-statistics {
        if-feature feature-list:HAVE_PBR;
        description "Use this RPC to clear route-map";
        input  {
            leaf route-map-name  {
                type string;
                mandatory true;
                description "";
            }
        }
    }

}
