/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-vpls-types.yang
*
*/

module ipi-vpls-types {

    yang-version 1.1;

    namespace   "http://www.ipinfusion.com/yang/ocnos/ipi-vpls-types";

    prefix "ipi-vpls-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Generic VPLS data Types";


    revision "2024-12-16" {
        description "Add new type for mac-limit VPLS_MPLS_MAC_LIMIT_ACTION_T";
        reference " 0.8.0.";
    }

    revision "2024-10-01" {
        description "Add new type for mac-withdrawal VPLS_MPLS_MAC_WITHDRAWAL_T";
        reference " 0.8.0.";
    }

    revision "2024-05-06" {
        description "Updated value for datatype VPLS_PEER_STATE_T";
        reference " 0.7.0.";
    }

    revision "2022-11-15" {
        description "Added new datatype VPLS_AC_TREAT_TYPE_T";
        reference " 0.6.1.";
    }

    revision "2022-06-01" {
        description "Updated the yang file with feature";
        reference " 0.6.0.";
    }

    revision "2022-03-23" {
        description "Added new datatype VPLS_MPLS_FLOW_LABEL_DIRECTION_T";
        reference " 0.4.0.";
    }

    revision "2022-02-20" {
        description "Remove Spoke type";
        reference " 0.6.2.";
    }

    revision "2022-02-16" {
        description "Updated VPLS_PEER_STATE_T enum value";
        reference " 0.5.0.";
    }

    revision "2021-09-03" {
        description "Update descriptions of attribute";
        reference " 0.3.0.";
    }

    revision "2021-08-03" {
        description "Added a new value for VPLS_SVC_TPID_T";
        reference " 0.2.0.";
    }

    revision "2020-08-11" {
        description "Datamodel restructuring";
        reference " 0.1.0.";
    }



    typedef  vpls_ac_admin_status_t {
        type enumeration {
            enum down {
                value 0;
                description "Set the admin role as Down";
            }
        }
        description "type definition for VPLS_AC_ADMIN_STATUS_T";
    }

    typedef  vpls_peer_state_t {
        type enumeration {
            enum down {
                value 0;
                description "Pseudowire state with peer as Down";
            }
            enum up {
                value 3;
                description "Pseudowire state with peer as UP";
            }
        }
        description "type definition for VPLS_PEER_STATE_T";
    }

    typedef  vpls_signaling_type_t {
        type enumeration {
            enum NA {
                value 0;
                description "No Signaling protocol";
            }
            enum static {
                value 1;
                description "No protocol";
            }
            enum bgp {
                value 2;
                description "Signalig Protocol BGP";
            }
            enum ldp {
                value 4;
                description "Signalig Protocol LDP";
            }
            enum ad-ldp {
                value 8;
                description "Signaling protocol auto-Discovered LDP";
            }
        }
        description "type definition for VPLS_SIGNALING_TYPE_T";
    }

    typedef  vpls_pseudowire_status_t {
        type enumeration {
            enum standby {
                value 0;
                description "Pseudowire status as Standby";
            }
            enum active {
                value 1;
                description "Pseudowire status as Active";
            }
        }
        description "type definition for VPLS_PSEUDOWIRE_STATUS_T";
    }

    typedef  vpls_ac_status_t {
        type enumeration {
            enum up {
                value 0;
                description "the AC is UP";
            }
            enum down {
                value 1;
                description "the AC is Down";
            }
        }
        description "type definition for VPLS_AC_STATUS_T";
    }

    typedef  vpls_mac_learning_t {
        type enumeration {
            enum enable {
                value 1;
                description "Enable MAC learning";
            }
            enum disable {
                value 2;
                description "Disable MAC learning";
            }
        }
        description "type definition for VPLS_MAC_LEARNING_T";
    }

    typedef  vpls_qos_map_profile_type_t {
        type enumeration {
            enum cos-to-queue {
                value 0;
                description "profile for cos to queue map";
            }
            enum queue-color-to-cos {
                value 1;
                if-feature feature-list:NOT_HAVE_CUSTOM1_MPLS;
                description "profile for queue color to cos map";
            }
        }
        description "type definition for VPLS_QOS_MAP_PROFILE_TYPE_T";
    }

    typedef  vpls_svc_tpid_t {
        type enumeration {
            enum dot1.q {
                value 33024;
                description "Set tpid value as 0x8100";
            }
            enum dot1.ad {
                value 34984;
                description "Set tpid value as 0x88a8";
            }
            enum 0x9100 {
                value 37120;
                description "Set tpid value as 0x9100";
            }
            enum 0x9200 {
                value 37376;
                description "Set tpid value as 0x9200";
            }
        }
        description "type definition for VPLS_SVC_TPID_T";
    }

    typedef  vpls_port_type_t {
        type enumeration {
            enum access-port {
                value 1;
                description "Access interface statistics counters";
            }
            enum network-port {
                value 2;
                description "Network interface statistics counters";
            }
        }
        description "type definition for VPLS_PORT_TYPE_T";
    }

    typedef  vpls_spoke_vc_type_t {
        type string;
        description "type definition for VPLS_SPOKE_VC_TYPE_T";
    }

    typedef  vpls_peer_type_t {
        type enumeration {
            enum manual {
                value 1;
                description "No signaling is used to set-up the Virtual Circuit";
            }
        }
        description "type definition for VPLS_PEER_TYPE_T";
    }

    typedef  vpls_vc_type_t {
        type enumeration {
            enum vlan {
                value 4;
                description "VLAN";
            }
            enum ethernet {
                value 5;
                description "Ethernet";
            }
        }
        description "type definition for VPLS_VC_TYPE_T";
    }

    typedef  cml_nsm_vpls_ac_treat_type_t {
        type enumeration {
            enum ignore-ac-spoke-state {
                value 1;
                description "Ignore access and spoke state";
            }
            enum block-mesh-spoke-on-all-ac-down {
                value 2;
                description "Block spoke and mesh pseudowires when acces is down";
            }
        }
        description "type definition for CML_NSM_VPLS_AC_TREAT_TYPE_T";
    }

    typedef  vpls_peer_address_type_t {
        type string;
        description "type definition for VPLS_PEER_ADDRESS_TYPE_T";
    }

    typedef  vpls_vlan_interface_t {
        type string;
        description "type definition for VPLS_VLAN_INTERFACE_T";
    }

    typedef  vpls_mpls_if_ether_t {
        type enumeration {
            enum ethernet {
                value 0;
                description "Ethernet";
            }
        }
        description "type definition for VPLS_MPLS_IF_ETHER_T";
    }

    typedef  vpls_mpls_access_type_t {
        type union {
            type vpls_vlan_interface_t {

            }
            type vpls_mpls_if_ether_t {

            }
        }
        description "type definition for VPLS_MPLS_ACCESS_TYPE_T";
    }

    typedef  vpls_mpls_flow_label_direction_t {
        type enumeration {
            enum both {
                value 1;
                description "flow label direction both(transmit and receive)";
            }
            enum transmit {
                value 2;
                description "flow label direction transmit";
            }
            enum receive {
                value 3;
                description "flow label direction receive";
            }
        }
        description "type definition for VPLS_MPLS_FLOW_LABEL_DIRECTION_T";
    }

    typedef  vpls_mpls_mac_withdrawal_t {
        type bits {
            bit flush-on-spoke-vc-standby-activation {
                position 1;
                description "Send MAC withdraw when the secondary spoke becomes the primary";
            }
            bit flush-propagate-spoke-to-mesh {
                position 2;
                description "Allow propagation of MAC withdraw from spoke to mesh";
            }
        }
        description "type definition for VPLS_MPLS_MAC_WITHDRAWAL_T";
    }

    typedef  vpls_mpls_mac_limit_action_t {
        type enumeration {
            enum log-only {
                value 1;
                description "logging only support";
            }
            enum log-errdisable {
                value 2;
                description "logging and errdisable support";
            }
        }
        description "type definition for VPLS_MPLS_MAC_LIMIT_ACTION_T";
    }

}
