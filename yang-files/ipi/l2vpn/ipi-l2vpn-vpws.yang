/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-l2vpn-vpws.yang
*
*/

module ipi-l2vpn-vpws {

    yang-version 1.1;

    namespace   "http://www.ipinfusion.com/yang/ocnos/ipi-l2vpn-vpws";

    prefix "ipi-l2vpn-vpws";

    import cml-data-types {
        prefix cml-data-types;
        revision-date 2026-05-15;
    }

    import ipi-interface {
        prefix ipi-interface;
        revision-date 2026-03-10;
    }

    import ipi-network-instance-types {
        prefix ipi-network-instance-types;
        revision-date 2023-03-14;
    }

    import ipi-network-instance {
        prefix ipi-network-instance;
        revision-date 2026-08-12;
    }

    import ipi-mpls {
        prefix ipi-mpls;
        revision-date 2026-08-27;
    }

    import ipi-vpws-types {
        prefix ipi-vpws-types;
        revision-date 2025-05-14;
    }

    import ipi-qos {
        prefix ipi-qos;
        revision-date 2026-09-09;
    }

    import ietf-inet-types {
        prefix inet;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for VPWS pseudowire";


    revision "2026-03-31" {
        description "Updated data-type of up-time, create-time and transport-update time to CML_LINE_T";
        reference " 7.1.0.";
    }

    revision "2025-12-15" {
        description "Add correct cliprependstr helpstrings";
        reference " 7.0.3.";
    }

    revision "2025-10-09" {
        description "Added hidden-cli for service-template-mapping";
        reference " 7.0.2.";
    }

    revision "2025-08-27" {
        description "Added streaming telemetry support";
        reference " 7.0.1.";
    }

    revision "2025-07-25" {
        description "Added vc revertive timer";
        reference " 7.0.0.";
    }

    revision "2025-05-14" {
        description "Added vccv cv-types";
        reference " 6.6.1.";
    }

    revision "2025-04-29" {
        description "Fix compilation warnings";
        reference " 6.6.4.";
    }

    revision "2025-04-25" {
        description "Added helpstring to the unset cli command of static flow-label";
        reference " 6.6.3.";
    }

    revision "2025-03-28" {
        description "vpws MAC-Withdrawal support";
        reference " 6.6.2.";
    }

    revision "2025-02-06" {
        description "Added when tag with condition inside forwarding-information-base objectlist";
        reference " 6.6.1.";
    }

    revision "2025-01-28" {
        description "Added when tag inside forwarding-information-base objectlist";
        reference " 6.6.0.";
    }

    revision "2024-10-26" {
        description "Added nexthop address as RDN for forwarding information base objectlist";
        reference " 6.0.0.";
    }

    revision "2024-09-17" {
        description "Added down-reason attribute in vpws-pseudowire-state grp";
        reference " 5.0.4.";
    }

    revision "2024-07-20" {
        description "Removed the hidden cli tag from control-word";
        reference " 5.0.3.";
    }

    revision "2024-06-03" {
        description "Removed max-elements as 1 from vc config";
        reference " 5.0.2.";
    }

    revision "2024-05-28" {
        description "Blocking the fec129 cli options";
        reference " 5.0.1.";
    }

    revision "2024-05-09" {
        description "Added mode for clear commands";
        reference " 5.0.0.";
    }

    revision "2024-02-15" {
        description "Added when tag for control verification type attribute";
        reference " 4.0.11.";
    }

    revision "2024-01-29" {
        description "Revert masking of service template commands for Marvell platform";
        reference " 4.0.10.";
    }

    revision "2024-01-15" {
        description "Mask service template commands for Marvell platform";
        reference " 4.0.9.";
    }

    revision "2023-10-05" {
        description "Adding skip-delete for one of encap when expression";
        reference " 4.0.8.";
    }

    revision "2023-06-20" {
        description "Updated datatype for ldp ecmp service attribute";
        reference " 4.0.7.";
    }

    revision "2023-05-04" {
        description "updated the length of the vpws-name to 1-128";
        reference " 4.0.6.";
    }

    revision "2023-04-29" {
        description "Help string of OUT-INTF in vpws-forwarding-information-base-config is modified";
        reference " 4.0.5.";
    }

    revision "2023-04-20" {
        description "Added proper xpath for enable-interface-parameter-tlv attribute";
        reference " 4.0.4.";
    }

    revision "2023-04-10" {
        description "Added new CLI option interface-param-tlv for fat in MPLS-VPWS Data Model";
        reference " 4.0.3.";
    }

    revision "2023-04-03" {
        description "Changed input_helpstring of instance_type";
        reference " 4.0.2.";
    }

    revision "2023-03-14" {
        description "Moved bridge-domain from interfaces hierarchy to network-instance";
        reference " 3.0.4.";
    }

    revision "2023-02-21" {
        description "Enclosed all config object lists with container for L2VPN Data Model";
        reference " 4.0.0.";
    }

    revision "2023-02-06" {
        description "Enclosed all config object lists with container for MPLS Data Model";
        reference " 4.0.1.";
    }

    revision "2023-01-23" {
        description "Addressed cli-prependstr not found cmlgen warnings";
        reference " 3.0.2.";
    }

    revision "2023-01-17" {
        description "Addressed cli-prependstr not used warnings";
        reference " 3.0.3.";
    }

    revision "2023-01-09" {
        description "Added Description to address the cmlgen warnings";
        reference " 3.0.0.";
    }

    revision "2022-11-01" {
        description "Added attributes to check service mapped over LDP ECMP and RSVP multipath ";
        reference " 2.0.9.";
    }

    revision "2022-08-18" {
        description "Fix trigger for VPWS remotion from interface";
        reference " 2.0.8.";
    }

    revision "2022-07-16" {
        description "Global yang model name is changed as Global TE yang model";
        reference " 2.0.7.";
    }

    revision "2022-07-12" {
        description "Updated the subinterface encapsulation dependencies correctly";
        reference " 2.0.4.";
    }

    revision "2022-07-11" {
        description "Fix dependency between pseudowire-mode and service-template-mapping";
        reference " 2.0.4.";
    }

    revision "2022-07-07" {
        description "Fix for MPLS debug deletion";
        reference " 2.0.3.";
    }

    revision "2022-07-01" {
        description "Added pattern check for bandwidth related commands in MPLS yang model";
        reference " 2.0.3.";
    }

    revision "2022-06-22" {
        description "Added attributes for access and network interface counter";
        reference " 2.0.2.";
    }

    revision "2022-06-21" {
        description "Changes in the MPLS yang model w.r.t to admin-groups";
        reference " 2.0.1.";
    }

    revision "2022-06-01" {
        description "Updated the yang file with feature";
        reference " 2.0.0.";
    }

    revision "2022-03-21" {
        description "Added flow label attributes for VPWS virtual circuit.";
        reference " 1.0.0.";
    }

    revision "2021-12-08" {
        description "Added if-not-feature flag for DC-MPLS for queue-to-cos-profile";
        reference " 0.10.0.";
    }

    revision "2021-11-16" {
        description "Adding L2CP support";
        reference " 0.9.0.";
    }

    revision "2021-09-06" {
        description "Removing the dependency of L2VPN VPWS configuration in subinterface with global L2VPN VPWS configurataion";
        reference " 0.8.0.";
    }

    revision "2021-09-01" {
        description "Changed base interface module's switchport attribute name and the datatype from bool to empty";
        reference " 0.7.0.";
    }

    revision "2021-08-24" {
        description "Updated dependency for VPWS interface on svc template name";
        reference " 0.6.0.";
    }

    revision "2021-08-03" {
        description "Added L2VPN VPWS attributes for Sub-interface";
        reference " 0.5.0.";
    }

    revision "2021-07-15" {
        description "Added attributes related to VCCV and additional constraints for tunnel attributes ";
        reference " 0.4.0.";
    }

    revision "2021-04-27" {
        description "service-template is constrained with string length";
        reference " 0.3.0.";
    }

    revision "2021-03-10" {
        description "pw-link-mode made mandatory to support Secondary pw-mode config";
        reference " 0.2.0.";
    }

    revision "2020-11-25" {
        description "Initial Version";
        reference " 0.1.0.";
    }

    grouping vpws-pseudowire-config {
        description
            "Top level Grouping for Fec128 pseudowire";
        leaf pseudowire-identifier  {
            type  uint32 {
                 range "1..4294967295"  {
                    description "1..4294967295: Supported range 1 - 4294967295";
                 }
            }
            description "Use this attribute to assign pseudowire identifier to create an
                        instance of an MPLS layer 2 virtual circuit.";
        } // END of pseudowire-identifier definition.

        leaf peer-address  {
            type  ipi-vpws-types:vpws_ip_addr_t;
            description "Use this attribute to specify pseudowire end peer IP address to create
                        an instance of an MPLS layer 2 virtual circuit";
        } // END of peer-address definition.

    } // END of vpws-pseudowire-config definition.
    grouping vpws-pseudowire-service-tpid-config {
        description
            "Grouping for Service TPID pseudowire";
        leaf service-tpid  {
            // when " not(/ipi-network-instance:network-instances/ipi-network-instance:network-instance/ipi-l2vpn-vpws:vpws-instance/ipi-l2vpn-vpws:pseudowires/ipi-l2vpn-vpws:pseudowire/ipi-l2vpn-vpws:raw/ipi-l2vpn-vpws:config/ipi-l2vpn-vpws:enable-raw-mode) + not(/ipi-network-instance:network-instances/ipi-network-instance:network-instance/ipi-l2vpn-vpws:vpws-instance/ipi-l2vpn-vpws:pseudowires/ipi-l2vpn-vpws:pseudowire/ipi-l2vpn-vpws:tagged/ipi-l2vpn-vpws:config/ipi-l2vpn-vpws:enable-tagged-mode) ";
            type  ipi-vpws-types:vpws_svc_tpid_t;
            description "Use this attribute to specify tunneling ethertype to be used for an
                        instance of an MPLS layer 2 virtual circuit";
        } // END of service-tpid definition.

    } // END of vpws-pseudowire-service-tpid-config definition.
    grouping vpws-pseudowire-fec129-config {
        description
            "Top level Grouping for Fec129 pseudowire";
        leaf peer-address  {
            type  inet:ipv4-address;
            description "Use this attribute to specify pseudowire end peer IP address to create
                        an instance of an MPLS layer 2 virtual circuit";
        } // END of peer-address definition.

        leaf attachment-group-identifier  {
            type  string {
                length "1..1965";
                pattern "[^?' =,>|]+";
            }
            description "Use this attribute to specify AGI value for genfec pseudowire";
        } // END of attachment-group-identifier definition.

        leaf source-attachment-individual-identifier  {
            type  string {
                length "1..4";
                pattern "[^?' =,>|]+";
            }
            description "Use this attribute to specify SAII value for genfec pseudowire";
        } // END of source-attachment-individual-identifier definition.

        leaf target-attachment-individual-identifier  {
            type  string {
                length "1..4";
                pattern "[^?' =,>|]+";
            }
            description "Use this attribute to specify TAII value for genfec pseudowire";
        } // END of target-attachment-individual-identifier definition.

    } // END of vpws-pseudowire-fec129-config definition.
    grouping vpws-pseudowire-fec129-common-config {
        description
            "Grouping for common attributes of fec129 pseudowire";
        leaf group-name  {
            type  string {
                length "1..32";
                pattern "[^?' =,>|]+";
            }
            description "Use this attribute to create a group name with default available
                        group-identifier for MPLS Layer-2 Virtual Circuit.";
        } // END of group-name definition.

        leaf group-identifier  {
            // when " ../group-name ";
            type  uint32 {
                 range "1..4294967295"  {
                    description "1..4294967295: Supported range 1 - 4294967295";
                 }
            }
            description "Use this attribute to create a group with specific group-identifier
                        for MPLS Layer-2 Virtual Circuit.";
        } // END of group-identifier definition.

        leaf enable-control-word  {
            type  empty;
            description "Use this attribute to enable control word for MPLS Layer-2 Virtual
                        Circuit.";
        } // END of enable-control-word definition.

        leaf service-tpid  {
            type  ipi-vpws-types:vpws_svc_tpid_t;
            description "Use this attribute to specify tunneling ethertype to be used for an
                        instance of an MPLS layer 2 virtual circuit";
        } // END of service-tpid definition.

        leaf tunnel-name  {
            // when " not(../tunnel-identifier) ";
            type  string {
                length "1..32";
                pattern "[^?' =,>|]+";
            }
            description "Use this attribute to specificy the transport tunnel-name to be used
                        for MPLS Layer-2 Virtual Circuit.";
        } // END of tunnel-name definition.

        leaf tunnel-policy  {
            // when " not(../tunnel-identifier) + not(../tunnel-name) ";
            if-feature feature-list:HAVE_SERVICE_MAPPING;
            type  string {
                length "1..127";
                pattern "[^?' =,>|]+";
            }
            description "Use this attribute to specificy transport tunnel-policy to be used for
                        MPLS Layer-2 Virtual Circuit.";
        } // END of tunnel-policy definition.

        leaf tunnel-identifier  {
            // when " not(../tunnel-name) ";
            type  uint32 {
                 range "1..5000"  {
                    description "1..5000: Supported range 1 - 5000";
                 }
            }
            description "Use this attribute to specificy the static tunnel-identifier to be
                        used for MPLS Layer-2 Virtual Circuit.";
        } // END of tunnel-identifier definition.

    } // END of vpws-pseudowire-fec129-common-config definition.
    grouping vpws-pseudowire-common-config {
        description
            "Grouping for common attributes of  pseudowire";
        leaf group-name  {
            type  string {
                length "1..32";
                pattern "[^?' =,>|]+";
            }
            description "Use this attribute to create a group name with default available
                        group-identifier for MPLS Layer-2 Virtual Circuit.";
        } // END of group-name definition.

        leaf group-identifier  {
            // when " ../group-name ";
            type  uint32 {
                 range "1..4294967295"  {
                    description "1..4294967295: Supported range 1 - 4294967295";
                 }
            }
            description "Use this attribute to create a group with specific group-identifier
                        for MPLS Layer-2 Virtual Circuit.";
        } // END of group-identifier definition.

        leaf enable-control-word  {
            type  empty;
            description "Use this attribute to enable control word for MPLS Layer-2 Virtual
                        Circuit.";
        } // END of enable-control-word definition.

        leaf tunnel-name  {
            // when " not(../tunnel-identifier) ";
            type  string {
                length "1..32";
                pattern "[^?' =,>|]+";
            }
            description "Use this attribute to specificy the transport tunnel-name to be used
                        for MPLS Layer-2 Virtual Circuit.";
        } // END of tunnel-name definition.

        leaf tunnel-policy  {
            // when " not(../tunnel-identifier) + not(../tunnel-name) ";
            if-feature feature-list:HAVE_SERVICE_MAPPING;
            type  string {
                length "1..127";
                pattern "[^?' =,>|]+";
            }
            description "Use this attribute to specificy transport tunnel-policy to be used for
                        MPLS Layer-2 Virtual Circuit.";
        } // END of tunnel-policy definition.

        leaf tunnel-identifier  {
            // when " not(../tunnel-name) ";
            type  uint32 {
                 range "1..5000"  {
                    description "1..5000: Supported range 1 - 5000";
                 }
            }
            description "Use this attribute to specificy the static tunnel-identifier to be
                        used for MPLS Layer-2 Virtual Circuit.";
        } // END of tunnel-identifier definition.

        leaf allow-l2protocol-peer  {
            if-feature feature-list:HAVE_CUSTOM1_MPLS;
            type  empty;
            description "Use this attribute to configure L2CP in peer mode";
        } // END of allow-l2protocol-peer definition.

    } // END of vpws-pseudowire-common-config definition.
    grouping vpws-pseudowire-fat-config {
        description
            "Grouping for attributes of FAT pseudowire";
        leaf enable-flow-label  {
            type  empty;
            description "Use this attribute to enable flow label for VPWS Virtual Circuits.";
        } // END of enable-flow-label definition.

        leaf flow-label-direction  {
            // when " ../enable-flow-label ";
            type  ipi-vpws-types:vpws_mpls_flow_label_direction_t;
            description "Use this attribute to configure flow label direction to
                        transmit,receive or both for VPWS Virtual Circuits.";
        } // END of flow-label-direction definition.

        leaf enable-static-flow-label  {
            // when " ../enable-flow-label ";
            type  empty;
            description "Use this attribute to enable static flow label for VPWS Virtual
                        Circuits.";
        } // END of enable-static-flow-label definition.

        leaf enable-interface-parameter-tlv  {
            // when " ../enable-flow-label ";
            type  empty;
            description "Use this attribute to configure interface parameter tlv for VPLS
                        Virtual Circuits.";
        } // END of enable-interface-parameter-tlv definition.

    } // END of vpws-pseudowire-fat-config definition.
    grouping vpws-pseudowire-default-tagged-config {
        description
            "Grouping for default tagged pseudowire attributes";
        leaf enable-default-tagged-mode  {
            type  empty;
            mandatory true;
            description "This attribute is used to enable default-tagged mode of pseudowire.
                        This can be enabled at creation time";
        } // END of enable-default-tagged-mode definition.

    } // END of vpws-pseudowire-default-tagged-config definition.
    grouping vpws-pseudowire-tagged-config {
        description
            "Grouping for tagged pseudowire attributes";
        leaf enable-tagged-mode  {
            type  empty;
            mandatory true;
            description "This attribute is used to enable tagged mode of pseudowire. This can
                        be enabled at creation time";
        } // END of enable-tagged-mode definition.

    } // END of vpws-pseudowire-tagged-config definition.
    grouping vpws-pseudowire-raw-config {
        description
            "Grouping for raw pseudowire attributes";
        leaf enable-raw-mode  {
            type  empty;
            mandatory true;
            description "This attribute is used to enable raw mode of pseudowire. This can be
                        enabled at creation time";
        } // END of enable-raw-mode definition.

    } // END of vpws-pseudowire-raw-config definition.
    grouping vpws-pseudowire-static-config {
        description
            "Grouping for static pw attributes";
        leaf enable-manual-pseudowire  {
            type  empty;
            description "This attribute is used to configure static pseudowire.";
        } // END of enable-manual-pseudowire definition.

    } // END of vpws-pseudowire-static-config definition.
    grouping vpws-pseudowire-vccv-config {
        description
            "Grouping for vccv attributes for PW";
        leaf control-channel-type  {
            if-feature feature-list:HAVE_VCCV;
            if-feature feature-list:HAVE_CUSTOM1_MPLS_BFD;
            type  ipi-vpws-types:vpws_mpls_vccv_cc_type_t;
            description "Use this attribute to configure the Control-Channel type for VCCV";
        } // END of control-channel-type definition.

        leaf control-verification-type  {
            if-feature feature-list:HAVE_VCCV;
            if-feature feature-list:HAVE_CUSTOM1_MPLS_BFD;
            type  ipi-vpws-types:vpws_mpls_vccv_cv_type_t;
            description "Use this attribute to configure the Control-Verification supported by
                        BFD for VCCV";
        } // END of control-verification-type definition.

    } // END of vpws-pseudowire-vccv-config definition.
    grouping vpws-pseudowire-mplstp-config {
        description
            "Grouping for MPLS-TP attributes for PW";
    } // END of vpws-pseudowire-mplstp-config definition.
    grouping vpws-interface-config {
        description
            "Grouping for Interface config attribute";
        leaf name  {
            type  leafref {
                path  "/ipi-interface:interfaces/ipi-interface:interface/ipi-interface:name";
            }
            description "This attribute describes the interface on which attachment circuit is
                        to be created for  pseudowire.";
        } // END of name definition.

    } // END of vpws-interface-config definition.
    grouping l2vpn-vpws-top {
        description
            "Top level grouping for L2VPN VPWS configuration";
        container vpws-access {
            // when " ipi-l2vpn-vpws:vpws/interfaces/interface/vpws-access/config/enable ";
            if-feature feature-list:HAVE_SUBINTERFACE;
            description
                "Container for L2VPN VPWS data";
            container config {
                presence "yes";
                description
                    "Configuration data for L2VPN VPWS";
                uses l2vpn-vpws-config;
            } // END of config-container definition.
            container state {
                config false;
                description
                    "Operational state data for L2VPN VPWS";
                uses l2vpn-vpws-config;
            } // END of state-container definition.
            container bindings {
                description
                    "Container for L2VPN VPWS binding";

                list binding {
                    key "vpws-name";
                    description
                        "VPWS binding related configuration";
                    leaf vpws-name  {
                        type  leafref {
                            path  "../config/vpws-name";
                        }
                        description "This attribute uniquely identifies a VPWS service on Subinterface";
                    } // END of vpws-name definition.

                    container config {
                        description
                            "Configuration data for L2VPN VPWS binding";
                        uses l2vpn-vpws-bind-config;
                    } // END of config-container definition.
                    container state {
                        config false;
                        description
                            "Operational state data for L2VPN VPWS binding";
                        uses l2vpn-vpws-bind-config;
                    } // END of state-container definition.
                } // End of binding-list
            } // END of bindings-container definition.
        } // END of vpws-access-container definition.
    } // END of l2vpn-vpws-top definition.
    grouping l2vpn-vpws-config {
        description
            "Grouping for L2VPN VPWS service configurations";
        leaf enable  {
            type  empty;
            mandatory true;
            description "This attribute is used to enable VPWS service on Subinterface";
        } // END of enable definition.

        leaf enable-revertive-mode  {
            type  empty;
            description "This attribute is used to configure vc-mode revertive on the interface";
        } // END of enable-revertive-mode definition.

        leaf revertive-timer  {
            // when " ../enable-revertive-mode ";
            type  uint16 {
                 range "0..3600"  {
                    description "0..3600: Supported range 0 - 3600";
                 }
            }
            description "This attribute is used to configure the vpws vc revertive timer.
                        Default value is 0";
        } // END of revertive-timer definition.

        leaf mac-withdrawal-send-on-vpws-vc-switchover  {
            type  empty;
            description "This attribute is used to configure mac withdrawal on vpws vc
                        switchover";
        } // END of mac-withdrawal-send-on-vpws-vc-switchover definition.

    } // END of l2vpn-vpws-config definition.
    grouping l2vpn-vpws-bind-config {
        description
            "Grouping for L2VPN VPWS bind configuration";
        leaf vpws-name  {
            type  string {
                length "1..128";
                pattern "[^?' =,>|]+";
            }
            description "This attribute uniquely identifies a VPWS service on Subinterface";
        } // END of vpws-name definition.

        leaf pseudowire-link-mode  {
            type  ipi-vpws-types:vpws_mpls_vclinkmode_t;
            mandatory true;
            description "This attribute is used to configure link mode as primary/secondary on
                        VPWS service. Default value is 0";
        } // END of pseudowire-link-mode definition.

    } // END of l2vpn-vpws-bind-config definition.
    grouping vpws-interface-top {
        description
            "Top level grouping for interface level configuration for PW";
        container interfaces {
            description
                "Top level container for interface level configuration for VPWS";

            list interface {
                key "name";
                description
                    "VPWS interface related configuration";
                leaf name  {
                    type  leafref {
                        path  "../config/name";
                    }
                    description "This attribute describes the interface on which attachment circuit is
                                to be created for  pseudowire.";
                } // END of name definition.

                container config {
                    description
                        "Configuration container for interface list";
                    uses vpws-interface-config;
                } // END of config-container definition.
                container state {
                    config false;
                    description
                        "Operation container for interface list";
                    uses vpws-interface-config;
                } // END of state-container definition.
                container pseudowire-modes {
                    description
                        "Container for VPWS interface modes related configuration";

                    list pseudowire-mode {
                        key "service-template";
                        description
                            "VPWS interface mode related configuration";
                        leaf service-template  {
                            type  leafref {
                                path  "../config/service-template";
                            }
                            description "This attribute is used to configure service-template for vc-mode";
                        } // END of service-template definition.

                        container config {
                            description
                                "Configuration data";
                            uses vpws-interface-global-config;
                        } // END of config-container definition.
                        container state {
                            config false;
                            description
                                "Container for Operational attributes";
                            uses vpws-interface-global-config;
                        } // END of state-container definition.
                    } // End of pseudowire-mode-list
                } // END of pseudowire-modes-container definition.
                uses l2vpn-vpws-top;
                uses vpws-service-template-mapping-top;
            } // End of interface-list
        } // END of interfaces-container definition.
    } // END of vpws-interface-top definition.
    grouping vpws-interface-global-config {
        description
            "Grouping for global interface level configuration for PW";
        leaf service-template  {
            type  string {
                length "1..1965";
                pattern "[^?' =,>|]+";
            }
            description "This attribute is used to configure service-template for vc-mode";
        } // END of service-template definition.

        leaf mode  {
            type  ipi-vpws-types:vpws_mpls_vcmode_t;
            mandatory true;
            description "This attribute is used to configure vc-mode revertive or standy on the
                        interface on which attachment circuit is created for pseudowire.";
        } // END of mode definition.

    } // END of vpws-interface-global-config definition.
    grouping vpws-service-template-mapping-top {
        description
            "Top level grouping for service-template mapping configuration for VPWS";
        container service-template-mappings {
            description
                "Container for VPWS mappings to service-template-mappings on interface";

            list service-template-mapping {
            when " /ipi-interface:interfaces/ipi-interface:interface/ipi-interface:config/ipi-interface:enable-switchport ";
                key "pseudowire-name";
                description
                    "List for VPWS mapping to service-template-mapping on interface";
                leaf pseudowire-name  {
                    type  leafref {
                        path  "../config/pseudowire-name";
                    }
                    description "Use this attribute to specify pseudowire name";
                } // END of pseudowire-name definition.

                container config {
                    description
                        "Configuration data";
                    uses vpws-service-template-mapping-config;
                } // END of config-container definition.
                container state {
                    config false;
                    description
                        "Container for Operational attributes";
                    uses vpws-service-template-mapping-config;
                } // END of state-container definition.
            } // End of service-template-mapping-list
        } // END of service-template-mappings-container definition.
    } // END of vpws-service-template-mapping-top definition.
    grouping vpws-service-template-mapping-config {
        description
            "Grouping for service-template mapping configurationattributes for VPWS";
        leaf pseudowire-name  {
            type  string {
                length "1..1965";
                pattern "[^?' =,>|]+";
            }
            description "This attribute is used to map pseudowire on customer interface for
                        attachment circuit";
        } // END of pseudowire-name definition.

        leaf service-template-name  {
            type  leafref {
                path  "/ipi-mpls:mpls/ipi-mpls:l2vpn/ipi-mpls:customer-service-templates/ipi-mpls:customer-service-template/ipi-mpls:name";
            }
            mandatory true;
            description "This attribute is used to map service-template on customer interface
                        for attachment circuit";
        } // END of service-template-name definition.

        leaf pseudowire-link-mode  {
            type  ipi-vpws-types:vpws_mpls_vclinkmode_t;
            mandatory true;
            description "This attribute is used to configure link mode as primary/secondary on
                        customer interface for attachment circuit";
        } // END of pseudowire-link-mode definition.

        leaf cos-to-queue-profile-name  {
            when " /ipi-qos:qos/ipi-qos:global/ipi-qos:map-profile/ipi-qos:cos-to-queue-profiles/ipi-qos:cos-to-queue-profile/ipi-qos:name ";
            if-feature feature-list:HAVE_QOS_MAPPING_PROFILE;
            type  string {
                length "1..1965";
                pattern "[^?' =,>|]+";
            }
            description "This attribute is used to map cos-to-queue profile on customer
                        interface for attahment circuit";
        } // END of cos-to-queue-profile-name definition.

        leaf queue-to-cos-profile-name  {
            when " /ipi-qos:qos/ipi-qos:global/ipi-qos:map-profile/ipi-qos:queue-color-to-cos-profiles/ipi-qos:queue-color-to-cos-profile/ipi-qos:name ";
            if-feature feature-list:HAVE_QOS_MAPPING_PROFILE;
            if-feature feature-list:NOT_HAVE_CUSTOM1_MPLS;
            type  string {
                length "1..1965";
                pattern "[^?' =,>|]+";
            }
            description "This attribute is used to map queue-to-cos profile on customer
                        interface for attahment circuit";
        } // END of queue-to-cos-profile-name definition.

    } // END of vpws-service-template-mapping-config definition.
    grouping vpws-static-forwarding-top {
        description
            "Top level grouping for static FIB configuration for VPWS";
        container static-forwarding {
            description
                "Top level container for Static VPWS FIB configuration";
            container forwarding-information-bases {
                description
                    "Enclosing container for VPWS static FIB entries";

                list forwarding-information-base {
                when " /ipi-network-instance:network-instances/ipi-network-instance:network-instance/ipi-l2vpn-vpws:vpws-instance/ipi-l2vpn-vpws:pseudowires/ipi-l2vpn-vpws:pseudowire/ipi-l2vpn-vpws:default-tagged/ipi-l2vpn-vpws:config/ipi-l2vpn-vpws:enable-manual-pseudowire or /ipi-network-instance:network-instances/ipi-network-instance:network-instance/ipi-l2vpn-vpws:vpws-instance/ipi-l2vpn-vpws:pseudowires/ipi-l2vpn-vpws:pseudowire/ipi-l2vpn-vpws:tagged/ipi-l2vpn-vpws:config/ipi-l2vpn-vpws:enable-manual-pseudowire or /ipi-network-instance:network-instances/ipi-network-instance:network-instance/ipi-l2vpn-vpws:vpws-instance/ipi-l2vpn-vpws:pseudowires/ipi-l2vpn-vpws:pseudowire/ipi-l2vpn-vpws:raw/ipi-l2vpn-vpws:config/ipi-l2vpn-vpws:enable-manual-pseudowire ";
                // when " ../forwarding-information-base/config/access-interface-name ";
                    key "pseudowire-identifier nexthop-address";
                    description
                        "VPWS static FIB entries configuration list";
                    leaf pseudowire-identifier  {
                        type  leafref {
                            path  "../config/pseudowire-identifier";
                        }
                        description "Use this attribute to configure pseudowire identifier";
                    } // END of pseudowire-identifier definition.

                    leaf nexthop-address  {
                        type  leafref {
                            path  "../config/nexthop-address";
                        }
                        description "This attribute is used to configure VC next-hop address for static VC
                                    fib entry";
                    } // END of nexthop-address definition.

                    container config {
                        description
                            "Configuration data";
                        uses vpws-forwarding-information-base-config;
                    } // END of config-container definition.
                    container state {
                        config false;
                        description
                            "Container for Operational attributes";
                        uses vpws-forwarding-information-base-config;
                    } // END of state-container definition.
                } // End of forwarding-information-base-list
            } // END of forwarding-information-bases-container definition.
        } // END of static-forwarding-container definition.
    } // END of vpws-static-forwarding-top definition.
    grouping vpws-forwarding-information-base-config {
        description
            "Grouping for static FIB configuration for VPWS";
        leaf pseudowire-identifier  {
            type  leafref {
                path  "/ipi-network-instance:network-instances/ipi-network-instance:network-instance/vpws-instance/pseudowires/pseudowire/config/pseudowire-identifier";
            }
            description "This attribute is used to map static pseudowire identifier for
                        creating static VC fib entry";
        } // END of pseudowire-identifier definition.

        leaf incoming-label  {
            type  uint32 {
                 range "16..52443"  {
                    description "16..52443:Feature : HAVE_SR_MPLS Supported range 16 - 15999Not Feature
                            : HAVE_SR_MPLS  Supported range 16 - 52443";
                 }
            }
            mandatory true;
            description "This attribute is used to configure in-label for static VC fib entry";
        } // END of incoming-label definition.

        leaf outgoing-label  {
            type  uint32 {
                 range "16..52443"  {
                    description "16..52443:Feature : HAVE_SR_MPLS Supported range 16 - 15999Not Feature
                            : HAVE_SR_MPLS  Supported range 16 - 52443";
                 }
            }
            mandatory true;
            description "This attribute is used to configure out-label for static VC fib entry";
        } // END of outgoing-label definition.

        leaf nexthop-address  {
            type  inet:ip-address;
            description "This attribute is used to configure VC next-hop address for static VC
                        fib entry";
        } // END of nexthop-address definition.

        leaf provider-interface-name  {
            type  leafref {
                path  "/ipi-interface:interfaces/ipi-interface:interface/ipi-interface:name";
            }
            mandatory true;
            description "This attribute is used to configure provider network interface for
                        static VC fib entry";
        } // END of provider-interface-name definition.

        leaf access-interface-name  {
            type  leafref {
                path  "/vpws/interfaces/interface/name";
            }
            mandatory true;
            description "This attribute is used to configure customer network interface for
                        static VC fib entry";
        } // END of access-interface-name definition.

    } // END of vpws-forwarding-information-base-config definition.
    grouping vpws-access-interface-counters-state {
        description
            "Top level grouping for access-interface-counters";
        leaf interface-name  {
            type  leafref {
                path  "/ipi-interface:interfaces/ipi-interface:interface/ipi-interface:name";
            }
            description "Attribute to acquire access interface name";
        } // END of interface-name definition.

        leaf pseudowire-identifier  {
            type  uint32;
            description "Attribute to acquire pw-id for a VPWS instance";
        } // END of pseudowire-identifier definition.

        leaf service-template-name  {
            type  string {
                length "1..1965";
                pattern "[^?' =,>|]+";
            }
            description "Attribute to acquire Service Template name mapped to this vpws AC
                        interface";
        } // END of service-template-name definition.

        leaf in-packets  {
            type  uint64;
            description "Attribute to acquire number of received(Rx) packets on this AC
                        interface";
        } // END of in-packets definition.

        leaf in-bytes  {
            type  uint64;
            description "Attribute to acquire number of received(Rx) bytes on this AC interface";
        } // END of in-bytes definition.

        leaf out-packets  {
            type  uint64;
            description "Attribute to acquire number of sent(Tx) packets on this AC interface";
        } // END of out-packets definition.

        leaf out-bytes  {
            type  uint64;
            description "Attribute to acquire number of sent(Tx) bytes on this AC interface";
        } // END of out-bytes definition.

    } // END of vpws-access-interface-counters-state definition.
    grouping vpws-network-interface-counters-state {
        description
            "Top level grouping for network-interface-counters";
        leaf peer-address  {
            type  inet:ipv4-address;
            description "Attribute to acquire peer-address for VPWS instance";
        } // END of peer-address definition.

        leaf pseudowire-identifier  {
            type  uint32;
            description "Attribute to acquire vpls-id for a VPWS instance";
        } // END of pseudowire-identifier definition.

        leaf interface-name  {
            type  leafref {
                path  "/ipi-interface:interfaces/ipi-interface:interface/ipi-interface:name";
            }
            description "Attribute to acquire network interface name";
        } // END of interface-name definition.

        leaf in-packets  {
            type  uint64;
            description "Attribute to acquire number of received(Rx) packets on this network
                        interface";
        } // END of in-packets definition.

        leaf in-bytes  {
            type  uint64;
            description "Attribute to acquire number of received(Rx) bytes on this network
                        interface";
        } // END of in-bytes definition.

        leaf out-packets  {
            type  uint64;
            description "Attribute to acquire number of sent(Tx) packets on this network
                        interface";
        } // END of out-packets definition.

        leaf out-bytes  {
            type  uint64;
            description "Attribute to acquire number of sent(Tx) bytes on this network
                        interface";
        } // END of out-bytes definition.

    } // END of vpws-network-interface-counters-state definition.
    grouping vpws-counters-top {
        description
            "Top level grouping for Counters";

        list access-interface-counters {
            if-feature feature-list:HAVE_MPLS_STATS;
            key "interface-name";
            config false;
            description
                "List of Access Interface Counters";
            leaf interface-name  {
                type  leafref {
                    path  "../state/interface-name";
                }
                description "Use this attribute to configure interface name";
            } // END of interface-name definition.

            container state {
                config false;
                description
                    "Operational state data";
                uses vpws-access-interface-counters-state;
            } // END of state-container definition.
        } // End of access-interface-counters-list

        list network-interface-counters {
            if-feature feature-list:HAVE_MPLS_STATS;
            key "peer-address";
            config false;
            description
                "List of Network Interface Counters";
            leaf peer-address  {
                type  leafref {
                    path  "../state/peer-address";
                }
                description "Attribute to specify peer-address for VPWS instance";
            } // END of peer-address definition.

            container state {
                config false;
                description
                    "Operational state data";
                uses vpws-network-interface-counters-state;
            } // END of state-container definition.
        } // End of network-interface-counters-list
    } // END of vpws-counters-top definition.
    grouping vpws-state-global-counters {
        description
            "Grouping for runtime counters attributes";
        leaf total-pseudowires  {
            type  uint32;
            config false;
            description "This attribute provides total number of pseudowires created";
        } // END of total-pseudowires definition.

        leaf active-pseudowires  {
            type  uint32;
            config false;
            description "This attribute provides total number of pseudowires active";
        } // END of active-pseudowires definition.

        leaf inactive-pseudowires  {
            type  uint32;
            config false;
            description "This attribute provides total number of pseudowires inactive";
        } // END of inactive-pseudowires definition.

        leaf oam-pseudowires  {
            type  uint32;
            config false;
            description "This attribute provides total number of oam pseudowires";
        } // END of oam-pseudowires definition.

    } // END of vpws-state-global-counters definition.
    grouping vpws-global-state-top {
        description
            "Top level grouping for runtime data for VPWS";
        container global {
            config false;
            description
                "Top level container for global state data";
            container state {
                config false;
                description
                    "State container for global state data";
                container counters {
                    config false;
                    description
                        "Container for VPWS counters data";
                    uses vpws-state-global-counters;
                } // END of counters-container definition.
            } // END of state-container definition.
        } // END of global-container definition.
    } // END of vpws-global-state-top definition.
    grouping vpws-pseudowire-state {
        description
            "Grouping for runtime attributes for pseudowire";
        leaf vc-admin-status  {
            if-feature feature-list:HAVE_UNI_CLI;
            type  ipi-vpws-types:vpws_mpls_vc_admin_status_t;
            config false;
            description "This attribute provides admin-status of pseudowire";
        } // END of vc-admin-status definition.

        leaf up-time  {
            type  cml-data-types:cml_line_t {
                length "1..1965";
            }
            config false;
            description "This attribute provides time when pseudowire comes to forwarding state";
        } // END of up-time definition.

        leaf transport-update  {
            type  cml-data-types:cml_line_t {
                length "1..1965";
            }
            config false;
            description "This attribute provides time when transport gets updated";
        } // END of transport-update definition.

        leaf create-time  {
            type  cml-data-types:cml_line_t {
                length "1..1965";
            }
            config false;
            description "This attribute provides time when pseudowire was created";
        } // END of create-time definition.

        leaf owner  {
            type  ipi-vpws-types:vpws_mpls_vc_owner_t;
            config false;
            description "This attribute provides owner name of pseudowire";
        } // END of owner definition.

        leaf non-te-mapping-direction  {
            type  ipi-vpws-types:vpws_mpls_mapping_dir_t;
            config false;
            description "This attribute provides mapping direction of pseudowire";
        } // END of non-te-mapping-direction definition.

        leaf remote-pseudowire-status  {
            type  ipi-vpws-types:vpws_mpls_pw_status_t;
            config false;
            description "This attribute provides pseudowire status of the peer end node";
        } // END of remote-pseudowire-status definition.

        leaf pseudowire-state  {
            type  ipi-vpws-types:vpws_mpls_pw_state_t;
            config false;
            description "This attribute provides local pseudowire state";
        } // END of pseudowire-state definition.

        leaf pseudowire-index  {
            type  uint32;
            config false;
            description "This attribute provides pseudowire index";
        } // END of pseudowire-index definition.

        leaf pseudowire-type  {
            type  ipi-vpws-types:vpws_mpls_pw_type_t;
            config false;
            description "This attribute provides type of pseudowire information";
        } // END of pseudowire-type definition.

        leaf pseudowire-mode  {
            type  ipi-vpws-types:vpws_mpls_pw_mode_t;
            config false;
            description "This attribute provides mode of pseudowire information";
        } // END of pseudowire-mode definition.

        leaf pseudowire-label  {
            type  uint32;
            config false;
            description "This attribute provides pseudowire out label information";
        } // END of pseudowire-label definition.

        leaf tunnel-label  {
            type  uint32;
            config false;
            description "This attribute provides tunnel label information";
        } // END of tunnel-label definition.

        leaf network-interface-name  {
            type  string {
                length "1..1965";
                pattern "[^?' =,>|]+";
            }
            config false;
            description "This attribute provides network provider interface name for the
                        pseudowire";
        } // END of network-interface-name definition.

        leaf customer-service-template-name  {
            type  string {
                length "1..1965";
                pattern "[^?' =,>|]+";
            }
            config false;
            description "This attribute provides service template name mapping on this
                        pseudowire";
        } // END of customer-service-template-name definition.

        leaf ldp-ecmp-svc  {
            if-feature feature-list:HAVE_MPLS_ECMP;
            type  string {
                length "1..1965";
                pattern "[^?' =,>|]+";
            }
            description "Added this attribute to check service mapped over LDP ECMP";
        } // END of ldp-ecmp-svc definition.

        leaf rsvp-multipath-svc  {
            if-feature feature-list:HAVE_RSVP_MULTIPATH;
            type  string {
                length "1..1965";
                pattern "[^?' =,>|]+";
            }
            description "Added this attribute to check service mapped for RSVP multipath
                        transport";
        } // END of rsvp-multipath-svc definition.

        leaf down-reason  {
            type  cml-data-types:cml_line_t {
                length "1..1965";
            }
            config false;
            description "Specifies the reason for VC down";
        } // END of down-reason definition.

    } // END of vpws-pseudowire-state definition.

    grouping  vpws-instance-grouping {
    description
        "Top level container for vpws instance";
    container vpws-instance {
        if-feature feature-list:HAVE_MPLS;
        if-feature feature-list:HAVE_MPLS_VC;
        description
            "Top level container for vpws instance";
        container pseudowires {
            description
                "Enclosing container for FEC-128 pseudowires";

            list pseudowire {
            // when " ipi-l2vpn-vpws:vpws-instance/pseudowires/pseudowire/raw/config/enable-raw-mode || ipi-l2vpn-vpws:vpws-instance/pseudowires/pseudowire/tagged/config/enable-tagged-mode || ipi-l2vpn-vpws:vpws-instance/pseudowires/pseudowire/default-tagged/config/enable-default-tagged-mode ";
                key "pseudowire-identifier peer-address";
                description
                    "Object list for FEC-128 pseudowire";
                leaf pseudowire-identifier  {
                    type  leafref {
                        path  "../config/pseudowire-identifier";
                    }
                    description "Use this attribute to assign pseudowire identifier to create an
                                instance of an MPLS layer 2 virtual circuit. A Layer-2 MPLS Virtual
                                Circuit instance may be bound to any interface on the router; however,
                                only one interface may be bound to a Layer-2 circuit at a time.";
                } // END of pseudowire-identifier definition.

                leaf peer-address  {
                    type  leafref {
                        path  "../config/peer-address";
                    }
                    description "Use this attribute to specify pseudowire end peer IP address to create
                                an instance of an MPLS layer 2 virtual circuit";
                } // END of peer-address definition.

                container config {
                    description
                        "Top level configuration data for Fec128 pseudowire";
                    uses vpws-pseudowire-config;
                } // END of config-container definition.
                container state {
                    config false;
                    description
                        "Container for Operational attributes for pseudowire";
                    uses vpws-pseudowire-config;
                    uses vpws-pseudowire-state;
                } // END of state-container definition.
                container default-tagged {
                    // when " not(/ipi-network-instance:network-instances/ipi-network-instance:network-instance/ipi-l2vpn-vpws:vpws-instance/ipi-l2vpn-vpws:pseudowires/ipi-l2vpn-vpws:pseudowire/ipi-l2vpn-vpws:raw/ipi-l2vpn-vpws:config/ipi-l2vpn-vpws:enable-raw-mode) + not(/ipi-network-instance:network-instances/ipi-network-instance:network-instance/ipi-l2vpn-vpws:vpws-instance/ipi-l2vpn-vpws:pseudowires/ipi-l2vpn-vpws:pseudowire/ipi-l2vpn-vpws:tagged/ipi-l2vpn-vpws:config/ipi-l2vpn-vpws:enable-tagged-mode) ";
                    description
                        "Default Tagged container for Fec128 pseudowire";
                    container config {
                        presence "Create Default-Tagged VPWS Fec-128 Instance";
                        description
                            "Top level configuration data for Fec128 pseudowire";
                        uses vpws-pseudowire-default-tagged-config;
                        uses vpws-pseudowire-service-tpid-config;
                        uses vpws-pseudowire-common-config;
                        uses vpws-pseudowire-fat-config;
                        uses vpws-pseudowire-static-config;
                        uses vpws-pseudowire-mplstp-config;
                        uses vpws-pseudowire-vccv-config;
                    } // END of config-container definition.
                    container state {
                        config false;
                        description
                            "Container for Operational attributes for pseudowire";
                        uses vpws-pseudowire-default-tagged-config;
                        uses vpws-pseudowire-service-tpid-config;
                        uses vpws-pseudowire-common-config;
                        uses vpws-pseudowire-fat-config;
                        uses vpws-pseudowire-static-config;
                        uses vpws-pseudowire-mplstp-config;
                        uses vpws-pseudowire-vccv-config;
                    } // END of state-container definition.
                } // END of default-tagged-container definition.
                container tagged {
                    // when " not(/ipi-network-instance:network-instances/ipi-network-instance:network-instance/ipi-l2vpn-vpws:vpws-instance/ipi-l2vpn-vpws:pseudowires/ipi-l2vpn-vpws:pseudowire/ipi-l2vpn-vpws:default-tagged/ipi-l2vpn-vpws:config/ipi-l2vpn-vpws:enable-default-tagged-mode) + not(/ipi-network-instance:network-instances/ipi-network-instance:network-instance/ipi-l2vpn-vpws:vpws-instance/ipi-l2vpn-vpws:pseudowires/ipi-l2vpn-vpws:pseudowire/ipi-l2vpn-vpws:raw/ipi-l2vpn-vpws:config/ipi-l2vpn-vpws:enable-raw-mode) ";
                    description
                        "Container for Tagged Fec128 pseudowire";
                    container config {
                        presence "Create Tagged VPWS Fec-128 Instance";
                        description
                            "Configuration data for Tagged Fec128 pseudowire";
                        uses vpws-pseudowire-tagged-config;
                        uses vpws-pseudowire-common-config;
                        uses vpws-pseudowire-static-config;
                        uses vpws-pseudowire-mplstp-config;
                        uses vpws-pseudowire-fat-config;
                        uses vpws-pseudowire-vccv-config;
                    } // END of config-container definition.
                    container state {
                        config false;
                        description
                            "Container for Operational attributes for pseudowire";
                        uses vpws-pseudowire-tagged-config;
                        uses vpws-pseudowire-common-config;
                        uses vpws-pseudowire-static-config;
                        uses vpws-pseudowire-mplstp-config;
                        uses vpws-pseudowire-fat-config;
                        uses vpws-pseudowire-vccv-config;
                    } // END of state-container definition.
                } // END of tagged-container definition.
                container raw {
                    // when " not(/ipi-network-instance:network-instances/ipi-network-instance:network-instance/ipi-l2vpn-vpws:vpws-instance/ipi-l2vpn-vpws:pseudowires/ipi-l2vpn-vpws:pseudowire/ipi-l2vpn-vpws:default-tagged/ipi-l2vpn-vpws:config/ipi-l2vpn-vpws:enable-default-tagged-mode) + not(/ipi-network-instance:network-instances/ipi-network-instance:network-instance/ipi-l2vpn-vpws:vpws-instance/ipi-l2vpn-vpws:pseudowires/ipi-l2vpn-vpws:pseudowire/ipi-l2vpn-vpws:tagged/ipi-l2vpn-vpws:config/ipi-l2vpn-vpws:enable-tagged-mode) ";
                    description
                        "Container for Raw Fec128 pseudowire";
                    container config {
                        presence "Create Raw VPWS Fec-128 Instance";
                        description
                            "Configuration data for Raw Fec128 pseudowire";
                        uses vpws-pseudowire-raw-config;
                        uses vpws-pseudowire-common-config;
                        uses vpws-pseudowire-static-config;
                        uses vpws-pseudowire-mplstp-config;
                        uses vpws-pseudowire-vccv-config;
                        uses vpws-pseudowire-fat-config;
                    } // END of config-container definition.
                    container state {
                        config false;
                        description
                            "Container for Operational attributes for pseudowire";
                        uses vpws-pseudowire-raw-config;
                        uses vpws-pseudowire-common-config;
                        uses vpws-pseudowire-static-config;
                        uses vpws-pseudowire-mplstp-config;
                        uses vpws-pseudowire-fat-config;
                        uses vpws-pseudowire-vccv-config;
                    } // END of state-container definition.
                } // END of raw-container definition.
            } // End of pseudowire-list
        } // END of pseudowires-container definition.
        uses vpws-counters-top;
    } // END of vpws-instance-container definition.
    } // END of vpws-instance-grouping definition.

    grouping  vpws-grouping {
    description
        "Top level container for vpws related configurations";
    container vpws {
        if-feature feature-list:HAVE_MPLS;
        if-feature feature-list:HAVE_MPLS_VC;
        description
            "Top level container for vpws related configurations";
        uses vpws-interface-top;
        uses vpws-static-forwarding-top;
        uses vpws-global-state-top;
    } // END of vpws-container definition.
    } // END of vpws-grouping definition.

    augment /ipi-network-instance:network-instances/ipi-network-instance:network-instance {
    when " /ipi-network-instance:network-instances/ipi-network-instance:network-instance/ipi-network-instance:instance-type = 'vpws' ";
        description
            "Top level container for vpws instance";
        uses vpws-instance-grouping;
    }

    uses vpws-grouping;

    rpc pseudowire-trap-configuration {
        if-feature feature-list:HAVE_SNMP;
        if-feature feature-list:HAVE_MPLS;
        if-feature feature-list:HAVE_MPLS_VC;
        description "Use this RPC to set the Pseudowire Trap Notification for SNMP";
        input  {
            leaf status-notification  {
                type boolean;
                mandatory true;
                description "Use this attribute to specify status change notification";
            }
            leaf delete-notification  {
                type boolean;
                mandatory true;
                description "Use this attribute to specify delete notification";
            }
            leaf configure-notification  {
                type cml-data-types:cml_enable_disable_t;
                mandatory true;
                description "Use this attribute to enable or disable configure notification";
            }
        }
    }

    rpc clear-mpls-l2-circuit-statistics {
        if-feature feature-list:HAVE_MPLS_STATS;
        if-feature feature-list:HAVE_MPLS_VC;
        if-feature feature-list:HAVE_MPLS;
        description "Use this attribute to Clear MPLS L2-Circuit Statistics";
        input  {
            leaf pseudowire-name  {
                type string;
                mandatory true;
                description "Use this attribute to configure pseudowire name";
            }
        }
    }

    rpc clear-mpls-l2-circuit-port-statistics {
        if-feature feature-list:HAVE_MPLS_STATS;
        if-feature feature-list:HAVE_MPLS_VC;
        if-feature feature-list:HAVE_MPLS;
        description "Use this attribute to Clear MPLS L2-Circuit Statistics by PortType";
        input  {
            leaf port-type  {
                type ipi-vpws-types:vpws_mpls_port_type_t;
                mandatory true;
                description "Use this attribute to configure port type";
            }
            leaf port-pseudowire-name  {
                type string;
                mandatory true;
                description "Use this attribute to configure port pseudowire name";
            }
        }
    }

    rpc pseudowire-manual-switchover {
        if-feature feature-list:HAVE_MPLS_VC;
        if-feature feature-list:HAVE_MPLS;
        description "Use this RPC to manually Switchover between VC's";
        input  {
            leaf primary-pseudowire  {
                type string;
                mandatory true;
                description "Use this attribute to specify primary pseudowire name";
            }
            leaf secondary-pseudowire  {
                type string;
                mandatory true;
                description "Use this attribute to specify secondary pseudowire name";
            }
        }
    }

    notification mpls-pseudowire-up {
        if-feature feature-list:HAVE_MPLS;
        if-feature feature-list:HAVE_MPLS_VC;

        description "This notification is sent when pseusowire-state enters the up(4) state.";

        leaf severity {
            type cml-data-types:cml_notif_severity_t;
            description "Notification severity level (value: MINOR)";
        }

        leaf eventClass {
            type cml-data-types:cml_notif_class_t;
            description "Notification event class (value: STATE)";
        }

        leaf pseudowire-identifier {
            type  uint32;
        description
            "Use this attribute to assign pseudowire identifier to create an
                    instance of an MPLS layer 2 virtual circuit. A Layer-2 MPLS Virtual
                    Circuit instance may be bound to any interface on the router; however,
                    only one interface may be bound to a Layer-2 circuit at a time.";
        }

        leaf peer-address {
            type ipi-vpws-types:vpws_ip_addr_t;
        description
            "Use this attribute to specify pseudowire end peer IP address to create
                    an instance of an MPLS layer 2 virtual circuit";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf pseudowire-state {
            type ipi-vpws-types:vpws_mpls_pw_state_t;
        description
            "This attribute provides local pseudowire state";
        }
    }

    notification mpls-pseudowire-down {
        if-feature feature-list:HAVE_MPLS;
        if-feature feature-list:HAVE_MPLS_VC;

        description "This notification is sent when pseusowire-state enters the down(1) state.";

        leaf severity {
            type cml-data-types:cml_notif_severity_t;
            description "Notification severity level (value: CRITICAL)";
        }

        leaf eventClass {
            type cml-data-types:cml_notif_class_t;
            description "Notification event class (value: STATE)";
        }

        leaf pseudowire-identifier {
            type  uint32;
        description
            "Use this attribute to assign pseudowire identifier to create an
                    instance of an MPLS layer 2 virtual circuit. A Layer-2 MPLS Virtual
                    Circuit instance may be bound to any interface on the router; however,
                    only one interface may be bound to a Layer-2 circuit at a time.";
        }

        leaf peer-address {
            type ipi-vpws-types:vpws_ip_addr_t;
        description
            "Use this attribute to specify pseudowire end peer IP address to create
                    an instance of an MPLS layer 2 virtual circuit";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf pseudowire-state {
            type ipi-vpws-types:vpws_mpls_pw_state_t;
        description
            "This attribute provides local pseudowire state";
        }
    }

    notification mpls-pseudowire-deleted {
        if-feature feature-list:HAVE_MPLS;
        if-feature feature-list:HAVE_MPLS_VC;

        description "This notification is sent when pseusowire is deleted.";

        leaf severity {
            type cml-data-types:cml_notif_severity_t;
            description "Notification severity level (value: MINOR)";
        }

        leaf eventClass {
            type cml-data-types:cml_notif_class_t;
            description "Notification event class (value: STATE)";
        }

        leaf pseudowire-identifier {
            type  uint32;
        description
            "Use this attribute to assign pseudowire identifier to create an
                    instance of an MPLS layer 2 virtual circuit. A Layer-2 MPLS Virtual
                    Circuit instance may be bound to any interface on the router; however,
                    only one interface may be bound to a Layer-2 circuit at a time.";
        }

        leaf peer-address {
            type ipi-vpws-types:vpws_ip_addr_t;
        description
            "Use this attribute to specify pseudowire end peer IP address to create
                    an instance of an MPLS layer 2 virtual circuit";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf pseudowire-state {
            type ipi-vpws-types:vpws_mpls_pw_state_t;
        description
            "This attribute provides local pseudowire state";
        }
    }

}
