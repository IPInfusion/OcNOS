/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-l2vpn-vpls.yang
*
*/

module ipi-l2vpn-vpls {

    yang-version 1.1;

    namespace   "http://www.ipinfusion.com/yang/ocnos/ipi-l2vpn-vpls";

    prefix "ipi-l2vpn-vpls";

    import cml-data-types {
        prefix cml-data-types;
        revision-date 2026-05-15;
    }

    import ipi-if-types {
        prefix ipi-if-types;
        revision-date 2026-03-10;
    }

    import ipi-vpls-types {
        prefix ipi-vpls-types;
        revision-date 2024-12-16;
    }

    import ietf-inet-types {
        prefix inet;
        revision-date 2013-07-15;
    }

    import ietf-yang-types {
        prefix yang;
        revision-date 2013-07-15;
    }

    import ipi-interface {
        prefix ipi-interface;
        revision-date 2026-03-10;
    }

    import ipi-network-instance-types {
        prefix ipi-network-instance-types;
        revision-date 2023-03-14;
    }

    import ipi-network-instance {
        prefix ipi-network-instance;
        revision-date 2026-08-12;
    }

    import ipi-mpls {
        prefix ipi-mpls;
        revision-date 2026-08-27;
    }

    import ipi-qos {
        prefix ipi-qos;
        revision-date 2026-09-09;
    }

    import ipi-l2vpn-vpws {
        prefix ipi-l2vpn-vpws;
        revision-date 2026-03-31;
    }

    import ipi-bgp-types {
        prefix ipi-bgp-types;
        revision-date 2025-12-22;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-l2vpn-vpls";


    revision "2026-03-10" {
        description "Added the datatype for media-type attribute";
        reference " 0.14.4.";
    }

    revision "2026-02-04" {
        description "Added implicit delete to mac-move-global config'";
        reference " 0.14.3.";
    }

    revision "2025-12-22" {
        description "Added BGP Origin Autonomous System (AS) validation state enumarate";
        reference " 0.14.2.";
    }

    revision "2025-12-15" {
        description "Add correct cliprependstr helpstrings";
        reference " 0.14.1.";
    }

    revision "2025-12-11" {
        description "Support for VPLS notification";
        reference " 0.13.18.";
    }

    revision "2025-11-04" {
        description "Added new attribute uptime for VPLS peer-list";
        reference " 0.13.17.";
    }

    revision "2025-10-10" {
        description "Dlink 'disable-oper-logs' from 'debug bgp all'";
        reference " 0.13.16.";
    }

    revision "2025-10-09" {
        description "Added hidden-cli for service-template-mapping";
        reference " 0.13.15.";
    }

    revision "2025-09-25" {
        description "Changed H-VPLS secondary pseudowire to include CML_SKIP_HITLESS_MERGE flag";
        reference " 0.13.14.";
    }

    revision "2025-09-24" {
        description "Changed the datatype for ether-type attribute";
        reference " 0.12.13.";
    }

    revision "2025-09-15" {
        description "Revert updated BGP_ROUTE_TARGET_TYPE_T for EVPN VXLAN feature";
        reference " 0.13.12.";
    }

    revision "2025-09-12" {
        description "Added ref of learning limit to spoke vpls and vpls access port";
        reference " 0.13.11.";
    }

    revision "2025-09-11" {
        description "Updated BGP_ROUTE_TARGET_TYPE_T for EVPN VXLAN stitching feature";
        reference " 0.13.10.";
    }

    revision "2025-08-27" {
        description "Added streaming telemetry support";
        reference " 0.13.9.";
    }

    revision "2025-08-23" {
        description "Spoke vc-mode revertive with timer support";
        reference " 0.13.8.";
    }

    revision "2025-08-22" {
        description "Changed error disable type from bits to enum";
        reference " 0.13.7.";
    }

    revision "2025-08-21" {
        description "Displayed remote VE-ID and mtu support";
        reference " 0.13.6.";
    }

    revision "2025-08-20" {
        description "Introduced  new bgp debug options 'debug bgp rpki' ";
        reference " 0.13.5.";
    }

    revision "2025-08-11" {
        description "Added two new bgp debug options to disable oper logs";
        reference " 0.13.4.";
    }

    revision "2025-07-07" {
        description "Remove 'errdisable-timeout' config when action 'log-errdisable' is removed using 'no action'";
        reference " 0.13.3.";
    }

    revision "2025-06-27" {
        description "New cmd added - l2protocol all learn-disable";
        reference " 0.13.2.";
    }

    revision "2025-06-25" {
        description "Updated datatype 'IF_ERRDISABLE_STATE_T 'values";
        reference " 0.13.1.";
    }

    revision "2025-06-13" {
        description "Updated the description for the large community";
        reference " 0.13.0.";
    }

    revision "2025-06-03" {
        description "Added port dfe and unreliable-los support";
        reference " 0.12.46.";
    }

    revision "2025-05-09" {
        description "Fix compilation warnings";
        reference " 0.12.45.";
    }

    revision "2025-04-28" {
        description "VPLS mac limit made correction to group name to match datamodel";
        reference " 0.12.44.";
    }

    revision "2025-04-25" {
        description "Added helpstring to the unset cli command of static flow-label";
        reference " 0.12.43.";
    }

    revision "2025-03-19" {
        description "VPLS mac move support updated state container";
        reference " 0.12.42.";
    }

    revision "2025-03-17" {
        description "Revert of EFM flag for l2pt efm CLI";
        reference " 0.12.41.";
    }

    revision "2025-02-25" {
        description "Removed BGP AD VPLS commit check for vpls-peer";
        reference " 0.12.40.";
    }

    revision "2025-02-24" {
        description "Added unique flag for secondary-pseudowire-name attributes";
        reference " 0.12.39.";
    }

    revision "2025-02-14" {
        description "Setting the default value for action attribute in mac limit profile";
        reference " 0.12.38.";
    }

    revision "2025-02-11" {
        description "Added skip-dependency-validation flag in when tag inside vpls-peer objectlist";
        reference " 0.12.35.";
    }

    revision "2025-02-05" {
        description "Changing the route-map keyword to vpls-route-map";
        reference " 0.12.34.";
    }

    revision "2025-02-04" {
        description "Updated the helpstring for VPLS AC and Spoke mac limit profile";
        reference " 0.12.33.";
    }

    revision "2025-02-03" {
        description "Removed CML_RESET_INSTANCE flag from secondary pseudowire attribute";
        reference " 0.12.32.";
    }

    revision "2025-01-16" {
        description "Updated the helpstring for ospf for redistributed routes";
        reference " 0.12.31.";
    }

    revision "2025-01-08" {
        description "Changed H-VPLS secondary pseudowire to include CML_RESET_INSTANCE flag";
        reference " 0.12.30.";
    }

    revision "2025-01-07" {
        description "Removed include input for unset tag for peer-type attribute";
        reference " 0.12.29.";
    }

    revision "2025-01-03" {
        description "Added pattern check for static-mac-address attribute";
        reference " 0.12.28.";
    }

    revision "2024-12-24" {
        description "VPLS Mac limit support";
        reference " 0.12.27.";
    }

    revision "2024-12-04" {
        description "Remove mac-withdrawal dependency on disable-mac-withdrawal";
        reference " 0.12.26.";
    }

    revision "2024-11-30" {
        description "VPLS mac move support";
        reference " 0.12.25.";
    }

    revision "2024-11-21" {
        description "Add mac-withdrawal attribute";
        reference " 0.12.24.";
    }

    revision "2024-11-18" {
        description "Added BGP auto-discovery dependency on BGP instance";
        reference " 0.12.23.";
    }

    revision "2024-11-15" {
        description "Updated value of datatype BGP_VERSION_T";
        reference " 0.12.22.";
    }

    revision "2024-11-13" {
        description "Introduced new bgp debug option 'debug bgp peer'";
        reference " 0.12.21.";
    }

    revision "2024-11-11" {
        description "Introduced  new bgp debug options 'debug bgp route-process' and 'debug bgp evpn'  ";
        reference " 0.12.20.";
    }

    revision "2024-11-07" {
        description "Added dependency for container ldp-sig-bgp-autodiscovery on HAVE_BGP_VPLS";
        reference " 0.12.19.";
    }

    revision "2024-10-29" {
        description "Add subtypes for global mtu configuration";
        reference " 0.12.18.";
    }

    revision "2024-10-18" {
        description "Added route-map CLI for supporting SR-ODN for L2VPN-VPLS";
        reference " 0.12.16.";
    }

    revision "2024-10-17" {
        description "Added missing interface types for IF_HW_TYPE_T";
        reference " 0.12.17.";
    }

    revision "2024-10-03" {
        description "Added support to 400G and 200G in interface negotiated-port-speed";
        reference " 0.12.15.";
    }

    revision "2024-09-27" {
        description "Added new attribute for MLAG switch";
        reference " 0.12.14.";
    }

    revision "2024-09-20" {
        description "Hide manual FEC129 configuration CLIs";
        reference " 0.12.13.";
    }

    revision "2024-09-19" {
        description "Modified cli helpstring for mac ageing mode";
        reference " 0.12.12.";
    }

    revision "2024-09-13" {
        description "Removed the config dependency from ac-grp";
        reference " 0.12.11.";
    }

    revision "2024-09-11" {
        description "Fix BGP address-family CLI helpstrings";
        reference " 0.12.10.";
    }

    revision "2024-09-06" {
        description "Added BGP auto-discovery support under ldp signaling";
        reference " 0.12.9.";
    }

    revision "2024-09-03" {
        description "CL108 FEC config support";
        reference " 0.12.8.";
    }

    revision "2024-08-21" {
        description "Added CML_MAC_AGEING_T ";
        reference " 0.12.7.";
    }

    revision "2024-08-19" {
        description "Added global mtu configuration support";
        reference " 0.12.6.";
    }

    revision "2024-08-12" {
        description "Added global l2protocol configuration";
        reference " 0.12.5.";
    }

    revision "2024-07-26" {
        description "Make previous revision tag consistent";
        reference " 0.12.4.";
    }

    revision "2024-07-25" {
        description "Added UCMP CLI option";
        reference " 0.12.3.";
    }

    revision "2024-06-18" {
        description "Added BVI element in hardware type datatype";
        reference " 0.12.2.";
    }

    revision "2024-05-24" {
        description "Removing restriction for split-horizon commands for DNX";
        reference " 0.12.1.";
    }

    revision "2024-05-06" {
        description "Added new attribute peer-vpls-type for sget of vpls type signaling";
        reference " 0.12.0.";
    }

    revision "2024-03-27" {
        description "Added limited autonegotiation support";
        reference " 0.11.10.";
    }

    revision "2024-03-05" {
        description "Remove default from mac-learning-limit";
        reference " 0.11.9.";
    }

    revision "2024-02-20" {
        description "Remove spoke type";
        reference " 0.11.8.";
    }

    revision "2024-01-29" {
        description "Revert masking of service template commands for Marvell platform";
        reference " 0.11.7.";
    }

    revision "2024-01-25" {
        description "Change Spoke Cli and added new split-horizon attribute";
        reference " 0.11.6.";
    }

    revision "2024-01-24" {
        description "Remove implicit delete from interface service template";
        reference " 0.11.5.";
    }

    revision "2024-01-15" {
        description "Mask service template commands for Marvell platform";
        reference " 0.11.4.";
    }

    revision "2024-01-06" {
        description "Added storm-control errdisable";
        reference " 0.11.3.";
    }

    revision "2023-12-27" {
        description "VPLS redundancy";
        reference " 0.11.2.";
    }

    revision "2023-12-20" {
        description "Added a new datatype IF_RAON_AODU_STATE";
        reference " 0.11.1.";
    }

    revision "2023-11-15" {
        description "VPLS AC treatment";
        reference " 0.11.0.";
    }

    revision "2023-10-27" {
        description "CLI support for vpls type signaling per peer";
        reference " 0.11.1.";
    }

    revision "2023-10-10" {
        description "Change storm-control maximum level to 99%";
        reference " 0.10.8.";
    }

    revision "2023-10-05" {
        description "Adding skip-delete for one of encap when expression";
        reference " 0.10.7.";
    }

    revision "2023-08-23" {
        description "Added datatype IF_ACLIF_TYPE_T";
        reference " 0.10.6.";
    }

    revision "2023-08-18" {
        description "Added pattern tag for the datatype IF_SUBIF_OUTER_TPID_T";
        reference " 0.10.5.";
    }

    revision "2023-08-07" {
        description "Increasing the vpls-edge-identifier to max 65535 value";
        reference " 0.10.3.";
    }

    revision "2023-08-03" {
        description "Change when for spoke VC to check for manual-pseudowire";
        reference " 0.10.4.";
    }

    revision "2023-06-26" {
        description "When tag Error in ncs sync list vpls-peer";
        reference " 0.10.2.";
    }

    revision "2023-05-26" {
        description "Added element types for FEC type configuration support";
        reference " 0.10.1.";
    }

    revision "2023-05-05" {
        description "Added vpls-peers count in MPLS VPLS global counters";
        reference " 0.9.8.";
    }

    revision "2023-05-04" {
        description "updated the length of the vpls-name to 1-128";
        reference " 0.10.0.";
    }

    revision "2023-05-02" {
        description "Removed HARDWARE_PORT_MODE data type";
        reference " 0.9.7.";
    }

    revision "2023-04-29" {
        description "Help string of OUT-INTF in vpls-static-forwarding-config is modified";
        reference " 0.9.6.";
    }

    revision "2023-04-25" {
        description "Added if-feature flag in import module";
        reference " 0.9.5.";
    }

    revision "2023-04-10" {
        description "Added new CLI option interface-param-tlv for fat in MPLS-VPLS Data Model";
        reference " 0.9.4.";
    }

    revision "2023-03-23" {
        description "Limiting the vpls-edge-identifier to max 64 value";
        reference " 0.9.3.";
    }

    revision "2023-03-20" {
        description "Cli-error formating update is called instead of create";
        reference " 0.9.2.";
    }

    revision "2023-03-03" {
        description "Updated split-horizon datatype name";
        reference " 0.8.3.";
    }

    revision "2023-02-21" {
        description "Enclosed all config object lists with container for L2VPN Data Model";
        reference " 0.9.0.";
    }

    revision "2023-02-12" {
        description "Updated split-horizon with platform specific flags";
        reference " 0.8.2.";
    }

    revision "2023-02-06" {
        description "Enclosed all config object lists with container for MPLS Data Model";
        reference " 0.9.1.";
    }

    revision "2023-01-20" {
        description "Added helpstring for tunnel-select-policy";
        reference " 0.8.1.";
    }

    revision "2023-01-09" {
        description "Added Description to address the cmlgen warnings";
        reference " 0.8.0.";
    }

    revision "2023-01-05" {
        description "Removed cliFlag from control-word attribute";
        reference " 0.7.15.";
    }

    revision "2022-08-24" {
        description "Revert changes to fix pre-qat failures";
        reference " 0.7.14.";
    }

    revision "2022-08-18" {
        description "Added proper help string for VPLS MTU";
        reference " 0.7.13.";
    }

    revision "2022-08-16" {
        description "Added vpls split-horizon support";
        reference " 0.7.12.";
    }

    revision "2022-07-18" {
        description "Added proper xpath for enable-flow-label attribute in yaml file";
        reference " 0.7.11.";
    }

    revision "2022-07-16" {
        description "Global yang model name is changed as Global TE yang model";
        reference " 0.7.10.";
    }

    revision "2022-07-11" {
        description "Updated the subinterface encapsulation dependencies correctly";
        reference " 0.7.8.";
    }

    revision "2022-07-10" {
        description "Added configure_dependency tag for 'attachment-circuit-group-name'";
        reference " 0.7.7.";
    }

    revision "2022-07-07" {
        description "Fix for MPLS debug deletion";
        reference " 0.7.6.";
    }

    revision "2022-07-01" {
        description "Added pattern check for bandwidth related commands in MPLS yang model";
        reference " 0.7.5.";
    }

    revision "2022-06-28" {
        description "Fix attachment circuit remotion";
        reference " 0.7.4.";
    }

    revision "2022-06-21" {
        description "Changes in the MPLS yang model w.r.t to admin-groups";
        reference " 0.7.3.";
    }

    revision "2022-06-01" {
        description "Updated the yang file with feature";
        reference " 0.7.2.";
    }

    revision "2022-04-04" {
        description "Added if-feature whereever needed";
        reference " 0.7.1.";
    }

    revision "2022-03-21" {
        description "Added flow label attributes for VPLS virtual circuit.";
        reference " 0.7.0.";
    }

    revision "2022-01-20" {
        description "Updated RDN for ro objectlist network-interface-counters";
        reference " 0.6.4.";
    }

    revision "2021-12-30" {
        description "Updated length constraint for tunnel-name";
        reference " 0.6.3.";
    }

    revision "2021-12-28" {
        description "Added when constraints for vpls-peer tunnel-identifier,tunnel-name and tunnel-policy";
        reference " 0.6.2.";
    }

    revision "2021-12-20" {
        description "Updated datatype and range for tunnel-identifier";
        reference " 0.6.1.";
    }

    revision "2021-12-15" {
        description "Added VPLS counters related operational attributes";
        reference " 0.6.0.";
    }

    revision "2021-11-30" {
        description "Updated dependency condition for signaling-ldp on vpls-peer";
        reference " 0.5.1.";
    }

    revision "2021-11-16" {
        description "Adding L2CP support";
        reference " 0.5.0.";
    }

    revision "2021-09-06" {
        description "Removed the dependency of L2VPN VPLS configuration in subinterface with global L2VPN VPLS configurataion";
        reference " 0.4.0.";
    }

    revision "2021-08-03" {
        description "Added L2VPN VPLS attributes for Sub-interface";
        reference " 0.3.0.";
    }

    revision "2021-03-08" {
        description "Added Read-only attributes for vpls info, mac-addresses learnt, vpls-peer and statistics info";
        reference " 0.2.0.";
    }

    revision "2020-11-30" {
        description "Initial Version";
        reference " 0.1.0.";
    }

    grouping vpls-service-template-mapping-top {
        description
            "Top level Grouping for service template mapping to VPLS on AC
                        interface";
        container service-template-mappings {
            description
                "Container for Service Templates mappings to VPLS on an interface";

            list service-template-mapping {
                key "interface-name vpls-name service-template-name";
                description
                    "Configuration data for Service Template mapping to VPLS on an
                                interface";
                leaf interface-name  {
                    type  leafref {
                        path  "../config/interface-name";
                    }
                    description "This attribute specifies the attachment circuit interface to which the
                                service template is applied";
                } // END of interface-name definition.

                leaf vpls-name  {
                    type  leafref {
                        path  "../config/vpls-name";
                    }
                    description "Specify VPLS instance name";
                } // END of vpls-name definition.

                leaf service-template-name  {
                    type  leafref {
                        path  "../config/service-template-name";
                    }
                    description "Specify Customer service template name to bind to this Attachment
                                circuit";
                } // END of service-template-name definition.

                container config {
                    description
                        "Configuration data for Attachment-Circuit";
                    uses vpls-service-template-mapping-config;
                } // END of config-container definition.
                container state {
                    config false;
                    description
                        "Operation state data for Attachment-Circuit";
                    uses vpls-service-template-mapping-config;
                } // END of state-container definition.
                uses virtual-circuit-quality-of-service-top;
            } // End of service-template-mapping-list
        } // END of service-template-mappings-container definition.
    } // END of vpls-service-template-mapping-top definition.
    grouping vpls-service-template-mapping-config {
        description
            "Grouping for VPLS Attachment-Circuit configuration";
        leaf interface-name  {
            type  leafref {
                path  "/ipi-interface:interfaces/ipi-interface:interface/ipi-interface:name";
            }
            description "This attribute specifies the attachment circuit interface to which the
                        service template is applied";
        } // END of interface-name definition.

        leaf service-template-name  {
            type  leafref {
                path  "/ipi-mpls:mpls/ipi-mpls:l2vpn/ipi-mpls:customer-service-templates/ipi-mpls:customer-service-template/ipi-mpls:config/ipi-mpls:name";
            }
            description "Specify Customer service template name to bind to this Attachment
                        circuit";
        } // END of service-template-name definition.

        leaf vpls-name  {
            type  string {
                length "1..1965";
                pattern "[^?' =,>|]+";
            }
            description "Specify VPLS instance name";
        } // END of vpls-name definition.

        leaf admin-status  {
            type  ipi-vpls-types:vpls_ac_admin_status_t;
            description "Specify admin status for VPLS AC";
        } // END of admin-status definition.

        leaf attachment-circuit-description  {
            type  cml-data-types:cml_line_t {
                length "1..1965";
            }
            description "Specify description of VPLS AC";
        } // END of attachment-circuit-description definition.

        leaf mac-learning  {
            type  ipi-vpls-types:vpls_mac_learning_t;
            description "Specify mac-learning for VPLS AC";
        } // END of mac-learning definition.

        leaf split-horizon  {
            if-feature feature-list:HAVE_CUSTOM2_MPLS;
            type  ipi-if-types:if_split_horizon_t;
            description "Specify split-horizon for VPLS";
        } // END of split-horizon definition.

        leaf allow-layer2-bridge-pdu  {
            if-feature feature-list:HAVE_CUSTOM1_MPLS;
            type  empty;
            description "Specify allowed L2 control packets in peer-mode";
        } // END of allow-layer2-bridge-pdu definition.

        leaf-list static-mac-address  {
            type  cml-data-types:cml_mac_addr_t {
                length "1..1965";
                pattern "[0-9a-fA-F]{4}.[0-9a-fA-F]{4}.[0-9a-fA-F]{4}";
            }
            description "Specify static-mac to be added on AC";
        } // END of static-mac-address definition.

    } // END of vpls-service-template-mapping-config definition.
    grouping virtual-circuit-quality-of-service-top {
        description
            "Top level grouping for VPLS QOS Profile on AC";
        container quality-of-service-profiles {
            description
                "Container for VPLS QOS profiles on AC";

            list quality-of-service-profile {
            when " /ipi-qos:qos/ipi-qos:global/ipi-qos:map-profile/ipi-qos:cos-to-queue-profiles/ipi-qos:cos-to-queue-profile/ipi-qos:name or /ipi-qos:qos/ipi-qos:global/ipi-qos:map-profile/ipi-qos:queue-color-to-cos-profiles/ipi-qos:queue-color-to-cos-profile/ipi-qos:name ";
                if-feature feature-list:HAVE_QOS;
                key "profile-type profile-name";
                description
                    "Configuration for VPLS QOS profile on AC";
                leaf profile-type  {
                    type  leafref {
                        path  "../config/profile-type";
                    }
                    description "Specify map profile type for VPLS";
                } // END of profile-type definition.

                leaf profile-name  {
                    type  leafref {
                        path  "../config/profile-name";
                    }
                    description "Specify profile name for map profile";
                } // END of profile-name definition.

                container config {
                    description
                        "Configuration data for Attachment-Circuit";
                    uses vpls-quality-of-service-config;
                } // END of config-container definition.
                container state {
                    config false;
                    description
                        "Operation state data for Attachment-Circuit";
                    uses vpls-quality-of-service-config;
                } // END of state-container definition.
            } // End of quality-of-service-profile-list
        } // END of quality-of-service-profiles-container definition.
    } // END of virtual-circuit-quality-of-service-top definition.
    grouping vpls-quality-of-service-config {
        description
            "Grouping for       VPLS QOS Profile Configuration attributes";
        leaf profile-type  {
            type  ipi-vpls-types:vpls_qos_map_profile_type_t;
            description "Specify map profile type for VPLS";
        } // END of profile-type definition.

        leaf profile-name  {
            type  string {
                length "1..1965";
                pattern "[^?' =,>|]+";
            }
            description "Specify profile name for map profile";
        } // END of profile-name definition.

    } // END of vpls-quality-of-service-config definition.
    grouping vpls-mac-learning-table-state {
        description
            "Top level grouping for Mac Learning table";
        leaf mac-address  {
            type  cml-data-types:cml_mac_addr_t {
                length "1..1965";
            }
            description "Attribute to acquire mac-address learnt on VPLS instance";
        } // END of mac-address definition.

        leaf vpls-identifier  {
            type  uint32;
            description "Attribute to acquire vpls-id for a VPLS instance";
        } // END of vpls-identifier definition.

        leaf learning-source-interface  {
            type  string {
                length "1..1965";
                pattern "[^?' =,>|]+";
            }
            description "Attribute to acquire interface name from where mac-address is learnt
                        on VPLS instance";
        } // END of learning-source-interface definition.

        leaf matched-vlan  {
            type  uint16;
            description "Attribute to acquire matched vlan value for the mac-address learnt";
        } // END of matched-vlan definition.

        leaf peer-address  {
            type  inet:ipv4-address;
            description "Attribute to acquire mesh peer address from whom mac-address is learnt";
        } // END of peer-address definition.

        leaf ageing-timeout  {
            type  uint32;
            units "seconds";
            description "Attribute to acquire ageing timeout for the learnt mac-address in VPLS
                        instance";
        } // END of ageing-timeout definition.

    } // END of vpls-mac-learning-table-state definition.
    grouping vpls-mac-learning-table-top {
        description
            "Top level grouping for Mac Learning table";

        list mac-learning-table {
            key "mac-address";
            config false;
            description
                "List of Mac Learning Table";
            leaf mac-address  {
                type  leafref {
                    path  "../state/mac-address";
                }
                description "Attribute to acquire mac-address learnt on VPLS instance";
            } // END of mac-address definition.

            container state {
                config false;
                description
                    "Operational state data";
                uses vpls-mac-learning-table-state;
            } // END of state-container definition.
        } // End of mac-learning-table-list
    } // END of vpls-mac-learning-table-top definition.
    grouping vpls-peer-list-state {
        description
            "Top level grouping for Operational Peer list";
        leaf peer-address  {
            type  inet:ipv4-address;
            description "Attribute to acquire destination peer address of a VPLS pseudowire";
        } // END of peer-address definition.

        leaf vpls-identifier  {
            type  uint32;
            description "Attribute to acquire vpls-id for a VPLS instance";
        } // END of vpls-identifier definition.

        leaf route-distinguisher  {
            type  string {
                length "1..1965";
                pattern "[^?' =,>|]+";
            }
            description "This attribute acquires the RD value if signaling-protocol is BGP";
        } // END of route-distinguisher definition.

        leaf vpls-edge-id  {
            type  uint32;
            description "This attribute acquires ve-id value if signaling-protocol is BGP";
        } // END of vpls-edge-id definition.

        leaf maximum-transmission-unit  {
            type  uint16;
            description "Set the Maximum Transmission Unit (MTU) size for a given VPLS
                        instance. This size is signaled to peer  VPLS routers";
        } // END of maximum-transmission-unit definition.

        leaf tunnel-label  {
            type  uint32;
            description "Attribute to acquire tunnel-label to be used for VPLS pseudowire";
        } // END of tunnel-label definition.

        leaf pseudowire-in-label  {
            type  uint32;
            description "Attribute to acquire incoming VC label for VPLS pseudowire";
        } // END of pseudowire-in-label definition.

        leaf pseudowire-out-label  {
            type  uint32;
            description "Attribute to acquire outgoing VC label for VPLS pseudowire";
        } // END of pseudowire-out-label definition.

        leaf peer-state  {
            type  ipi-vpls-types:vpls_peer_state_t;
            description "Attribute to acquire state of mesh peer pseudowire";
        } // END of peer-state definition.

        leaf up-time  {
            type  cml-data-types:cml_line_t {
                length "1..1965";
            }
            description "Attribute to acquire uptime of mesh peer pseudowire";
        } // END of up-time definition.

        leaf pseudowire-status  {
            type  ipi-vpls-types:vpls_pseudowire_status_t;
            description "Attribute to acquire pseudowire status of a VPLS instance";
        } // END of pseudowire-status definition.

        leaf peer-vpls-type  {
            type  ipi-vpls-types:vpls_vc_type_t;
            description "This attribute acquires Peer VPLS type as ethernet or vlan";
        } // END of peer-vpls-type definition.

        leaf network-interface  {
            type  string {
                length "1..1965";
                pattern "[^?' =,>|]+";
            }
            description "Attribute to acquire the network interface name using which
                        mesh-pseudowire is created";
        } // END of network-interface definition.

        leaf signaling-protocol  {
            type  ipi-vpls-types:vpls_signaling_type_t;
            default "NA";
            description "Attribute to acquire the signaling protocol used for establishment of
                        vpls pseudowire";
        } // END of signaling-protocol definition.

    } // END of vpls-peer-list-state definition.
    grouping vpls-peer-list-top {
        description
            "Top level grouping for Operational Peer list";

        list peer-list {
            key "peer-address";
            config false;
            description
                "Peer list";
            leaf peer-address  {
                type  leafref {
                    path  "../state/peer-address";
                }
                description "Attribute to configure address of peer";
            } // END of peer-address definition.

            container state {
                config false;
                description
                    "Operational state data";
                uses vpls-peer-list-state;
            } // END of state-container definition.
        } // End of peer-list-list
    } // END of vpls-peer-list-top definition.
    grouping vpls-quality-of-service-top {
        description
            "Top level grouping for VPLS QOS Profile on AC";
        container quality-of-service-profiles {
            description
                "Enclosing container for VPLS QOS profiles on AC";

            list quality-of-service-profile {
            when " /ipi-qos:qos/ipi-qos:global/ipi-qos:map-profile/ipi-qos:cos-to-queue-profiles/ipi-qos:cos-to-queue-profile/ipi-qos:name or /ipi-qos:qos/ipi-qos:global/ipi-qos:map-profile/ipi-qos:queue-color-to-cos-profiles/ipi-qos:queue-color-to-cos-profile/ipi-qos:name ";
                if-feature feature-list:HAVE_QOS;
                key "profile-type profile-name";
                description
                    "Configuration VPLS QOS profile on AC";
                leaf profile-type  {
                    type  leafref {
                        path  "../config/profile-type";
                    }
                    description "Specify map profile type for VPLS";
                } // END of profile-type definition.

                leaf profile-name  {
                    type  leafref {
                        path  "../config/profile-name";
                    }
                    description "Specify profile name";
                } // END of profile-name definition.

                container config {
                    description
                        "Configuration data for Attachment-Circuit";
                    uses vpls-quality-of-service-config;
                } // END of config-container definition.
                container state {
                    config false;
                    description
                        "Operation state data for Attachment-Circuit";
                    uses vpls-quality-of-service-config;
                } // END of state-container definition.
            } // End of quality-of-service-profile-list
        } // END of quality-of-service-profiles-container definition.
    } // END of vpls-quality-of-service-top definition.
    grouping vpls-mac-limit-profiles-top {
        description
            "Top level grouping for mac limit profile";
        container mac-limit-profiles {
            description
                "Top level container for vpls mac move instance";

            list mac-limit-profile {
                if-feature feature-list:HAVE_VPLS;
                key "profile-name";
                description
                    "List for Mac limit profile";
                leaf profile-name  {
                    type  leafref {
                        path  "../config/profile-name";
                    }
                    description "VPLS instance mac limit config";
                } // END of profile-name definition.

                container config {
                    description
                        "Mac limit VPLS profile config";
                    uses vpls-mac-limit-profile-config;
                } // END of config-container definition.
                container state {
                    config false;
                    description
                        "Operation state data for Mac limit profile VPLS";
                    uses vpls-mac-limit-profile-config;
                } // END of state-container definition.
            } // End of mac-limit-profile-list
        } // END of mac-limit-profiles-container definition.
    } // END of vpls-mac-limit-profiles-top definition.
    grouping vpls-mac-limit-profile-config {
        description
            "Grouping for global vpls peer configuration attributes";
        leaf profile-name  {
            type  string {
                length "1..1965";
                pattern "[^?' =,>|]+";
            }
            description "VPLS instance mac limit config";
        } // END of profile-name definition.

        leaf learning-limit  {
            type  uint16 {
                 range "1..32767"  {
                    description "1..32767: Supported range 1 - 32767";
                 }
            }
            default "32767";
            description "No of mac limit supported";
        } // END of learning-limit definition.

        leaf action  {
            type  ipi-vpls-types:vpls_mpls_mac_limit_action_t;
            default "log-only";
            description "Mac limit action";
        } // END of action definition.

        leaf high-watermark  {
            type  uint16 {
                 range "1..100"  {
                    description "1..100: Supported range 1 - 100";
                 }
            }
            default "90";
            description "High watermark for logging";
        } // END of high-watermark definition.

        leaf low-watermark  {
            type  uint16 {
                 range "1..100"  {
                    description "1..100: Supported range 1 - 100";
                 }
            }
            default "70";
            description "Low watermark for logging";
        } // END of low-watermark definition.

        leaf errdisable-timeout-interval  {
            // when " ipi-l2vpn-vpls:vpls/mac-limit-profiles/mac-limit-profile/config/action == '2' ";
            type  uint32 {
                 range "0..86400"  {
                    description "0..86400: Supported range 0 - 86400";
                 }
            }
            default "0";
            description "Error disable timeout interval";
        } // END of errdisable-timeout-interval definition.

    } // END of vpls-mac-limit-profile-config definition.
    grouping vpls-static-vpls-top {
        description
            "Top level Grouping for Static Forwarding for VPLS";
        container vpls-entries {
            description
                "Enclosing container for Static VPLS Forwarding Information Base
                        entries";

            list vpls-entry {
            when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type = 'manual' ";
                key "vpls-identifier peer-address";
                description
                    "List for Static VPLS Forwarding Information Base";
                leaf vpls-identifier  {
                    type  leafref {
                        path  "../config/vpls-identifier";
                    }
                    description "VPLS Instance Identifier for static VPLS signaling";
                } // END of vpls-identifier definition.

                leaf peer-address  {
                    type  leafref {
                        path  "../config/peer-address";
                    }
                    description "Specify VPLS peer IPv4 address";
                } // END of peer-address definition.

                container config {
                    description
                        "Configuration data for Static VPLS";
                    uses vpls-static-forwarding-keys-config;
                    uses vpls-static-forwarding-config;
                } // END of config-container definition.
                container state {
                    config false;
                    description
                        "Operation state data for Static VPLS";
                    uses vpls-static-forwarding-keys-config;
                    uses vpls-static-forwarding-config;
                } // END of state-container definition.
            } // End of vpls-entry-list
        } // END of vpls-entries-container definition.
    } // END of vpls-static-vpls-top definition.
    grouping vpls-static-hvpls-top {
        description
            "Top level Grouping for Static Forwarding for HVPLS";
        container hierarchical-vpls-entries {
            description
                "Enclosing container for static forwarding for HVPLS entries";

            list hierarchical-vpls-entry {
            when " /ipi-network-instance:network-instances/ipi-network-instance:network-instance/ipi-l2vpn-vpws:vpws-instance/ipi-l2vpn-vpws:pseudowires/ipi-l2vpn-vpws:pseudowire/ipi-l2vpn-vpws:default-tagged/ipi-l2vpn-vpws:config/ipi-l2vpn-vpws:enable-manual-pseudowire ";
                key "vpls-identifier spoke-pseudowire-name";
                description
                    "List for Configuration data of Static Forwarding for HVPLS";
                leaf vpls-identifier  {
                    type  leafref {
                        path  "../config/vpls-identifier";
                    }
                    description "Specify VPLS identifier";
                } // END of vpls-identifier definition.

                leaf spoke-pseudowire-name  {
                    type  leafref {
                        path  "../config/spoke-pseudowire-name";
                    }
                    description "Specify spoke virtual circuit name";
                } // END of spoke-pseudowire-name definition.

                container config {
                    description
                        "Configuration data for Static HVPLS";
                    uses vpls-static-forwarding-hvpls-keys-config;
                    uses vpls-static-forwarding-config;
                } // END of config-container definition.
                container state {
                    config false;
                    description
                        "Operation state data for Static HVPLS";
                    uses vpls-static-forwarding-hvpls-keys-config;
                    uses vpls-static-forwarding-config;
                } // END of state-container definition.
            } // End of hierarchical-vpls-entry-list
        } // END of hierarchical-vpls-entries-container definition.
    } // END of vpls-static-hvpls-top definition.
    grouping vpls-static-forwarding-keys-config {
        description
            "Grouping for VPLS static forwarding configuration attributes";
        leaf vpls-identifier  {
            type  leafref {
                path  "/ipi-network-instance:network-instances/ipi-network-instance:network-instance/vpls-instance/config/vpls-identifier";
            }
            description "VPLS Instance Identifier for static VPLS signaling";
        } // END of vpls-identifier definition.

        leaf peer-address  {
            type  leafref {
                path  "/ipi-network-instance:network-instances/ipi-network-instance:network-instance/vpls-instance/vpls-peers/vpls-peer/config/peer-address";
            }
            description "Specify VPLS peer IPv4 address";
        } // END of peer-address definition.

    } // END of vpls-static-forwarding-keys-config definition.
    grouping vpls-static-forwarding-hvpls-keys-config {
        description
            "Grouping for VPLS static forwarding configuration attributes";
        leaf vpls-identifier  {
            type  leafref {
                path  "/ipi-network-instance:network-instances/ipi-network-instance:network-instance/vpls-instance/config/vpls-identifier";
            }
            description "Specify VPLS identifier";
        } // END of vpls-identifier definition.

        leaf spoke-pseudowire-name  {
            type  leafref {
                path  "/ipi-network-instance:network-instances/ipi-network-instance:network-instance/vpls-instance/spoke-pseudowires/spoke-pseudowire/config/pseudowire-name";
            }
            description "Specify spoke virtual circuit name";
        } // END of spoke-pseudowire-name definition.

    } // END of vpls-static-forwarding-hvpls-keys-config definition.
    grouping vpls-static-forwarding-config {
        description
            "Grouping for VPLS static forwarding configuration attributes";
        leaf in-label  {
            type  uint32 {
                 range "16..52443"  {
                    description "16..52443:Feature : HAVE_SR_MPLS Supported range 16 - 15999Not Feature
                            : HAVE_SR_MPLS  Supported range 16 - 52443";
                 }
            }
            mandatory true;
            description "Specify in-coming label for VPLS static forwarding";
        } // END of in-label definition.

        leaf out-label  {
            type  uint32 {
                 range "16..52443"  {
                    description "16..52443:Feature : HAVE_SR_MPLS Supported range 16 - 15999Not Feature
                            : HAVE_SR_MPLS  Supported range 16 - 52443";
                 }
            }
            mandatory true;
            description "Specify out going label for VPLS static forwarding";
        } // END of out-label definition.

        leaf out-interface-name  {
            type  string {
                length "1..1965";
                pattern "[^?' =,>|]+";
            }
            mandatory true;
            description "Specify provider facing interface name";
        } // END of out-interface-name definition.

    } // END of vpls-static-forwarding-config definition.
    grouping vpls-mac-move-top {
        description
            "Top level Grouping Mac Move in VPLS";
        container mac-move-global {
            description
                "Globacl Mac move container";
            container config {
                description
                    "Enclosing container for VPLS mac move configuration";
                uses vpls-mac-move-config;
            } // END of config-container definition.
            container state {
                config false;
                description
                    "Operation state data for VPLS mac move";
                uses vpls-mac-move-config;
            } // END of state-container definition.
        } // END of mac-move-global-container definition.
    } // END of vpls-mac-move-top definition.
    grouping vpls-mac-move-config {
        description
            "Top level Grouping Mac Move attributes in VPLS";
        leaf detect-time  {
            type  uint16 {
                 range "1..1000"  {
                    description "1..1000: Supported range 1 - 1000";
                 }
            }
            default "5";
            description "No of mac moves to flag violation";
        } // END of detect-time definition.

        leaf detect-interval  {
            type  uint16 {
                 range "5..300"  {
                    description "5..300: Supported range 5 - 300";
                 }
            }
            units "seconds";
            default "15";
            description "Mac move detection interval";
        } // END of detect-interval definition.

    } // END of vpls-mac-move-config definition.
    grouping vpls-instance-global-state {
        description
            "Grouping for VPLS Instance global runtime attributes";
        leaf signaling-protocol  {
            type  ipi-vpls-types:vpls_signaling_type_t;
            default "NA";
            description "This attribute acquires signaling protocol used to establish VPLS
                        service";
        } // END of signaling-protocol definition.

        leaf route-distinguisher  {
            type  string {
                length "1..1965";
                pattern "[^?' =,>|]+";
            }
            description "This attribute acquires the RD value if signaling-protocol is BGP";
        } // END of route-distinguisher definition.

        leaf route-target  {
            type  string {
                length "1..1965";
                pattern "[^?' =,>|]+";
            }
            description "This attribute acquires RT value if signaling-protocol is BGP";
        } // END of route-target definition.

        leaf vpls-edge-id  {
            type  uint32;
            description "This attribute acquires ve-id value if signaling-protocol is BGP";
        } // END of vpls-edge-id definition.

        leaf attachment-circuit-status  {
            type  ipi-vpls-types:vpls_ac_status_t;
            description "This attribute acquires AC status which is mapped to VPLS instance";
        } // END of attachment-circuit-status definition.

        leaf vpls-type  {
            type  ipi-vpls-types:vpls_vc_type_t;
            description "This attribute acquires VPLS type as ethernet or vlan";
        } // END of vpls-type definition.

        leaf service-vlan-id  {
            type  uint16;
            description "This attribute acquires service vlan identifier value";
        } // END of service-vlan-id definition.

        leaf group-identifier  {
            type  uint32;
            description "This attribute acquires group identifier for pseudowire";
        } // END of group-identifier definition.

        leaf total-mac-addresses-learnt  {
            type  uint32;
            description "This attribute acquires the total number of mac-addresses learnt by
                        this VPLS Instance";
        } // END of total-mac-addresses-learnt definition.

        leaf vc-id  {
            type  uint32;
            description "This attribute specify spoke vc-id";
        } // END of vc-id definition.

        leaf vc-name  {
            type  string {
                length "1..1965";
                pattern "[^?' =,>|]+";
            }
            description "This attribute specify spoke vc name";
        } // END of vc-name definition.

        leaf peer-address  {
            type  string {
                length "1..1965";
                pattern "[^?' =,>|]+";
            }
            description "This attribute specify spoke vc peer address";
        } // END of peer-address definition.

        leaf spoke-state  {
            type  ipi-vpls-types:vpls_peer_state_t;
            description "Attribute specify state of spoke VPLS";
        } // END of spoke-state definition.

    } // END of vpls-instance-global-state definition.
    grouping vpls-instance-global-config {
        description
            "Grouping for VPLS Instance global configuration  attributes";
        leaf vpls-identifier  {
            type  uint32 {
                 range "1..4294967295"  {
                    description "1..4294967295: Supported range 1 - 4294967295";
                 }
            }
            mandatory true;
            description "Specify VPLS identifier";
        } // END of vpls-identifier definition.

        leaf service-transport-identifier  {
            type  ipi-vpls-types:vpls_svc_tpid_t;
            description "Specify service transport identifier";
        } // END of service-transport-identifier definition.

        leaf route-map  {
            type  string {
                length "1..1965";
                pattern "[^?' =,>|]+";
            }
            description "Use this attribute to set route-map";
        } // END of route-map definition.

        leaf maximum-transmission-unit  {
            type  uint16 {
                 range "576..65535"  {
                    description "576..65535: Supported range 576 - 65535";
                 }
            }
            default "1500";
            description "Set the Maximum Transmission Unit (MTU) size for a given VPLS
                        instance. This size is signaled to peer VPLS routers";
        } // END of maximum-transmission-unit definition.

        leaf vpls-description  {
            type  cml-data-types:cml_line_t {
                length "1..64";
            }
            default "NULL";
            description "Specify a description for this VPLS instance";
        } // END of vpls-description definition.

        leaf control-word  {
            type  empty;
            description "Control Word for VPLS instance";
        } // END of control-word definition.

        leaf mac-learning-disable  {
            type  empty;
            description "Specify mac learning disable for VPLS instance";
        } // END of mac-learning-disable definition.

        leaf mac-learning-limit  {
            if-feature feature-list:NOT_HAVE_TRIDENT2;
            if-feature feature-list:NOT_HAVE_TRIDENT2PLUS;
            type  uint32 {
                 range "5..32767"  {
                    description "5..32767: Supported range 5 - 32767";
                 }
            }
            description "Specify mac learning limit";
        } // END of mac-learning-limit definition.

        leaf attachment-circuit-group-name  {
            type  leafref {
                path  "/ipi-mpls:mpls/ipi-mpls:l2vpn/ipi-mpls:access-circuit-groups/ipi-mpls:access-circuit-group/ipi-mpls:config/ipi-mpls:group-name";
            }
            description "Specify ac-group name";
        } // END of attachment-circuit-group-name definition.

        leaf mac-withdrawal  {
            type  ipi-vpls-types:vpls_mpls_mac_withdrawal_t;
            description "Specify mac address withdrawal type";
        } // END of mac-withdrawal definition.

        leaf mac-flush-send-on-mlag-switchover  {
            type  empty;
            description "Enable mac withdrawal mlag switch for MPLS VPLS";
        } // END of mac-flush-send-on-mlag-switchover definition.

    } // END of vpls-instance-global-config definition.
    grouping vpls-spoke-pseudowire-top {
        description
            "Top level grouping for H-VPLS spoke-pseudowire";
        container spoke-pseudowires {
            description
                "Enclosing container for Spoke Pseudowires list for H-VPLS";

            list spoke-pseudowire {
                key "pseudowire-name";
                unique "config/secondary-pseudowire-name";
                description
                    "Spoke Pseudowire list for H-VPLS";
                leaf pseudowire-name  {
                    type  leafref {
                        path  "../config/pseudowire-name";
                    }
                    description "Specify pseudowire name to be added";
                } // END of pseudowire-name definition.

                container config {
                    description
                        "Configuration data for spoke-pseudowire";
                    uses vpls-spoke-pseudowire-config;
                } // END of config-container definition.
                container state {
                    config false;
                    description
                        "Operation state data for spoke-pseudowire";
                    uses vpls-spoke-pseudowire-config;
                } // END of state-container definition.
            } // End of spoke-pseudowire-list
        } // END of spoke-pseudowires-container definition.
    } // END of vpls-spoke-pseudowire-top definition.
    grouping vpls-spoke-pseudowire-config {
        description
            "Grouping for H-VPLS spoke-pseudowire configuration attributes";
        leaf pseudowire-name  {
            type  string {
                length "1..255";
                pattern "[^?' =,>|]+";
            }
            description "Specify pseudowire name to be added";
        } // END of pseudowire-name definition.

        leaf secondary-pseudowire-name  {
            type  string {
                length "1..255";
                pattern "[^?' =,>|]+";
            }
            description "Specify secondary pseudowire name to be added";
        } // END of secondary-pseudowire-name definition.

        leaf learning-limit  {
            type  leafref {
                path  "/vpls/mac-limit-profiles/mac-limit-profile/config/profile-name";
            }
            description "Specify vc mac learning limit profile";
        } // END of learning-limit definition.

        leaf enable-revertive-mode  {
            type  empty;
            description "This attribute is used to configure vc-mode revertive for vpls spoke
                        vc";
        } // END of enable-revertive-mode definition.

        leaf revertive-timer  {
            // when " ../enable-revertive-mode ";
            type  uint16 {
                 range "0..3600"  {
                    description "0..3600: Supported range 0 - 3600";
                 }
            }
            description "This attribute is used to configure the vpls vc revertive timer.
                        Default value is 0";
        } // END of revertive-timer definition.

        leaf split-horizon  {
            if-feature feature-list:HAVE_CUSTOM2_MPLS;
            type  ipi-if-types:if_split_horizon_t;
            description "Specify split-horizon for VPLS";
        } // END of split-horizon definition.

    } // END of vpls-spoke-pseudowire-config definition.
    grouping vpls-mac-move-instance-top {
        description
            "Top level grouping for mac move instance";
        container vpls-mac-move-instance {
            description
                "Top level container for vpls mac move instance";
            container config {
                presence "Mac Move instance VPLS";
                description
                    "Mac Move VPLS Instance config";
                uses vpls-mac-move-instance-config;
            } // END of config-container definition.
            container state {
                config false;
                description
                    "Operation state data for VPLS mac move instance";
                uses vpls-mac-move-instance-config;
            } // END of state-container definition.
        } // END of vpls-mac-move-instance-container definition.
    } // END of vpls-mac-move-instance-top definition.
    grouping vpls-mac-move-instance-config {
        description
            "Grouping for global vpls peer configuration attributes";
        leaf mac-move-instance  {
            type  empty;
            mandatory true;
            description "VPLS instance mac move config";
        } // END of mac-move-instance definition.

        leaf detect-time  {
            type  uint16 {
                 range "1..1000"  {
                    description "1..1000: Supported range 1 - 1000";
                 }
            }
            default "5";
            description "No of mac moves to flag violation";
        } // END of detect-time definition.

        leaf detect-interval  {
            type  uint16 {
                 range "5..300"  {
                    description "5..300: Supported range 5 - 300";
                 }
            }
            units "seconds";
            default "15";
            description "Mac move detection interval";
        } // END of detect-interval definition.

        leaf errdisable-timeout-interval  {
            type  uint32 {
                 range "0..86400"  {
                    description "0..86400: Supported range 0 - 86400";
                 }
            }
            default "0";
            description "Error disable timeout interval";
        } // END of errdisable-timeout-interval definition.

        leaf errdisable-allow-mesh-blocking  {
            type  empty;
            description "Allow blocking for Mesh PW";
        } // END of errdisable-allow-mesh-blocking definition.

    } // END of vpls-mac-move-instance-config definition.
    grouping vpls-peer-top {
        description
            "Top level grouping for VPLS Peer";
        container vpls-peers {
            description
                "Top level container for vpls peer";

            list vpls-peer {
                key "peer-address";
                description
                    "Configuration data for VPLS peer";
                leaf peer-address  {
                    type  leafref {
                        path  "../config/peer-address";
                    }
                    description "Specify VPLS peer address";
                } // END of peer-address definition.

                container config {
                    description
                        "Configuration data for vpls peer";
                    uses vpls-peer-config;
                } // END of config-container definition.
                container state {
                    config false;
                    description
                        "Operation state data for vpls peer";
                    uses vpls-peer-config;
                } // END of state-container definition.
                uses vpls-peer-fec129-top;
            } // End of vpls-peer-list
            container config {
                presence "Enable Ldp signaling for VPLS";
                description
                    "Global Configuration data for vpls peers";
                uses vpls-global-peer-config;
            } // END of config-container definition.
            container state {
                config false;
                description
                    "Global Operation state data for vpls peers";
                uses vpls-global-peer-config;
            } // END of state-container definition.
        } // END of vpls-peers-container definition.
    } // END of vpls-peer-top definition.
    grouping vpls-global-peer-config {
        description
            "Grouping for global vpls peer configuration attributes";
        leaf signaling-protocol-ldp  {
            when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type != 'manual' ";
            type  empty;
            mandatory true;
            description "Specify protocol used for signaling is ldp";
        } // END of signaling-protocol-ldp definition.

        leaf disable-mac-withdrawal  {
            // when " ipi-l2vpn-vpls:vpls-instance/vpls-peers/config/signaling-protocol-ldp ";
            type  empty;
            description "Specify mac address withdrawal disable";
        } // END of disable-mac-withdrawal definition.

        leaf vpls-ac-treatment-type  {
            type  ipi-vpls-types:cml_nsm_vpls_ac_treat_type_t;
            description "Customaizations for access state treatment";
        } // END of vpls-ac-treatment-type definition.

        leaf vpls-encapsulation-type  {
            type  ipi-vpls-types:vpls_vc_type_t;
            description "Specify encapsulation type";
        } // END of vpls-encapsulation-type definition.

    } // END of vpls-global-peer-config definition.
    grouping vpls-peer-config {
        description
            "Grouping for vpls peer configuration attributes";
        leaf peer-address  {
            type  inet:ipv4-address;
            description "Specify VPLS peer address";
        } // END of peer-address definition.

        leaf tunnel-name  {
            // when " not(../tunnel-identifier) ";
            type  string {
                length "1..128";
                pattern "[^?' =,>|]+";
            }
            description "Specify tunnel name";
        } // END of tunnel-name definition.

        leaf tunnel-policy  {
            // when " not(../tunnel-identifier) + not(../tunnel-name) ";
            if-feature feature-list:HAVE_SERVICE_MAPPING;
            type  string {
                length "1..127";
                pattern "[^?' =,>|]+";
            }
            description "Specify tunnel selection policy name";
        } // END of tunnel-policy definition.

        leaf tunnel-identifier  {
            // when " not(../tunnel-name) ";
            type  uint32 {
                 range "1..5000"  {
                    description "1..5000: Supported range 1 - 5000";
                 }
            }
            description "Specify static tunnel identifier value";
        } // END of tunnel-identifier definition.

        leaf peer-type  {
            // when " not(/ipi-network-instance:network-instances/ipi-network-instance:network-instance/ipi-l2vpn-vpls:vpls-instance/ipi-l2vpn-vpls:vpls-peers/ipi-l2vpn-vpls:config/ipi-l2vpn-vpls:signaling-protocol-ldp) ";
            type  ipi-vpls-types:vpls_peer_type_t;
            default "manual";
            description "Specify that peer type is manual and  no signaling is used to set-up
                        the Virtual Circuit";
        } // END of peer-type definition.

        leaf vpls-type  {
            type  ipi-vpls-types:vpls_vc_type_t;
            description "Specify Peer VPLS Type";
        } // END of vpls-type definition.

    } // END of vpls-peer-config definition.
    grouping vpls-ldp-route-target-config {
        description
            "Configuration data for VPLS LDP route target";
        leaf rt-string  {
            type  ipi-bgp-types:bgp_vrf_rt_t {
                length "1..1965";
            }
            description "Use this attribute to assign route target (RT)";
        } // END of rt-string definition.

        leaf direction  {
            type  ipi-bgp-types:bgp_target_route_type_t;
            mandatory true;
            description "Use this attribute to add a list of import and export route-target
                        extended communities for the VPLS instance";
        } // END of direction definition.

    } // END of vpls-ldp-route-target-config definition.
    grouping vpls-ldp-route-target {
        description
            "Grouping for route target information";
        container route-targets {
            description
                "Top level container for Route target information";

            list route-target {
                key "rt-string";
                description
                    "Route target information";
                leaf rt-string  {
                    type  leafref {
                        path  "../config/rt-string";
                    }
                    description "Assigns Route Target";
                } // END of rt-string definition.

                container config {
                    description
                        "Configuration data for BGP route target";
                    uses vpls-ldp-route-target-config;
                } // END of config-container definition.
                container state {
                    config false;
                    description
                        "State parameters for BGP VRF route target";
                    uses vpls-ldp-route-target-config;
                } // END of state-container definition.
            } // End of route-target-list
        } // END of route-targets-container definition.
    } // END of vpls-ldp-route-target definition.
    grouping vpls-ldp-sig-bgp-autodiscovery-config {
        description
            "Grouping for VPLS LDP BGP-Autodiscovery configuration attributes";
        leaf rd-string  {
            type  string {
                length "1..32";
                pattern "[^?' =,>|]+";
            }
            description "Use this attribute to assign a route distinguisher (RD) for the VPLS
                        instance in ASN:nn or IP-address:nn format
                        RD must be unique across all VPLS instances";
        } // END of rd-string definition.

        leaf l2vpn-id  {
            type  string {
                length "1..32";
                pattern "[^?' =,>|]+";
            }
            description "Specify L2 VPN ID in ASN:nn or IP-address:nn format
                        L2 VPN ID must be unique across all VPLS instances";
        } // END of l2vpn-id definition.

        leaf bgp-auto-discovery  {
            type  empty;
            mandatory true;
            description "Enable BGP Auto-Discovery for LDP peers";
        } // END of bgp-auto-discovery definition.

    } // END of vpls-ldp-sig-bgp-autodiscovery-config definition.
    grouping vpls-ldp-sig-bgp-autodiscovery-top {
        description
            "Top level grouping for VPLS BGP Autodiscovery Config";
        container ldp-sig-bgp-autodiscovery {
            if-feature feature-list:HAVE_BGP_VPLS;
            description
                "Top level container for VPLS BGP Autodiscovery";
            container config {
                when " /ipi-network-instance:network-instances/ipi-network-instance:network-instance/ipi-l2vpn-vpls:vpls-instance/ipi-l2vpn-vpls:vpls-peers/ipi-l2vpn-vpls:config/ipi-l2vpn-vpls:signaling-protocol-ldp ";
                presence "Enable BGP AD";
                description
                    "Global Configuration data for VPLS BGP Autodiscovery";
                uses vpls-ldp-sig-bgp-autodiscovery-config;
            } // END of config-container definition.
            container state {
                config false;
                description
                    "Global Operation state data for VPLS BGP Autodiscovery";
                uses vpls-ldp-sig-bgp-autodiscovery-config;
            } // END of state-container definition.
            uses vpls-ldp-route-target;
        } // END of ldp-sig-bgp-autodiscovery-container definition.
    } // END of vpls-ldp-sig-bgp-autodiscovery-top definition.
    grouping vpls-fat-config {
        description
            "Grouping for vpls fat label configuration attributes";
        leaf enable-flow-label  {
            type  empty;
            mandatory true;
            description "Use this attribute to enable flow label for VPLS Virtual Circuits";
        } // END of enable-flow-label definition.

        leaf flow-label-direction  {
            // when " ../enable-flow-label ";
            type  ipi-vpls-types:vpls_mpls_flow_label_direction_t;
            description "Use this attribute to configure flow label direction to transmit,
                        receive or both for VPLS Virtual Circuits";
        } // END of flow-label-direction definition.

        leaf enable-static-flow-label  {
            // when " ../enable-flow-label ";
            type  empty;
            description "Use this attribute to configure static flow label for VPLS Virtual
                        Circuits.";
        } // END of enable-static-flow-label definition.

        leaf enable-interface-parameter-tlv  {
            // when " ../enable-flow-label ";
            type  empty;
            description "Use this attribute to configure interface parameter tlv for VPLS
                        Virtual Circuits.";
        } // END of enable-interface-parameter-tlv definition.

    } // END of vpls-fat-config definition.
    grouping vpls-fat-top {
        description
            "Grouping for fat label configuration attributes";
        container fat-label {
            description
                "Top level container for flow-label";
            container config {
                presence "Enable FAT Label";
                description
                    "Configuration data for fat label";
                uses vpls-fat-config;
            } // END of config-container definition.
            container state {
                config false;
                description
                    "Operation state data for fat label";
                uses vpls-fat-config;
            } // END of state-container definition.
        } // END of fat-label-container definition.
    } // END of vpls-fat-top definition.
    grouping vpls-peer-fec129-top {
        description
            "Top level grouping for Fec129 (Genfec) VPLS Peer";
        container fec129s {
            description
                "Enclosing container for VPLS genfec peers";

            list fec129 {
            when " /ipi-network-instance:network-instances/ipi-network-instance:network-instance/ipi-l2vpn-vpls:vpls-instance/ipi-l2vpn-vpls:vpls-peers/ipi-l2vpn-vpls:config/ipi-l2vpn-vpls:signaling-protocol-ldp ";
                key "attachment-group-identifier source-attachment-individual-identifier target-attachment-individual-identifier";
                max-elements 1;
                description
                    "Configuration data for VPLS genfec peer";
                leaf attachment-group-identifier  {
                    type  leafref {
                        path  "../config/attachment-group-identifier";
                    }
                    description "Specify the Address Group Identifier";
                } // END of attachment-group-identifier definition.

                leaf source-attachment-individual-identifier  {
                    type  leafref {
                        path  "../config/source-attachment-individual-identifier";
                    }
                    description "Specify the Source Attachment Individual Identifier";
                } // END of source-attachment-individual-identifier definition.

                leaf target-attachment-individual-identifier  {
                    type  leafref {
                        path  "../config/target-attachment-individual-identifier";
                    }
                    description "Specify the Target Attachment Individual Identifier";
                } // END of target-attachment-individual-identifier definition.

                container config {
                    description
                        "Configuration data for vpls peer";
                    uses vpls-peer-fec129-config;
                } // END of config-container definition.
                container state {
                    config false;
                    description
                        "Operation state data for vpls peer";
                    uses vpls-peer-fec129-config;
                } // END of state-container definition.
            } // End of fec129-list
        } // END of fec129s-container definition.
    } // END of vpls-peer-fec129-top definition.
    grouping vpls-peer-fec129-config {
        description
            "Configuration attributes for genfec based VPLS peer";
        leaf attachment-group-identifier  {
            type  string {
                length "1..1965";
                pattern "[^?' =,>|]+";
            }
            description "Specify the Address Group Identifier";
        } // END of attachment-group-identifier definition.

        leaf source-attachment-individual-identifier  {
            type  string {
                length "1..1965";
                pattern "[^?' =,>|]+";
            }
            description "Specify the Source Attachment Individual Identifier";
        } // END of source-attachment-individual-identifier definition.

        leaf target-attachment-individual-identifier  {
            type  string {
                length "1..1965";
                pattern "[^?' =,>|]+";
            }
            description "Specify the Target Attachment Individual Identifier";
        } // END of target-attachment-individual-identifier definition.

        leaf tunnel-name  {
            // when " not(/ipi-network-instance:network-instances/ipi-network-instance:network-instance/ipi-l2vpn-vpls:vpls-instance/ipi-l2vpn-vpls:vpls-peers/ipi-l2vpn-vpls:config/ipi-l2vpn-vpls:signaling-protocol-ldp) ";
            type  string {
                length "1..1965";
                pattern "[^?' =,>|]+";
            }
            description "Specify tunnel id value";
        } // END of tunnel-name definition.

        leaf tunnel-policy  {
            // when " not(/ipi-network-instance:network-instances/ipi-network-instance:network-instance/ipi-l2vpn-vpls:vpls-instance/ipi-l2vpn-vpls:vpls-peers/ipi-l2vpn-vpls:config/ipi-l2vpn-vpls:signaling-protocol-ldp) ";
            if-feature feature-list:HAVE_SERVICE_MAPPING;
            type  string {
                length "1..127";
                pattern "[^?' =,>|]+";
            }
            description "Specify tunnel selection policy name";
        } // END of tunnel-policy definition.

        leaf tunnel-identifier  {
            type  string {
                length "1..1965";
                pattern "[^?' =,>|]+";
            }
            description "Specify tunnel id value";
        } // END of tunnel-identifier definition.

    } // END of vpls-peer-fec129-config definition.
    grouping vpls-bgp-top {
        description
            "Top level grouping for BGP VPLS";
        container bgp-signaling {
            if-feature feature-list:HAVE_BGP_VPLS;
            description
                "Top level container for BGP vpls";
            container config {
                when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type != 'manual' ";
                // when " not(/ipi-network-instance:network-instances/ipi-network-instance:network-instance/ipi-l2vpn-vpls:vpls-instance/ipi-l2vpn-vpls:vpls-peers/ipi-l2vpn-vpls:config/ipi-l2vpn-vpls:signaling-protocol-ldp) ";
                presence "Enable BGP VPLS";
                description
                    "Configuration data for bgp vpls";
                uses vpls-bgp-config;
            } // END of config-container definition.
            container state {
                config false;
                description
                    "Operation state data for bgp vpls";
                uses vpls-bgp-config;
            } // END of state-container definition.
        } // END of bgp-signaling-container definition.
    } // END of vpls-bgp-top definition.
    grouping vpls-bgp-config {
        description
            "Grouping for BGP VPLS Configuration attributes";
        leaf signaling-protocol-bgp  {
            type  empty;
            mandatory true;
            description "Specify protocol used for signaling is bgp";
        } // END of signaling-protocol-bgp definition.

        leaf vpls-edge-identifier  {
            type  uint16 {
                 range "1..65535"  {
                    description "1..65535: Supported range 1 - 65535";
                 }
            }
            description "Specify VPLS edge identifier value";
        } // END of vpls-edge-identifier definition.

        leaf tunnel-policy  {
            if-feature feature-list:HAVE_SERVICE_MAPPING;
            type  string {
                length "1..127";
                pattern "[^?' =,>|]+";
            }
            description "Specify tunnel selection policy name";
        } // END of tunnel-policy definition.

    } // END of vpls-bgp-config definition.
    grouping vpls-access-interface-counters-state {
        description
            "Top level grouping for access-interface-counters";
        leaf interface-name  {
            type  leafref {
                path  "/ipi-interface:interfaces/ipi-interface:interface/ipi-interface:name";
            }
            description "Attribute to acquire access interface name";
        } // END of interface-name definition.

        leaf vpls-identifier  {
            type  uint32;
            description "Attribute to acquire vpls-id for a VPLS instance";
        } // END of vpls-identifier definition.

        leaf service-template-name  {
            type  string {
                length "1..1965";
                pattern "[^?' =,>|]+";
            }
            description "Attribute to acquire Customer Service Template name mapped to this
                        vpls AC interface";
        } // END of service-template-name definition.

        leaf in-packets  {
            type  uint64;
            description "Attribute to acquire number of received(Rx) packets on this AC
                        interface";
        } // END of in-packets definition.

        leaf in-bytes  {
            type  uint64;
            description "Attribute to acquire number of received(Rx) bytes on this AC interface";
        } // END of in-bytes definition.

        leaf out-packets  {
            type  uint64;
            description "Attribute to acquire number of sent(Tx) packets on this AC interface";
        } // END of out-packets definition.

        leaf out-bytes  {
            type  uint64;
            description "Attribute to acquire number of sent(Tx) bytes on this AC interface";
        } // END of out-bytes definition.

    } // END of vpls-access-interface-counters-state definition.
    grouping vpls-network-interface-counters-state {
        description
            "Top level grouping for network-interface-counters";
        leaf peer-address  {
            type  inet:ipv4-address;
            description "Attribute to acquire peer-address for VPLS instance";
        } // END of peer-address definition.

        leaf vpls-identifier  {
            type  uint32;
            description "Attribute to acquire vpls-id for a VPLS instance";
        } // END of vpls-identifier definition.

        leaf peer-state  {
            type  ipi-vpls-types:vpls_peer_state_t;
            description "Attribute to acquire vpls-id for a VPLS instance";
        } // END of peer-state definition.

        leaf interface-name  {
            type  leafref {
                path  "/ipi-interface:interfaces/ipi-interface:interface/ipi-interface:name";
            }
            description "Attribute to acquire network interface name";
        } // END of interface-name definition.

        leaf in-packets  {
            type  uint64;
            description "Attribute to acquire number of received(Rx) packets on this AC
                        interface";
        } // END of in-packets definition.

        leaf in-bytes  {
            type  uint64;
            description "Attribute to acquire number of received(Rx) bytes on this AC interface";
        } // END of in-bytes definition.

        leaf out-packets  {
            type  uint64;
            description "Attribute to acquire number of sent(Tx) packets on this AC interface";
        } // END of out-packets definition.

        leaf out-bytes  {
            type  uint64;
            description "Attribute to acquire number of sent(Tx) bytes on this AC interface";
        } // END of out-bytes definition.

    } // END of vpls-network-interface-counters-state definition.
    grouping vpls-counters-top {
        description
            "Top level grouping for Counters";

        list access-interface-counters {
            if-feature feature-list:HAVE_MPLS_STATS;
            key "interface-name";
            config false;
            description
                "Access Interface Counters";
            leaf interface-name  {
                type  leafref {
                    path  "../state/interface-name";
                }
                description "Name of the interface";
            } // END of interface-name definition.

            container state {
                config false;
                description
                    "Operational state data";
                uses vpls-access-interface-counters-state;
            } // END of state-container definition.
        } // End of access-interface-counters-list

        list network-interface-counters {
            if-feature feature-list:HAVE_MPLS_STATS;
            key "peer-address";
            config false;
            description
                "Network Interface Counters";
            leaf peer-address  {
                type  leafref {
                    path  "../state/peer-address";
                }
                description "Attribute to acquire peer-address for VPLS instance";
            } // END of peer-address definition.

            container state {
                config false;
                description
                    "Operational state data";
                uses vpls-network-interface-counters-state;
            } // END of state-container definition.
        } // End of network-interface-counters-list
    } // END of vpls-counters-top definition.
    grouping vpls-interface-config {
        description
            "Grouping for Interface config attribute";
        leaf name  {
            type  leafref {
                path  "/ipi-interface:interfaces/ipi-interface:interface/ipi-interface:name";
            }
            description "This attribute describes the interface on which attachment circuit is
                        to be created for  pseudowire.";
        } // END of name definition.

    } // END of vpls-interface-config definition.
    grouping vpls-interface-top {
        description
            "Top level grouping for interface level configuration for PW";
        container interfaces {
            description
                "Top level container for interface level configuration for VPLS";

            list interface {
                key "name";
                description
                    "VPLS interface related configuration";
                leaf name  {
                    type  leafref {
                        path  "../config/name";
                    }
                    description "This attribute describes the interface on which attachment circuit is
                                to be created for  pseudowire.";
                } // END of name definition.

                container config {
                    description
                        "Configuration container for interface list";
                    uses vpls-interface-config;
                } // END of config-container definition.
                container state {
                    config false;
                    description
                        "Operation container for interface list";
                    uses vpls-interface-config;
                } // END of state-container definition.
                uses l2vpn-vpls-top;
            } // End of interface-list
        } // END of interfaces-container definition.
    } // END of vpls-interface-top definition.
    grouping l2vpn-vpls-top {
        description
            "Top level grouping for L2VPN VPLS configuration";
        container vpls-access {
            if-feature feature-list:HAVE_SUBINTERFACE;
            description
                "Container for L2vpn Vpls data";
            container config {
                presence "yes";
                description
                    "Configuration data for L2VPN VPLS";
                uses l2vpn-vpls-config;
            } // END of config-container definition.
            container state {
                config false;
                description
                    "Operation state data for L2VPN VPLS";
                uses l2vpn-vpls-config;
            } // END of state-container definition.
        } // END of vpls-access-container definition.
    } // END of l2vpn-vpls-top definition.
    grouping l2vpn-vpls-config {
        description
            "Grouping for L2VPN VPLS variables for sub interfaces";
        leaf enable  {
            type  empty;
            mandatory true;
            description "This attribute is used to enable VPLS service on Subinterface";
        } // END of enable definition.

        leaf vpls-name  {
            type  string {
                length "1..128";
                pattern "[^?' =,>|]+";
            }
            description "This attribute uniquely identifies a VPLS service on Subinterface";
        } // END of vpls-name definition.

        leaf disable-mac-learning  {
            type  empty;
            description "Use this attribute to disable dynamic learning of MAC's";
        } // END of disable-mac-learning definition.

        leaf learning-limit  {
            type  leafref {
                path  "/vpls/mac-limit-profiles/mac-limit-profile/config/profile-name";
            }
            description "Specify AC mac learning limit profile";
        } // END of learning-limit definition.

        leaf-list static-mac-address  {
            type  cml-data-types:cml_mac_addr_t {
                length "1..1965";
            }
            description "Specify static-mac to be added on L2VPN VPLS";
        } // END of static-mac-address definition.

    } // END of l2vpn-vpls-config definition.
    grouping vpls-global-counters-state {
        description
            "Grouping for global counters for VPLS";
        leaf total-instances  {
            type  yang:counter32;
            description "This attribute acquires total VPLS instances";
        } // END of total-instances definition.

        leaf total-peers  {
            type  yang:counter32;
            description "This attribute acquires total VPLS peers";
        } // END of total-peers definition.

        leaf active-peer-instances  {
            type  yang:counter32;
            description "This attribute acquires total active VPLS peer instances";
        } // END of active-peer-instances definition.

        leaf inactive-peer-instances  {
            type  yang:counter32;
            description "This attribute acquires total non-active VPLS peer instances";
        } // END of inactive-peer-instances definition.

    } // END of vpls-global-counters-state definition.
    grouping vpls-global-top {
        description
            "Top level grouping for global VPLS attributes";
        container global {
            description
                "Top level container for global configuration for VPLS";
            container state {
                config false;
                description
                    "State container for operational attributes";
                container counters {
                    config false;
                    description
                        "Operational container for VPLS counters";
                    uses vpls-global-counters-state;
                } // END of counters-container definition.
            } // END of state-container definition.
        } // END of global-container definition.
    } // END of vpls-global-top definition.

    grouping  vpls-grouping {
    description
        "VPLS global level container";
    container vpls {
        if-feature feature-list:HAVE_VPLS;
        if-feature feature-list:HAVE_MPLS;
        description
            "VPLS global level container";
        container attachment-circuit {
            description
                "VPLS-Attachment Circuit container";
            uses vpls-service-template-mapping-top;
        } // END of attachment-circuit-container definition.
        container static-forwarding {
            description
                "Static VPLS Forwarding Information Base container";
            uses vpls-static-vpls-top;
            uses vpls-static-hvpls-top;
        } // END of static-forwarding-container definition.
        uses vpls-mac-move-top;
        uses vpls-mac-limit-profiles-top;
        uses vpls-interface-top;
        uses vpls-global-top;
    } // END of vpls-container definition.
    } // END of vpls-grouping definition.

    grouping  vpls-instance-grouping {
    description
        "Top level list for VPLS-Instance";
    container vpls-instance {
        if-feature feature-list:HAVE_VPLS;
        if-feature feature-list:HAVE_MPLS;
        description
            "Top level list for VPLS-Instance";
        container config {
            presence "Create VPLS Instance";
            description
                "Configuration data for VPLS-Instance";
            uses vpls-instance-global-config;
        } // END of config-container definition.
        container state {
            config false;
            description
                "Operation state data for VPLS-Instance";
            uses vpls-instance-global-config;
            uses vpls-instance-global-state;
        } // END of state-container definition.
        uses vpls-spoke-pseudowire-top;
        uses vpls-fat-top;
        uses vpls-peer-top;
        uses vpls-ldp-sig-bgp-autodiscovery-top;
        uses vpls-bgp-top;
        uses vpls-quality-of-service-top;
        uses vpls-mac-learning-table-top;
        uses vpls-mac-move-instance-top;
        uses vpls-peer-list-top;
        uses vpls-counters-top;
    } // END of vpls-instance-container definition.
    } // END of vpls-instance-grouping definition.

    uses vpls-grouping;
    augment /ipi-network-instance:network-instances/ipi-network-instance:network-instance {
    when " /ipi-network-instance:network-instances/ipi-network-instance:network-instance/ipi-network-instance:instance-type = 'vpls' ";
    // when " ipi-l2vpn-vpls:vpls-instance/config/vpls-identifier ";
        description
            "Top level list for VPLS-Instance";
        uses vpls-instance-grouping;
    }


    rpc clear-mpls-vpls-name-statistics-port-type {
        if-feature feature-list:HAVE_MPLS_STATS;
        if-feature feature-list:HAVE_VPLS;
        if-feature feature-list:HAVE_MPLS;
        description "Use this attribute to clear mpls vpls statistics by portType";
        input  {
            leaf port-type  {
                type ipi-vpls-types:vpls_port_type_t;
                mandatory true;
                description "Specify port type";
            }
            leaf port-circuit-name  {
                type string;
                mandatory true;
                description "Specify port circuit name";
            }
        }
    }

    rpc clear-mpls-vpls-name-statistics-network-port-peer {
        if-feature feature-list:HAVE_MPLS_STATS;
        if-feature feature-list:HAVE_VPLS;
        if-feature feature-list:HAVE_MPLS;
        description "Use this attribute to clear mpls vpls statistics by network portType";
        input  {
            leaf port-circuit-name  {
                type string;
                mandatory true;
                description "Specify port circuit name";
            }
            leaf vc-circuit-type  {
                type ipi-vpls-types:vpls_peer_address_type_t;
                mandatory true;
                description "Specify peer VC circuit name";
            }
        }
    }

    rpc clear-mpls-vpls-name-statistics-network-port-spoke {
        if-feature feature-list:HAVE_MPLS_STATS;
        if-feature feature-list:HAVE_VPLS;
        if-feature feature-list:HAVE_MPLS;
        description "Use this attribute to clear mpls vpls statistics by network portType";
        input  {
            leaf port-circuit-name  {
                type string;
                mandatory true;
                description "Specify port circuit name";
            }
            leaf vc-circuit-type  {
                type ipi-vpls-types:vpls_spoke_vc_type_t;
                mandatory true;
                description "Specify VC circuit name";
            }
        }
    }

    rpc clear-mpls-vpls-name-statistics-access-port {
        if-feature feature-list:HAVE_MPLS_STATS;
        if-feature feature-list:HAVE_VPLS;
        if-feature feature-list:HAVE_MPLS;
        description "Use this attribute to clear mpls l2-circuit statistics by access
                    portType";
        input  {
            leaf port-circuit-name  {
                type string;
                mandatory true;
                description "Specify port circuit name";
            }
            leaf vc-interface-name  {
                type string;
                mandatory true;
                description "Specify ingress VC interface name";
            }
            leaf vc-access-type  {
                type ipi-vpls-types:vpls_mpls_access_type_t;
                mandatory true;
                description "Specify VC access type";
            }
        }
    }

    rpc clear-mpls-vpls-name-statistics {
        if-feature feature-list:HAVE_VPLS;
        if-feature feature-list:HAVE_MPLS_STATS;
        if-feature feature-list:HAVE_MPLS;
        description "Use this attribute to clear vpls statistics";
        input  {
            leaf vpls-circuit-name  {
                type string;
                mandatory true;
                description "Specify VC circuit name";
            }
        }
    }

    rpc clear-mpls-vpls-mac-addresses-for-instance {
        if-feature feature-list:HAVE_VPLS;
        if-feature feature-list:HAVE_MPLS;
        description "Use this attribute to clear mpls vpls by NAME and mac_addresses";
        input  {
            leaf name  {
                type string;
                mandatory true;
                description "Specify VPLS instance name";
            }
        }
    }

    rpc clear-mpls-vpls-mac-addresses-all {
        if-feature feature-list:HAVE_VPLS;
        if-feature feature-list:HAVE_MPLS;
        description "Use this attribute to clear mpls vpls mac_addresses";
    }

    rpc clear-mpls-vpls-mac-move-for-instance {
        if-feature feature-list:HAVE_VPLS;
        if-feature feature-list:HAVE_MPLS;
        description "Use this attribute to clear mpls vpls mac move by NAME";
        input  {
            leaf name  {
                type string;
                mandatory true;
                description "Specify VPLS instance name";
            }
        }
    }

    notification mpls-vpls-session-up {
        if-feature feature-list:HAVE_VPLS;
        if-feature feature-list:HAVE_MPLS;

        description "This notification is sent when vpls peer enter the up state.";

        leaf severity {
            type cml-data-types:cml_notif_severity_t;
            description "Notification severity level (value: MINOR)";
        }

        leaf eventClass {
            type cml-data-types:cml_notif_class_t;
            description "Notification event class (value: STATE)";
        }

        leaf peer-address {
            type  inet:ipv4-address;
        description
            "Attribute to configure address of peer";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf vpls-identifier {
            type  uint32;
        description
            "Attribute to acquire vpls-id for a VPLS instance";
        }

        leaf peer-state {
            type ipi-vpls-types:vpls_peer_state_t;
        description
            "Attribute to acquire state of mesh peer pseudowire";
        }
    }

    notification mpls-vpls-session-down {
        if-feature feature-list:HAVE_VPLS;
        if-feature feature-list:HAVE_MPLS;

        description "This notification is sent when vpls peer enter the down state.";

        leaf severity {
            type cml-data-types:cml_notif_severity_t;
            description "Notification severity level (value: CRITICAL)";
        }

        leaf eventClass {
            type cml-data-types:cml_notif_class_t;
            description "Notification event class (value: STATE)";
        }

        leaf peer-address {
            type  inet:ipv4-address;
        description
            "Attribute to configure address of peer";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf vpls-identifier {
            type  uint32;
        description
            "Attribute to acquire vpls-id for a VPLS instance";
        }

        leaf peer-state {
            type ipi-vpls-types:vpls_peer_state_t;
        description
            "Attribute to acquire state of mesh peer pseudowire";
        }
    }

    notification mpls-vpls-spoke-session-up {
        if-feature feature-list:HAVE_VPLS;
        if-feature feature-list:HAVE_MPLS;

        description "This notification is sent when vpls spoke enter the up state.";

        leaf severity {
            type cml-data-types:cml_notif_severity_t;
            description "Notification severity level (value: MINOR)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf vpls-identifier {
            type  uint32;
        description
            "Specify VPLS identifier";
        }

        leaf vc-id {
            type  uint32;
        description
            "This attribute specify spoke vc-id";
        }

        leaf vc-name {
            type  string;
        description
            "This attribute specify spoke vc name";
        }

        leaf peer-address {
            type  string;
        description
            "This attribute specify spoke vc peer address";
        }

        leaf spoke-state {
            type ipi-vpls-types:vpls_peer_state_t;
        description
            "Attribute specify state of spoke VPLS";
        }
    }

    notification mpls-vpls-spoke-session-down {
        if-feature feature-list:HAVE_VPLS;
        if-feature feature-list:HAVE_MPLS;

        description "This notification is sent when vpls spoke enter the down state.";

        leaf severity {
            type cml-data-types:cml_notif_severity_t;
            description "Notification severity level (value: CRITICAL)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf vpls-identifier {
            type  uint32;
        description
            "Specify VPLS identifier";
        }

        leaf vc-id {
            type  uint32;
        description
            "This attribute specify spoke vc-id";
        }

        leaf vc-name {
            type  string;
        description
            "This attribute specify spoke vc name";
        }

        leaf peer-address {
            type  string;
        description
            "This attribute specify spoke vc peer address";
        }

        leaf spoke-state {
            type ipi-vpls-types:vpls_peer_state_t;
        description
            "Attribute specify state of spoke VPLS";
        }
    }

}
