/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-unicast-rpf-types.yang
*
*/

module ipi-unicast-rpf-types {

    yang-version 1.1;

    namespace   "http://www.ipinfusion.com/yang/ocnos/ipi-unicast-rpf-types";

    prefix "ipi-unicast-rpf-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module defines data types related to the uRPF model";


    revision "2022-06-07" {
        description "Initial version";
        reference " 0.1.0.";
    }



    typedef  urpf_src_reachability_mode_t {
        type enumeration {
            enum any {
                value 1;
                description "Enable Loose Mode uRPF on the router. Source is reachable via any interface";
            }
            enum rx {
                value 2;
                description "Enable Strict Mode uRPF on the router. Source is reachable via interface on which packet was received";
            }
            enum any-allow-default {
                value 3;
                if-feature feature-list:NOT_HAVE_DUNE;
                description "Enable Loose Mode uRPF on the router. Source is reachable via any interface,Loose Default Route uRPF. Allow default route to match when checking source address";
            }
        }
        description "type definition for URPF_SRC_REACHABILITY_MODE_T";
    }

}
