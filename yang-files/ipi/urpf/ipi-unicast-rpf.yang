/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-unicast-rpf.yang
*
*/

module ipi-unicast-rpf {

    yang-version 1.1;

    namespace   "http://www.ipinfusion.com/yang/ocnos/ipi-unicast-rpf";

    prefix "ipi-unicast-rpf";

    import ipi-unicast-rpf-types {
        prefix ipi-unicast-rpf-types;
        revision-date 2022-06-07;
    }

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for IPI Unicast Reverse Path Forwarding";


    revision "2026-05-14" {
        description "Added dependency handling to ensure encapsulation is configured before applying uRPF on sub-interfaces.";
        reference " 0.2.6.";
    }

    revision "2025-10-14" {
        description "Blocking ip urpf command for Tomahawk3, Tomahawk4, Tomahawk5";
        reference " 0.2.5.";
    }

    revision "2025-08-08" {
        description "Added dependency for configuring source-reachability-mode";
        reference " 0.2.4.";
    }

    revision "2025-07-29" {
        description "Blocking ip urpf command for Trident4";
        reference " 0.2.3.";
    }

    revision "2022-12-14" {
        description "Updated when expression related to double-tag-vlan-match xpath";
        reference " 0.2.2.";
    }

    revision "2022-09-23" {
        description "Added when tag for deletion of encapsulation-type of L3 subinterface";
        reference " 0.2.1.";
    }

    revision "2022-07-30" {
        description "Modified when expression";
        reference " 0.2.0.";
    }

    revision "2022-06-07" {
        description "Initial Version";
        reference " 0.1.0.";
    }

    grouping urpf-global-parameters-config {
        description
            "Top level grouping for uRPF global configuration data";
        leaf enable-route-lookup  {
            type  empty;
            description "Use this attribute to enable uRPF globally on the system";
        } // END of enable-route-lookup definition.

        leaf enable-default-route-check  {
            if-feature feature-list:HAVE_DUNE;
            if-feature feature-list:HAVE_GLOBAL_URPF_ALLOW_DEFAULT;
            type  empty;
            description "Use this attribute to enable default route to match when checking
                        source IP address";
        } // END of enable-default-route-check definition.

    } // END of urpf-global-parameters-config definition.
    grouping urpf-global-top {
        description
            "Top level grouping for uRPF global configuration and state data";
        container global {
            description
                "uRPF global configuration and state data";
            container config {
                description
                    "Configuration data for uRPF global configuration";
                uses urpf-global-parameters-config;
            } // END of config-container definition.
            container state {
                config false;
                description
                    "Operational data for uRPF global configuration";
                uses urpf-global-parameters-config;
            } // END of state-container definition.
        } // END of global-container definition.
    } // END of urpf-global-top definition.
    grouping urpf-interfaces-top {
        description
            "Top level grouping for uRPF interface configuration and state data";
        container interfaces {
            description
                "Support uRPF functionality at inteface level";

            list interface {
            // when " not(/ipi-interface:interfaces/ipi-interface:interface/ipi-interface:config/ipi-interface:enable-switchport) ";
                key "name";
                description
                    "List of uRPF enabled interfaces";
                leaf name  {
                    type  leafref {
                        path  "../config/name";
                    }
                    description "This attriute maps to physical/L3 LAG interface/L3 Sub-interface on
                                which uRPF is enabled";
                } // END of name definition.

                container config {
                    description
                        "Configuration data for uRPF";
                    uses urpf-interfaces-parameters-config;
                } // END of config-container definition.
                container state {
                    config false;
                    description
                        "Operational data for uRPF";
                    uses urpf-interfaces-parameters-config;
                } // END of state-container definition.
            } // End of interface-list
        } // END of interfaces-container definition.
    } // END of urpf-interfaces-top definition.
    grouping urpf-interfaces-parameters-config {
        description
            "uRPF interface config data";
        leaf name  {
            type  leafref {
                path  "/ipi-interface:interfaces/ipi-interface:interface/ipi-interface:name";
            }
            description "This attriute maps to physical/L3 LAG interface/L3 Sub-interface on
                        which uRPF is enabled";
        } // END of name definition.

        leaf source-reachability-mode  {
            when " /ipi-unicast-rpf:unicast-rpf/ipi-unicast-rpf:global/ipi-unicast-rpf:config/ipi-unicast-rpf:enable-route-lookup ";
            type  ipi-unicast-rpf-types:urpf_src_reachability_mode_t;
            mandatory true;
            description "Use this attribute to enable uRPF for an interface with specified
                        reachability mode";
        } // END of source-reachability-mode definition.

    } // END of urpf-interfaces-parameters-config definition.

    grouping  unicast-rpf-grouping {
    description
        "Main container for Unicast Reverse Path Forwarding (uRPF)";
    container unicast-rpf {
        if-feature feature-list:HAVE_RPF;
        description
            "Main container for Unicast Reverse Path Forwarding (uRPF)";
        uses urpf-global-top;
        uses urpf-interfaces-top;
    } // END of unicast-rpf-container definition.
    } // END of unicast-rpf-grouping definition.

    uses unicast-rpf-grouping;

}
