/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-macsec.yang
*
*/

module ipi-macsec {

    yang-version 1.1;

    namespace   "http://www.ipinfusion.com/yang/ocnos/ipi-macsec";

    prefix "ipi-macsec";

    import ietf-inet-types {
        prefix inet;
        revision-date 2013-07-15;
    }

    import ietf-yang-types {
        prefix yang;
        revision-date 2013-07-15;
    }

    import cml-data-types {
        prefix cml-data-types;
        revision-date 2026-05-15;
    }

    import ipi-macsec-types {
        prefix ipi-macsec-types;
        revision-date 2026-05-11;
    }

    import feature-list {
        prefix feature-list;
        revision-date 2026-09-15;
    }

    include ipi-macsec-interface { revision-date 2026-04-29;}
    organization
        "IP Infusion Inc.";

    contact
        "Address: 3965 Freedom Circle, Suite 200, Santa Clara, CA 95054
         Phone: +1 408-400-1900
         E-mail: support@ipinfusion.com
         Web: http://www.ipinfusion.com/";

    description
        "Data model for MACsec Module";


    revision "2026-05-28" {
        description "Hide the delay-protect attribute for 7.0.1";
        reference " 0.2.13.";
    }

    revision "2026-05-11" {
        description "Disable counters that do not increment";
        reference " 0.2.12.";
    }

    revision "2026-04-30" {
        description "Adding dependency for deletion between ca profile attributes and interface";
        reference " 0.2.11.";
    }

    revision "2026-04-28" {
        description "Removed QKD enum values";
        reference " 0.2.10.";
    }

    revision "2026-04-27" {
        description "Fixed error message when configure security mode";
        reference " 0.2.9.";
    }

    revision "2026-04-21" {
        description "Removed cml limit on value of max-elements in connectivity-association";
        reference " 0.2.8.";
    }

    revision "2026-04-20" {
        description "Add support to replay-protection and delay-protect configuration";
        reference " 0.2.7.";
    }

    revision "2026-04-19" {
        description "Fix previous revisions";
        reference " 0.2.6.";
    }

    revision "2026-04-16" {
        description "Rename interface key attribute from interface-name to name";
        reference " 0.2.5.";
    }

    revision "2026-04-15" {
        description "Added debug macsec mka comamnd";
        reference " 0.2.4.";
    }

    revision "2026-04-14" {
        description "Add xpn cipher suite values";
        reference " 0.2.3.";
    }

    revision "2026-03-30" {
        description "Prevent enabling macsec on interfaces that are part of a link aggregation";
        reference " 0.2.2.";
    }

    revision "2026-02-16" {
        description "Add new runtime attributes related to show commands and unhide configurations";
        reference " 0.2.1.";
    }

    revision "2025-10-24" {
        description "Add support to MKA pre-shared-key and modify security-mode-profile name in SecY";
        reference " 0.2.0.";
    }

    revision "2023-05-16" {
        description "Change macsec-ca-name under interface to if-macsec-ca to fix issue with mode change";
        reference " 0.1.6.";
    }

    revision "2023-03-09" {
        description "Change port limit to allow https port configuration";
        reference " 0.1.5.";
    }

    revision "2023-03-06" {
        description "Add implicit_delete tag to remove interface object when macsec-ca-name is removed";
        reference " 0.1.4.";
    }

    revision "2023-02-24" {
        description "Add dependecy tag for creation/delition of secy and qkd security, qkd neighbour";
        reference " 0.1.3.";
    }

    revision "2023-02-15" {
        description "Add dependecy tag for creation/delition of macsec objects";
        reference " 0.1.2.";
    }

    revision "2023-01-05" {
        description "Remove connectivity association session secure association list";
        reference " 0.1.1.";
    }

    revision "2022-11-22" {
        description "Initial Version";
        reference " 0.1.0.";
    }

    grouping key-management-entity-config {
        description
            "Grouping for Key Management Entity config parameters";
        leaf kme-name  {
            type  string {
                length "1..32";
                pattern "[^?' =,>|]+";
            }
            description "Key management entity server name";
        } // END of kme-name definition.

        leaf sae-peer-name  {
            type  string {
                length "1..250";
                pattern "[^?' =,>|]+";
            }
            description "Secure application entity peer identifier, participating in MACsec
                        operation";
        } // END of sae-peer-name definition.

        leaf transport-protocol  {
            type  ipi-macsec-types:macsec_transport_protocol_t;
            default "https";
            description "Transport protocol to communicate with KME";
        } // END of transport-protocol definition.

        leaf host-address  {
            type  cml-data-types:cml_hostname_t;
            description "The host address can be IPv4/IPv6 address or hostname";
        } // END of host-address definition.

        leaf port  {
            type  ipi-macsec-types:macsec_port_number_t {
                 range "0..65535"  {
                    description "0..65535: Supported range 0 - 65535";
                 }
            }
            description "KME port to form URL";
        } // END of port definition.

    } // END of key-management-entity-config definition.
    grouping key-management-entity-top {
        description
            "Grouping for Key Management Entity top level grouping";
        container key-management-entities {
            description
                "Key Management Entity";

            list key-management-entity {
                key "kme-name";
                max-elements 1;
                description
                    "Key Management Entity list";
                leaf kme-name  {
                    type  leafref {
                        path  "../config/kme-name";
                    }
                    description "Key management entity server profile name";
                } // END of kme-name definition.

                container config {
                    description
                        "KME server config parameters";
                    uses key-management-entity-config;
                } // END of config-container definition.
                container state {
                    config false;
                    description
                        "KME server operational parameters";
                    uses key-management-entity-config;
                } // END of state-container definition.
            } // End of key-management-entity-list
        } // END of key-management-entities-container definition.
    } // END of key-management-entity-top definition.
    grouping quantum-key-distribution-transport-security-config {
        description
            "Grouping for quantum key distribution transport security configuration
                        parameters";
        leaf server-certificate-name  {
            type  string {
                length "1..511";
                pattern "[^?' =,>|]+";
            }
            description "Server Certificate to be used while establishing secure connection
                        with peer key-distribution proxy application";
        } // END of server-certificate-name definition.

        leaf server-key-name  {
            type  string {
                length "1..511";
                pattern "[^?' =,>|]+";
            }
            description "Server key to be used while establishing secure connection with peer
                        key-distribution proxy application";
        } // END of server-key-name definition.

    } // END of quantum-key-distribution-transport-security-config definition.
    grouping quantum-key-distribution-neighbour-config {
        description
            "Grouping for quantum key distribution neighbour configuration
                        parameters";
        leaf host-address  {
            type  cml-data-types:cml_hostname_t;
            description "The host address can be IPv4/IPv6 address or hostname";
        } // END of host-address definition.

        leaf port  {
            type  ipi-macsec-types:macsec_port_number_t {
                 range "1024..65535"  {
                    description "1024..65535: Supported range 1024 - 65535";
                 }
            }
            description "The port this server instance binds to";
        } // END of port definition.

    } // END of quantum-key-distribution-neighbour-config definition.
    grouping quantum-key-distribution-config {
        description
            "Grouping for quantum key distribution configuration parameters";
        leaf qkd-name  {
            type  string {
                length "1..32";
                pattern "[^?' =,>|]+";
            }
            description "quantum key distribution profile name";
        } // END of qkd-name definition.

        leaf key-management-entity  {
            type  leafref {
                path  "/macsec/key-management-entities/key-management-entity/kme-name";
            }
            description "Reference to KME configuration";
        } // END of key-management-entity definition.

        leaf host-address  {
            type  cml-data-types:cml_hostname_t;
            description "The host address can be IPv4/IPv6 address or hostname";
        } // END of host-address definition.

        leaf port  {
            type  ipi-macsec-types:macsec_port_number_t {
                 range "1024..65535"  {
                    description "1024..65535: Supported range 1024 - 65535";
                 }
            }
            description "The port this server instance binds to";
        } // END of port definition.

    } // END of quantum-key-distribution-config definition.
    grouping quantum-key-distribution-top {
        description
            "Grouping for quantum key distribution top level grouping";
        container quantum-key-distributions {
            description
                "quantum key distribution";

            list quantum-key-distribution {
                key "qkd-name";
                max-elements 1;
                description
                    "quantum key distribution list";
                leaf qkd-name  {
                    type  leafref {
                        path  "../config/qkd-name";
                    }
                    description "quantum key distribution profile name";
                } // END of qkd-name definition.

                container config {
                    description
                        "QKD server configuration parameters";
                    uses quantum-key-distribution-config;
                } // END of config-container definition.
                container state {
                    config false;
                    description
                        "QKD server operational parameters";
                    uses quantum-key-distribution-config;
                } // END of state-container definition.
                container transport-security {
                    description
                        "Server side certificates to be used in the TLS connection KaY server
                                and KaY neighbour";
                    container config {
                        description
                            "Server side certificates to be used in the TLS connection KaY server
                                    and KaY neighbour";
                        uses quantum-key-distribution-transport-security-config;
                    } // END of config-container definition.
                    container state {
                        config false;
                        description
                            "Server side certificates to be used in the TLS connection KaY server
                                    and KaY neighbour";
                        uses quantum-key-distribution-transport-security-config;
                    } // END of state-container definition.
                } // END of transport-security-container definition.
                container neighbour {
                    description
                        "KaY server neighbour participating in MACsec operation";
                    container config {
                        description
                            "QKD server neighbour configuration parameters";
                        uses quantum-key-distribution-neighbour-config;
                    } // END of config-container definition.
                    container state {
                        config false;
                        description
                            "QKD server neighbour operational parameters";
                        uses quantum-key-distribution-neighbour-config;
                    } // END of state-container definition.
                } // END of neighbour-container definition.
            } // End of quantum-key-distribution-list
        } // END of quantum-key-distributions-container definition.
    } // END of quantum-key-distribution-top definition.
    grouping security-entity-config {
        description
            "Grouping for security entity configuration parameters";
        leaf secy-name  {
            type  string {
                length "1..255";
                pattern "[^?' =,>|]+";
            }
            description "security entity profile name identifier in user readable string format";
        } // END of secy-name definition.

        leaf host-address  {
            type  cml-data-types:cml_hostname_t;
            description "Security entity (SecY) service binds to this address";
        } // END of host-address definition.

        leaf port  {
            type  ipi-macsec-types:macsec_port_number_t {
                 range "1024..65535"  {
                    description "1024..65535: Supported range 1024 - 65535";
                 }
            }
            description "Security entity (SecY) service binds to this port";
        } // END of port definition.

        leaf kay-host-address  {
            type  cml-data-types:cml_hostname_t;
            description "KaY service binds to this address";
        } // END of kay-host-address definition.

        leaf kay-port  {
            type  inet:port-number {
                 range "1024..65535"  {
                    description "1024..65535: Supported range 1024 - 65535";
                 }
            }
            description "KaY service binds to this port";
        } // END of kay-port definition.

        leaf ka-profile  {
            type  leafref {
                path  "/macsec/quantum-key-distributions/quantum-key-distribution/qkd-name";
            }
            description "The ka used profile used by KaY";
        } // END of ka-profile definition.

    } // END of security-entity-config definition.
    grouping security-entity-top {
        description
            "Grouping for security entity top level grouping";
        container security-entities {
            description
                "security entity";

            list security-entity {
                key "secy-name";
                max-elements 1;
                description
                    "security entity object list";
                leaf secy-name  {
                    type  leafref {
                        path  "../config/secy-name";
                    }
                    description "Security entity name";
                } // END of secy-name definition.

                container config {
                    description
                        "security entity configuration";
                    uses security-entity-config;
                } // END of config-container definition.
                container state {
                    config false;
                    description
                        "security entity state";
                    uses security-entity-config;
                } // END of state-container definition.
            } // End of security-entity-list
        } // END of security-entities-container definition.
    } // END of security-entity-top definition.
    grouping connectivity-association-config {
        description
            "Connectivity Association configuration parameters";
        leaf ca-name  {
            type  string {
                length "1..32";
                pattern "[^?' =,>|]+";
            }
            description "Connectivity association profile name identifier in user readable
                        string format";
        } // END of ca-name definition.

        leaf key-server-priority  {
            type  uint8 {
                 range "0..255"  {
                    description "0..255: Supported range 0 - 255";
                 }
            }
            description "Specifies the MKA server election priority number. The lower the
                        number, the higher the priority.";
        } // END of key-server-priority definition.

        leaf key-renewal-duration  {
            type  uint32 {
                 range "5..64800"  {
                    description "5..64800: Supported range 5 - 64800";
                 }
            }
            units "seconds";
            description "Renew the encryption key periodically";
        } // END of key-renewal-duration definition.

        leaf cipher-suite  {
            type  ipi-macsec-types:macsec_cipher_suite_t;
            description "Cipher suite for masec dataplane encryption / decryption";
        } // END of cipher-suite definition.

        leaf secy  {
            // when " ../security-mode='1' or ../security-mode='2' ";
            type  leafref {
                path  "/macsec/security-entities/security-entity/secy-name";
            }
            description "Security entity (SecY) profile";
        } // END of secy definition.

        leaf pre-shared-key-ckn  {
            // when " ../security-mode='pre-shared-cak' ";
            type  ipi-macsec-types:macsec_hex_string_ckn_t;
            description "This is the CKN (Connectivity Association Key Name) to be used in
                        macsec authentication. Takes a hex-string (2..64 hex-digits), in steps
                        of 2.";
        } // END of pre-shared-key-ckn definition.

        leaf pre-shared-key-cak  {
            // when " ../security-mode='pre-shared-cak' ";
            type  ipi-macsec-types:macsec_hex_string_cak_t;
            description "This is the Secure CAK(Connectivity Association Key) and it takes a
                        hex-string of 32 hex-digits or 64 hex-digits.";
        } // END of pre-shared-key-cak definition.

        leaf security-mode  {
            type  ipi-macsec-types:macsec_security_mode_t;
            description "The security mode used by KaY";
        } // END of security-mode definition.

        leaf replay-protect  {
            type  empty;
            description "This enables the replay protection feature. By default, if window size
                        is not configured, it will set
                        the window size to 0. This enforces strict ordering, where any packet
                        arriving out of sequence is dropped.
                        If this attribute is not set, the replay-protect is not enabled and
                        all PN are allowed.";
        } // END of replay-protect definition.

        leaf replay-protect-window-size  {
            // when " ipi-macsec:macsec/connectivity-associations/connectivity-association/config/replay-protect ";
            type  uint32 {
                 range "0..4294967295"  {
                    description "0..4294967295: Supported range 0 - 4294967295";
                 }
            }
            default "0";
            description "A Replay Protection Window Size can be configured to allow a specific
                        number of out-of-order packets without discarding them.
                        Setting the window size to 0 enforces strict ordering, where any
                        packet arriving out of sequence is dropped.";
        } // END of replay-protect-window-size definition.

    } // END of connectivity-association-config definition.
    grouping connectivity-associations-top {
        description
            "Connectivity Association Top level grouping";
        container connectivity-associations {
            description
                "Connectivity Association";

            list connectivity-association {
                key "ca-name";
                description
                    "Connectivity Association List";
                leaf ca-name  {
                    type  leafref {
                        path  "../config/ca-name";
                    }
                    description "Connectivity Association name";
                } // END of ca-name definition.

                container config {
                    description
                        "Connectivity Association config parameters";
                    uses connectivity-association-config;
                } // END of config-container definition.
                container state {
                    config false;
                    description
                        "State parameters of connectivity association";
                    uses connectivity-association-config;
                } // END of state-container definition.
            } // End of connectivity-association-list
        } // END of connectivity-associations-container definition.
    } // END of connectivity-associations-top definition.
    grouping sessions-hw-events-statistics-state {
        description
            "MACsec sessions MKA SA statistics state parameters";
        leaf error-unknown-policy  {
            type  yang:counter32;
            description "The number of packets with error unknown policy";
        } // END of error-unknown-policy definition.

        leaf error-tag-ctrl-port  {
            type  yang:counter32;
            description "The number of packets with error tagged frames disabled";
        } // END of error-tag-ctrl-port definition.

        leaf error-untag-ctrl-port  {
            type  yang:counter32;
            description "The number of packets with error untagged frames disabled";
        } // END of error-untag-ctrl-port definition.

        leaf error-ipv4-mpls  {
            type  yang:counter32;
            description "The number of packets with error in IPv4 and MPLS BOS";
        } // END of error-ipv4-mpls definition.

        leaf error-invalid-sectag  {
            type  yang:counter32;
            description "The number of packets with error invalid SecTag";
        } // END of error-invalid-sectag definition.

        leaf error-unknown-secure-channel  {
            type  yang:counter32;
            description "The number of packets with error unknown secure channel";
        } // END of error-unknown-secure-channel definition.

        leaf error-unknown-secure-association  {
            type  yang:counter32;
            description "The number of packets with error unknown secure association";
        } // END of error-unknown-secure-association definition.

        leaf error-replay-failure  {
            type  yang:counter32;
            description "The number of packets with error replay failure";
        } // END of error-replay-failure definition.

    } // END of sessions-hw-events-statistics-state definition.
    grouping sessions-hw-events-statistics-top {
        description
            "MACsec sessions HW Events Statistics Top level grouping";
        container hardware-events-statistics {
            config false;
            description
                "MACsec sessions HW Events Statistics";
            container state {
                config false;
                description
                    "State parameters of HW Events Statistics";
                uses sessions-hw-events-statistics-state;
            } // END of state-container definition.
        } // END of hardware-events-statistics-container definition.
    } // END of sessions-hw-events-statistics-top definition.
    grouping sessions-mka-mkpdu-statistics-rx-state {
        description
            "MACsec sessions MKPDU RX statistics state parameters";
        leaf mkpdu-quantity  {
            type  yang:counter32;
            description "The number of received MPKDUs";
        } // END of mkpdu-quantity definition.

        leaf distributed-sak  {
            type  yang:counter32;
            description "The number of distributed SAK keys";
        } // END of distributed-sak definition.

        leaf distributed-cak  {
            type  yang:counter32;
            description "The number of distributed CAK keys";
        } // END of distributed-cak definition.

        leaf invalid-icv  {
            type  yang:counter32;
            description "The number of invalid packets with wrong ICV. The receiver's
                        calculated ICV doesn't match the one in the packet, the packet is
                        discarded as invalid";
        } // END of invalid-icv definition.

        leaf invalid-version  {
            type  yang:counter32;
            description "The number of received packets that have EAPOL unsopported version.";
        } // END of invalid-version definition.

        leaf invalid-length  {
            type  yang:counter32;
            description "The number of packets received with invalid MKPDU invalid size";
        } // END of invalid-length definition.

        leaf invalid-ckn  {
            type  yang:counter32;
            description "The number of packets with invalid CKN. The packet received does not
                        match the received CKN";
        } // END of invalid-ckn definition.

    } // END of sessions-mka-mkpdu-statistics-rx-state definition.
    grouping sessions-mka-mkpdu-statistics-rx-top {
        description
            "MACsec sessions MKA MKPDU RX statistics Top level grouping";
        container rx {
            config false;
            description
                "MACsec sessions MKA MKPDU RX statistics";
            container state {
                config false;
                description
                    "State parameters of MKA MKPDU RX";
                uses sessions-mka-mkpdu-statistics-rx-state;
            } // END of state-container definition.
        } // END of rx-container definition.
    } // END of sessions-mka-mkpdu-statistics-rx-top definition.
    grouping sessions-mka-mkpdu-statistics-tx-state {
        description
            "MACsec sessions MKPDU TX statistics state parameters";
        leaf mkpdu-quantity  {
            type  yang:counter32;
            description "The number of transmitted MPKDUs";
        } // END of mkpdu-quantity definition.

        leaf distributed-sak  {
            type  yang:counter32;
            description "The number of SAK keys distributed";
        } // END of distributed-sak definition.

        leaf distributed-cak  {
            type  yang:counter32;
            description "The number of CAK keys distributed";
        } // END of distributed-cak definition.

    } // END of sessions-mka-mkpdu-statistics-tx-state definition.
    grouping sessions-mka-mkpdu-statistics-tx-top {
        description
            "MACsec sessions MKA MKPDU TX statistics Top level grouping";
        container tx {
            config false;
            description
                "MACsec sessions MKA SA statistics";
            container state {
                config false;
                description
                    "State parameters of MKA MKPDU TX";
                uses sessions-mka-mkpdu-statistics-tx-state;
            } // END of state-container definition.
        } // END of tx-container definition.
    } // END of sessions-mka-mkpdu-statistics-tx-top definition.
    grouping sessions-mka-mkpdu-statistics-top {
        description
            "MACsec sessions MKA MKPDU statistics Top level grouping";
        container mkpdu-statistics {
            config false;
            description
                "MACsec sessions MKA MKPDU statistics";
            uses sessions-mka-mkpdu-statistics-tx-top;
            uses sessions-mka-mkpdu-statistics-rx-top;
        } // END of mkpdu-statistics-container definition.
    } // END of sessions-mka-mkpdu-statistics-top definition.
    grouping sessions-mka-sa-statistics-state {
        description
            "MACsec sessions MKA SA statistics state parameters";
        leaf saks-generated  {
            type  yang:counter32;
            description "The number of SAKs generated";
        } // END of saks-generated definition.

        leaf saks-rekeyed  {
            type  yang:counter32;
            description "The number of times that SAK was rekeyed";
        } // END of saks-rekeyed definition.

        leaf saks-received  {
            type  yang:counter32;
            description "The number of received SAKs";
        } // END of saks-received definition.

        leaf saks-responses-received  {
            type  yang:counter32;
            description "The number of responses for packets with SAK key";
        } // END of saks-responses-received definition.

    } // END of sessions-mka-sa-statistics-state definition.
    grouping sessions-mka-sa-statistics-top {
        description
            "MACsec sessions MKA SA statistics Top level grouping";
        container secure-association-statistics {
            config false;
            description
                "MACsec sessions MKA SA statistics";
            container state {
                config false;
                description
                    "State parameters of MKA SA statistics";
                uses sessions-mka-sa-statistics-state;
            } // END of state-container definition.
        } // END of secure-association-statistics-container definition.
    } // END of sessions-mka-sa-statistics-top definition.
    grouping sessions-mka-statistics-top {
        description
            "MACsec sessions MKA statistics Top level grouping";
        container mka-statistics {
            config false;
            description
                "MACsec sessions MKA statistics";
            uses sessions-mka-sa-statistics-top;
            uses sessions-mka-mkpdu-statistics-top;
        } // END of mka-statistics-container definition.
    } // END of sessions-mka-statistics-top definition.
    grouping sessions-receive-sa-state {
        description
            "Connectivity Association Secure Association state parameters";
        leaf rx-sa-identifier  {
            type  uint32;
            description "Association number";
        } // END of rx-sa-identifier definition.

        leaf rx-secure-channel-identifier  {
            type  string {
                length "1..1965";
                pattern "[^?' =,>|]+";
            }
            description "Secure channel identifier (SCI)";
        } // END of rx-secure-channel-identifier definition.

        leaf rx-sa-programming-state  {
            type  ipi-macsec-types:macsec_sa_programming_state_t;
            description "Indicates the programming state of the Security Association";
        } // END of rx-sa-programming-state definition.

    } // END of sessions-receive-sa-state definition.
    grouping sessions-transmit-sa-state {
        description
            "Connectivity Association Secure Association state parameters";
        leaf tx-sa-identifier  {
            type  uint32;
            description "Association number";
        } // END of tx-sa-identifier definition.

        leaf tx-secure-channel-identifier  {
            type  string {
                length "1..1965";
                pattern "[^?' =,>|]+";
            }
            description "Secure channel identifier (SCI)";
        } // END of tx-secure-channel-identifier definition.

        leaf tx-sa-programming-state  {
            type  ipi-macsec-types:macsec_sa_programming_state_t;
            description "Indicates the programming state of the Security Association";
        } // END of tx-sa-programming-state definition.

    } // END of sessions-transmit-sa-state definition.
    grouping sessions-receive-sa-top {
        description
            "MACsec sessions direction SA Top level grouping";
        container receive-secure-associations {
            config false;
            description
                "MACsec sessions secure associations";

            list receive-secure-association {
                key "rx-sa-identifier";
                config false;
                description
                    "MACsec sessions secure association list";
                leaf rx-sa-identifier  {
                    type  leafref {
                        path  "../state/rx-sa-identifier";
                    }
                    description "Association number";
                } // END of rx-sa-identifier definition.

                container state {
                    config false;
                    description
                        "State parameters of secure association";
                    uses sessions-receive-sa-state;
                } // END of state-container definition.
            } // End of receive-secure-association-list
        } // END of receive-secure-associations-container definition.
    } // END of sessions-receive-sa-top definition.
    grouping sessions-transmit-sa-top {
        description
            "MACsec sessions direction SA Top level grouping";
        container transmit-secure-associations {
            config false;
            description
                "MACsec sessions secure associations";

            list transmit-secure-association {
                key "tx-sa-identifier";
                config false;
                description
                    "MACsec sessions secure association list";
                leaf tx-sa-identifier  {
                    type  leafref {
                        path  "../state/tx-sa-identifier";
                    }
                    description "Association number";
                } // END of tx-sa-identifier definition.

                container state {
                    config false;
                    description
                        "State parameters of secure association";
                    uses sessions-transmit-sa-state;
                } // END of state-container definition.
            } // End of transmit-secure-association-list
        } // END of transmit-secure-associations-container definition.
    } // END of sessions-transmit-sa-top definition.
    grouping sessions-receive-state {
        description
            "Operational state data";
        leaf rx-identifier  {
            type  string {
                length "1..1965";
                pattern "[^?' =,>|]+";
            }
            description "Session identifier";
        } // END of rx-identifier definition.

        leaf rx-session-state  {
            type  ipi-macsec-types:macsec_ca_session_state_t;
            description "The state of Connectivity Association state machine";
        } // END of rx-session-state definition.

        leaf rx-inactive-error-reason  {
            type  ipi-macsec-types:macsec_ca_error_reason_t;
            description "The error reason when the session is inactive";
        } // END of rx-inactive-error-reason definition.

    } // END of sessions-receive-state definition.
    grouping sessions-transmit-state {
        description
            "Operational state data";
        leaf tx-identifier  {
            type  string {
                length "1..1965";
                pattern "[^?' =,>|]+";
            }
            description "Session identifier";
        } // END of tx-identifier definition.

        leaf tx-session-state  {
            type  ipi-macsec-types:macsec_ca_session_state_t;
            description "The state of Connectivity Association state machine";
        } // END of tx-session-state definition.

        leaf tx-inactive-error-reason  {
            type  ipi-macsec-types:macsec_ca_error_reason_t;
            description "The error reason when the session is inactive";
        } // END of tx-inactive-error-reason definition.

    } // END of sessions-transmit-state definition.
    grouping sessions-receive-top {
        description
            "MACsec sessions receive direction Top level grouping";
        container receive-direction {
            config false;
            description
                "MACsec sessions receive direction";
            container state {
                config false;
                description
                    "State parameters of SecY KAY connection";
                uses sessions-receive-state;
            } // END of state-container definition.
            uses sessions-receive-sa-top;
        } // END of receive-direction-container definition.
    } // END of sessions-receive-top definition.
    grouping sessions-transmit-top {
        description
            "MACsec sessions transmit direction state Top level grouping";
        container transmit-direction {
            config false;
            description
                "MACsec sessions transmit direction";
            container state {
                config false;
                description
                    "State parameters of SecY KAY connection";
                uses sessions-transmit-state;
            } // END of state-container definition.
            uses sessions-transmit-sa-top;
        } // END of transmit-direction-container definition.
    } // END of sessions-transmit-top definition.
    grouping sessions-secy-kay-connection-state {
        description
            "Operational state data";
        leaf kay-connection-status  {
            type  ipi-macsec-types:macsec_kay_connection_status_t;
            description "MACsec KAY connection status, indicating whether it is operational or
                        not";
        } // END of kay-connection-status definition.

        leaf secy-server-host  {
            type  cml-data-types:cml_hostname_t;
            description "Server bound host";
        } // END of secy-server-host definition.

        leaf secy-server-port  {
            type  ipi-macsec-types:macsec_port_number_t;
            description "Server bound port";
        } // END of secy-server-port definition.

        leaf secy-server-listen  {
            type  boolean;
            description "Indicated whether the server is listening or not for connections";
        } // END of secy-server-listen definition.

        leaf kay-client-host  {
            type  cml-data-types:cml_hostname_t;
            description "Client connected from host";
        } // END of kay-client-host definition.

        leaf kay-client-port  {
            type  ipi-macsec-types:macsec_port_number_t;
            description "Client connected from port";
        } // END of kay-client-port definition.

        leaf kay-client-accept  {
            type  boolean;
            description "Indicates whether kay-client connection accepted or not";
        } // END of kay-client-accept definition.

    } // END of sessions-secy-kay-connection-state definition.
    grouping sessions-secy-kay-connection-top {
        description
            "MACsec sessions SecY KAY connection state Top level grouping";
        container secy-kay-connection {
            config false;
            description
                "MACsec sessions SecY KAY connection";
            container state {
                config false;
                description
                    "State parameters of SecY KAY connection";
                uses sessions-secy-kay-connection-state;
            } // END of state-container definition.
        } // END of secy-kay-connection-container definition.
    } // END of sessions-secy-kay-connection-top definition.
    grouping sessions-state {
        description
            "Operational state data for macsec-sessions";
        leaf session-interface-name  {
            type  string {
                length "1..49";
                pattern "[^?' =,>|]+";
            }
            description "MACsec session interface name";
        } // END of session-interface-name definition.

        leaf session-ca-name  {
            type  string {
                length "1..127";
                pattern "[^?' =,>|]+";
            }
            description "MACsec session CA name";
        } // END of session-ca-name definition.

        leaf association-state  {
            type  ipi-macsec-types:macsec_ca_interface_association_state_t;
            description "Indicates whether the CA is associate or not to interface. This
                        attribute value changes when the associated interface flaps";
        } // END of association-state definition.

        leaf traffic-status  {
            type  ipi-macsec-types:macsec_ca_traffic_status_t;
            description "This attribute indicated if the traffic in protected or not";
        } // END of traffic-status definition.

        leaf member-identifier  {
            type  string {
                length "1..1965";
                pattern "[^?' =,>|]+";
            }
            description "This attribute indicates the member identifier (MI), that is a unique
                        identifier used to distinguish each participating network node within
                        a Connectivity Association (CA) domain";
        } // END of member-identifier definition.

        leaf cak-name  {
            type  string {
                length "1..1965";
                pattern "[^?' =,>|]+";
            }
            description "This attribute indicates the Connectivity Association Key Name (CKN)";
        } // END of cak-name definition.

        leaf rekey-interval  {
            type  uint32;
            description "This attribute indicates the interval that is configured in MKA for
                        the rekeying of SAKs";
        } // END of rekey-interval definition.

        leaf key-server-priority  {
            type  uint8;
            description "This attribute specifies the MKA server election priority number";
        } // END of key-server-priority definition.

        leaf key-server  {
            type  boolean;
            description "This attribute indicates whether the node is the key server or not";
        } // END of key-server definition.

        leaf latest-sak-an  {
            type  uint8;
            description "This attribute indicates the current SAK association number";
        } // END of latest-sak-an definition.

        leaf previous-sak-an  {
            type  uint8;
            description "This attribute indicates the previous SAK association number";
        } // END of previous-sak-an definition.

        leaf security-suite  {
            type  ipi-macsec-types:macsec_cipher_suite_t;
            description "This attribute specifies the security-suite that was chosen by
                        key-server to encrypt SAKs";
        } // END of security-suite definition.

    } // END of sessions-state definition.
    grouping sessions-top {
        description
            "MACsec sessions state Top level grouping";
        container sessions {
            config false;
            description
                "MACsec sessions";

            list session {
                key "session-interface-name session-ca-name";
                config false;
                description
                    "MACsec sessions list";
                leaf session-interface-name  {
                    type  leafref {
                        path  "../state/session-interface-name";
                    }
                    description "MACsec session interface name";
                } // END of session-interface-name definition.

                leaf session-ca-name  {
                    type  leafref {
                        path  "../state/session-ca-name";
                    }
                    description "MACsec session CA name";
                } // END of session-ca-name definition.

                container state {
                    config false;
                    description
                        "State parameters of connectivity association";
                    uses sessions-state;
                } // END of state-container definition.
                uses sessions-secy-kay-connection-top;
                uses sessions-receive-top;
                uses sessions-transmit-top;
                uses sessions-mka-statistics-top;
                uses sessions-hw-events-statistics-top;
            } // End of session-list
        } // END of sessions-container definition.
    } // END of sessions-top definition.
    grouping macsec-debug-config {
        description
            "Grouping for debug configuration for Macsec";
        leaf options  {
            type  ipi-macsec-types:macsec_mka_debug_t;
            description "Use this attribute to enable macsec debug";
        } // END of options definition.

    } // END of macsec-debug-config definition.
    grouping macsec-debug-top {
        description
            "Grouping for debug top";
        container debug {
            description
                "Debug Flags";
            container config {
                description
                    "Debug flags for configuration";
                uses macsec-debug-config;
            } // END of config-container definition.
            container state {
                config false;
                description
                    "Debug flags state information";
                uses macsec-debug-config;
            } // END of state-container definition.
        } // END of debug-container definition.
    } // END of macsec-debug-top definition.

    grouping  macsec-grouping {
    description
        "Top level container for macsec configurations";
    container macsec {
        if-feature feature-list:HAVE_MACSEC;
        description
            "Top level container for macsec configurations";
        uses key-management-entity-top;
        uses quantum-key-distribution-top;
        uses security-entity-top;
        uses connectivity-associations-top;
        uses sessions-top;
        uses macsec-debug-top;
        uses interfaces-grouping;
    } // END of macsec-container definition.
    } // END of macsec-grouping definition.

    uses macsec-grouping;

    rpc macsec-clear-statistics-interface {
        if-feature feature-list:HAVE_MACSEC;
        description "Clears MACsec statistics from interface";
        input  {
            leaf name  {
                type string;
                mandatory true;
                description "Specify the interface name for which statistics should be cleared";
            }
        }
    }

    rpc macsec-clear-sessions-interface-statistics {
        if-feature feature-list:HAVE_MACSEC;
        description "Clears MACsec sessions statistics from interface";
        input  {
            leaf name  {
                type string;
                mandatory true;
                description "Specify the interface name for which statistics should be cleared";
            }
        }
    }

    rpc macsec-clear-secy-statistics {
        if-feature feature-list:HAVE_MACSEC;
        description "Clears MACsec secy statistics";
    }

}
