/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-macsec-types.yang
*
*/

module ipi-macsec-types {

    yang-version 1.1;

    namespace   "http://www.ipinfusion.com/yang/ocnos/ipi-macsec-types";

    prefix "ipi-macsec-types";

    organization
        "IP Infusion Inc.";

    contact
        "Address: 3965 Freedom Circle, Suite 200, Santa Clara, CA 95054
         Phone: +1 408-400-1900
         E-mail: support@ipinfusion.com
         Web: http://www.ipinfusion.com/";

    description
        "MACsec data types";


    revision "2026-05-11" {
        description "Disable counters that do not increment";
        reference " 0.2.6.";
    }

    revision "2026-04-30" {
        description "Fixed previous revision";
        reference " 0.2.5.";
    }

    revision "2026-04-28" {
        description "Removed QKD enum values";
        reference " 0.2.4.";
    }

    revision "2026-04-15" {
        description "Added debug mka type";
        reference " 0.2.3.";
    }

    revision "2026-04-14" {
        description "Add xpn cipher suite values";
        reference " 0.2.2.";
    }

    revision "2026-02-16" {
        description "Add new runtime attributes related to show commands";
        reference " 0.2.1.";
    }

    revision "2025-10-24" {
        description "Add new types to support MKA pre-shared-key";
        reference " 0.2.0.";
    }

    revision "2022-11-22" {
        description "Initial Version";
        reference " 0.1.0.";
    }



    typedef  macsec_port_number_t {
        type uint16 {
             range 0..65535;
        }
        description "The port-number type represents a 16-bit port number of an Internet
                    transport-layer protocol such as UDP, TCP, DCCP, or SCTP.";
    }

    typedef  macsec_ca_session_state_t {
        type enumeration {
            enum INIT {
                value 0;
                description "Default state";
            }
            enum IN-PROGRESS {
                value 1;
                description "MACsec CA session connecting with KaY server";
            }
            enum ACTIVE {
                value 2;
                description "MACsec CA session connected with KaY server";
            }
            enum INACTIVE {
                value 3;
                description "MACsec CA session disconnected from KaY server";
            }
        }
        description "type definition for MACSEC_CA_SESSION_STATE_T";
    }

    typedef  macsec_ca_interface_association_state_t {
        type enumeration {
            enum NONE {
                value 0;
                description "Default state";
            }
            enum DISSOCIATED {
                value 1;
                description "MACsec CA Dissociated from interface";
            }
            enum ASSOCIATED {
                value 2;
                description "MACsec CA Assocaited with interface";
            }
        }
        description "type definition for MACSEC_CA_INTERFACE_ASSOCIATION_STATE_T";
    }

    typedef  macsec_sa_programming_state_t {
        type enumeration {
            enum INIT {
                value 1;
                description "Was not programmed";
            }
            enum PROGRAMMED_IN_DATA_PLANE {
                value 2;
                description "Secure Association (SA) programmed in data plane";
            }
            enum PROGRAMMED_IN_CONTROL_PLANE {
                value 3;
                description "Secure Association (SA) programmed in control plane";
            }
        }
        description "type definition for MACSEC_SA_PROGRAMMING_STATE_T";
    }

    typedef  macsec_security_mode_t {
        type enumeration {
            enum pre-shared-cak {
                value 3;
                description "MKA pre-shared key";
            }
        }
        description "type definition for MACSEC_SECURITY_MODE_T";
    }

    typedef  macsec_cipher_suite_t {
        type enumeration {
            enum gcm-aes-128 {
                value 1;
                description "AES-128-CMAC algorithm";
            }
            enum gcm-aes-256 {
                value 2;
                description "AES-256-CMAC algorithm";
            }
            enum gcm-aes-xpn-128 {
                value 3;
                description "AES-128-CMAC algorithm for XPN";
            }
            enum gcm-aes-xpn-256 {
                value 4;
                description "AES-256-CMAC algorithm for XPN";
            }
        }
        description "type definition for MACSEC_CIPHER_SUITE_T";
    }

    typedef  macsec_transport_protocol_t {
        type enumeration {
            enum http {
                value 1;
                description "TCP transport";
            }
            enum https {
                value 2;
                description "SSL/TLS secure transport";
            }
        }
        description "type definition for MACSEC_TRANSPORT_PROTOCOL_T";
    }

    typedef  macsec_hex_string_ckn_t {
        type string {
            length 2..64;
            pattern "([0-9A-Fa-f]{2})+";
        }
        description "type definition for MACSEC_HEX_STRING_CKN_T";
    }

    typedef  macsec_hex_string_cak_t {
        type string {
            length 32..64;
            pattern "([0-9A-Fa-f]{32}|[0-9A-Fa-f]{64})";
        }
        description "type definition for MACSEC_HEX_STRING_CAK_T";
    }

    typedef  macsec_ca_error_reason_t {
        type enumeration {
            enum no-error {
                value 0;
                description "None";
            }
            enum cak-mismatch {
                value 1;
                description "None";
            }
            enum ckn-mismatch {
                value 2;
                description "None";
            }
        }
        description "type definition for MACSEC_CA_ERROR_REASON_T";
    }

    typedef  macsec_ca_traffic_status_t {
        type enumeration {
            enum not-protected {
                value 0;
                description "None";
            }
            enum protected {
                value 1;
                description "None";
            }
        }
        description "type definition for MACSEC_CA_TRAFFIC_STATUS_T";
    }

    typedef  macsec_kay_connection_status_t {
        type enumeration {
            enum init {
                value 1;
                description "None";
            }
            enum operational {
                value 2;
                description "None";
            }
        }
        description "type definition for MACSEC_KAY_CONNECTION_STATUS_T";
    }

    typedef  macsec_mka_debug_t {
        type enumeration {
            enum mka {
                value 1;
                description "MKA";
            }
        }
        description "type definition for MACSEC_MKA_DEBUG_T";
    }

}
