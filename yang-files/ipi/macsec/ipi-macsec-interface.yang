/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-macsec-interface.yang
*
*/

submodule ipi-macsec-interface {

    yang-version 1.1;

    belongs-to  ipi-macsec { prefix ipi-macsec; }

    import feature-list {
        prefix feature-list;
        revision-date 2026-09-15;
    }

    import ipi-interface {
        prefix ipi-interface;
        revision-date 2026-03-10;
    }

    import ietf-yang-types {
        prefix yang;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for MACsec Module interface";


    revision "2026-04-29" {
        description "Disable counters that do not increment";
        reference " 0.2.4.";
    }

    revision "2026-04-15" {
        description "Rename interface key attribute from interface-name to name";
        reference " 0.2.3.";
    }

    revision "2026-03-30" {
        description "Prevent enabling macsec on interfaces that are part of a link aggregation";
        reference " 0.2.2.";
    }

    revision "2026-02-16" {
        description "Add new runtime attributes related to show commands and unhide configuration commands";
        reference " 0.2.1.";
    }

    revision "2025-10-24" {
        description "Added MKA pre-shared-key to macsec";
        reference " 0.2.0.";
    }

    revision "2023-05-16" {
        description "Change macsec-ca-name under interface to if-macsec-ca to fix issue with mode change";
        reference " 0.1.4.";
    }

    revision "2023-03-06" {
        description "Add implicit_delete tag to remove interface object when macsec-ca-name is removed";
        reference " 0.1.3.";
    }

    revision "2023-02-15" {
        description "Add dependecy tag for creation/delition of macsec objects";
        reference " 0.1.2.";
    }

    revision "2023-01-05" {
        description "Change macsec-ca under interface to macsec-ca-name";
        reference " 0.1.1.";
    }

    revision "2022-11-22" {
        description "Initial Version";
        reference " 0.1.0.";
    }

    grouping macsec-interface-config {
        description
            "Connectivity Association to interface config parameters";
        leaf name  {
            type  leafref {
                path  "/ipi-interface:interfaces/ipi-interface:interface/ipi-interface:name";
            }
            description "The interface name to configure the CA parameters.";
        } // END of name definition.

        leaf if-macsec-ca  {
            type  leafref {
                path  "/ipi-macsec:macsec/ipi-macsec:connectivity-associations/ipi-macsec:connectivity-association/ipi-macsec:ca-name";
            }
            description "Connectivity Association name";
        } // END of if-macsec-ca definition.

    } // END of macsec-interface-config definition.
    grouping interface-macsec-statistic-sa-egress-extended-state {
        description
            "macsec interface statistic per secure association";
        leaf pkts-encrypted  {
            type  yang:counter32;
            description "Number of integrity protected and encrypted packets for this
                        transmitting SA";
        } // END of pkts-encrypted definition.

        leaf pkts-protected  {
            type  yang:counter32;
            description "Number of integrity protected but not encrypted packets for this
                        transmitting SA";
        } // END of pkts-protected definition.

    } // END of interface-macsec-statistic-sa-egress-extended-state definition.
    grouping interface-macsec-statistic-sa-egress-state {
        description
            "macsec interface statistic per secure association";
        leaf out-pkts-encrypted-protected  {
            type  yang:counter32;
            description "Number of egress encrypted packets";
        } // END of out-pkts-encrypted-protected definition.

        leaf out-pkts-too-long  {
            type  yang:counter32;
            description "Number of egress packets to long";
        } // END of out-pkts-too-long definition.

        leaf out-pkts-sa-not-inuse  {
            type  yang:counter32;
            description "Number of egress packets with SA not inuse";
        } // END of out-pkts-sa-not-inuse definition.

        leaf out-octets-encrypted-protected  {
            type  yang:counter32;
            description "Number of egress ecnrypted octets";
        } // END of out-octets-encrypted-protected definition.

    } // END of interface-macsec-statistic-sa-egress-state definition.
    grouping interface-macsec-statistic-sa-egress-top {
        description
            "macsec interface statistic sa egress top grouping";
        container egress {
            config false;
            description
                "macsec interface statistics sa egress top container";
            container state {
                config false;
                description
                    "macsec interface statistics sa egress state parameters";
                uses interface-macsec-statistic-sa-egress-state;
                uses interface-macsec-statistic-sa-egress-extended-state;
            } // END of state-container definition.
        } // END of egress-container definition.
    } // END of interface-macsec-statistic-sa-egress-top definition.
    grouping interface-macsec-statistic-sa-ingress-extended-state {
        description
            "macsec interface statistic per secure association";
        leaf pkts-unused-sa  {
            if-feature feature-list:HAVE_MACSEC_J2P_SEC_TAG_VALIDATE_STRICT_MODE_NOT_SET;
            type  yang:counter32;
            description "Number of ingress unencrypted packets on this SA which is not
                        currently in use";
        } // END of pkts-unused-sa definition.

        leaf pkts-not-using-sa  {
            type  yang:counter32;
            description "Number of ingress packets discarded or encrypted for this SA which is
                        not currently in use";
        } // END of pkts-not-using-sa definition.

        leaf pkts-not-valid  {
            type  yang:counter32;
            description "Number of ingress discarded packets that are not valid and encrypted";
        } // END of pkts-not-valid definition.

        leaf pkts-invalid  {
            if-feature feature-list:HAVE_MACSEC_J2P_SEC_TAG_VALIDATE_STRICT_MODE_NOT_SET;
            type  yang:counter32;
            description "Number of ingress packets that are invalid";
        } // END of pkts-invalid definition.

        leaf pkts-ok  {
            type  yang:counter32;
            description "Number of ingress successfully validated packets";
        } // END of pkts-ok definition.

    } // END of interface-macsec-statistic-sa-ingress-extended-state definition.
    grouping interface-macsec-statistic-sa-ingress-state {
        description
            "macsec interface statistic per secure association";
        leaf in-pkts-delayed  {
            type  yang:counter32;
            description "Number of ingress delayed packets, whose PN is lower than the current
                        lower-bound replay-protection PN";
        } // END of in-pkts-delayed definition.

        leaf in-pkts-late  {
            type  yang:counter32;
            description "Number of ingress late packets";
        } // END of in-pkts-late definition.

        leaf in-pkts-ok  {
            type  yang:counter32;
            description "Number of ingress successfully decrypted packets";
        } // END of in-pkts-ok definition.

        leaf in-pkts-invalid  {
            type  yang:counter32;
            description "Number of ingress invalid packets";
        } // END of in-pkts-invalid definition.

        leaf in-pkts-not-valid  {
            type  yang:counter32;
            description "Number of ingress not valid packets";
        } // END of in-pkts-not-valid definition.

        leaf in-pkts-not-using-sa  {
            type  yang:counter32;
            description "Number of ingress packets discarded because not using current SA";
        } // END of in-pkts-not-using-sa definition.

        leaf in-pkts-unused-sa  {
            type  yang:counter32;
            description "Number of ingress unencrypted packets unused by current SA";
        } // END of in-pkts-unused-sa definition.

        leaf in-pkts-unchecked  {
            type  yang:counter32;
            description "Number of ingress packet that were not fully checked/validated by the
                        current SA";
        } // END of in-pkts-unchecked definition.

        leaf in-octets-decrypted  {
            type  yang:counter32;
            description "Number of ingress decrypted octets";
        } // END of in-octets-decrypted definition.

        leaf in-octets-validated  {
            type  yang:counter32;
            description "Number of ingress validated octets";
        } // END of in-octets-validated definition.

    } // END of interface-macsec-statistic-sa-ingress-state definition.
    grouping interface-macsec-statistic-sa-ingress-top {
        description
            "macsec interface statistic sa ingress top grouping";
        container ingress {
            config false;
            description
                "macsec interface statistics security-entity ingress top container";
            container state {
                config false;
                description
                    "macsec interface statistics security-entity ingress state parameters";
                uses interface-macsec-statistic-sa-ingress-state;
                uses interface-macsec-statistic-sa-ingress-extended-state;
            } // END of state-container definition.
        } // END of ingress-container definition.
    } // END of interface-macsec-statistic-sa-ingress-top definition.
    grouping interface-macsec-statistic-sa-state {
        description
            "macsec interface statistic";
        leaf sa-identifier  {
            type  uint32;
            description "Association number";
        } // END of sa-identifier definition.

    } // END of interface-macsec-statistic-sa-state definition.
    grouping interface-macsec-statistic-sa-top {
        description
            "macsec interface statistic per secure association top grouping";
        container secure-associations {
            config false;
            description
                "macsec interface statistics secure association top container";

            list secure-association {
                key "sa-identifier";
                config false;
                description
                    "MACsec sessions secure association list";
                leaf sa-identifier  {
                    type  leafref {
                        path  "../state/sa-identifier";
                    }
                    description "Association number";
                } // END of sa-identifier definition.

                container state {
                    config false;
                    description
                        "State parameters of secure association";
                    uses interface-macsec-statistic-sa-state;
                } // END of state-container definition.
                uses interface-macsec-statistic-sa-ingress-top;
                uses interface-macsec-statistic-sa-egress-top;
            } // End of secure-association-list
        } // END of secure-associations-container definition.
    } // END of interface-macsec-statistic-sa-top definition.
    grouping interface-macsec-statistic-secy-egress-extended-state {
        description
            "macsec interface statistic";
        leaf tx-pkts-encrypted  {
            type  yang:counter32;
            description "Number of egress integrity protected and encrypted packets on the
                        transmitting SC";
        } // END of tx-pkts-encrypted definition.

        leaf tx-octets-encrypted  {
            type  yang:counter32;
            description "Number of egress integrity protected and encrypted octets on the
                        transmitting SC";
        } // END of tx-octets-encrypted definition.

        leaf tx-pkts-dropped  {
            type  yang:counter32;
            description "Number of egress dropped packets on the transmitting SC";
        } // END of tx-pkts-dropped definition.

        leaf tx-unctrl-port-octets  {
            type  yang:counter32;
            description "This is the sum of all the octets of the frames transmitted by the
                        Uncontrolled Port";
        } // END of tx-unctrl-port-octets definition.

        leaf tx-unctrl-port-pkts-unicast  {
            type  yang:counter32;
            description "This is the sum of all the unicast frames transmitted by the
                        Uncontrolled Port";
        } // END of tx-unctrl-port-pkts-unicast definition.

        leaf tx-unctrl-port-pkts-multicast  {
            type  yang:counter32;
            description "This is the sum of all the multicast frames transmitted by the
                        Uncontrolled Port";
        } // END of tx-unctrl-port-pkts-multicast definition.

        leaf tx-unctrl-port-pkts-broadcast  {
            type  yang:counter32;
            description "This is the sum of all the broadcast frames transmitted by the
                        Uncontrolled Port";
        } // END of tx-unctrl-port-pkts-broadcast definition.

        leaf tx-unctrl-port-pkts-error  {
            type  yang:counter32;
            description "This is the sum of all the frames transmitted by the Uncontrolled Port
                        that exceed the MTU size";
        } // END of tx-unctrl-port-pkts-error definition.

        leaf tx-ctrl-port-octets  {
            type  yang:counter32;
            description "This is the sum of all the octets of the frames transmitted by the
                        Controlled Port";
        } // END of tx-ctrl-port-octets definition.

        leaf tx-ctrl-port-pkts-unicast  {
            type  yang:counter32;
            description "This is the sum of all the unicast frames transmitted by the
                        Controlled Port";
        } // END of tx-ctrl-port-pkts-unicast definition.

        leaf tx-ctrl-port-pkts-multicast  {
            type  yang:counter32;
            description "This is the sum of all the multicast frames transmitted by the
                        Controlled Port";
        } // END of tx-ctrl-port-pkts-multicast definition.

        leaf tx-ctrl-port-pkts-broadcast  {
            type  yang:counter32;
            description "This is the sum of all the broadcast frames transmitted by the
                        Controlled Port";
        } // END of tx-ctrl-port-pkts-broadcast definition.

        leaf tx-ctrl-port-pkts-error  {
            type  yang:counter32;
            description "This is the sum of all the frames transmitted by the Controlled Port
                        that contains some error";
        } // END of tx-ctrl-port-pkts-error definition.

        leaf tx-secy-untagged-pkts  {
            type  yang:counter32;
            description "Number of egress packets without the MAC security tag (SecTAG)";
        } // END of tx-secy-untagged-pkts definition.

        leaf tx-secy-too-long-pkts  {
            type  yang:counter32;
            description "Number of egress packets discarded because the packet length is
                        greater than the MTU of the Common Port interface";
        } // END of tx-secy-too-long-pkts definition.

        leaf tx-mgmt-pkts  {
            type  yang:counter32;
            description "This is the sum of all the management and KaY frames transmitted by
                        the Uncontrolled Port";
        } // END of tx-mgmt-pkts definition.

    } // END of interface-macsec-statistic-secy-egress-extended-state definition.
    grouping interface-macsec-statistic-secy-egress-state {
        description
            "macsec interface statistic";
        leaf out-pkts-transform-error  {
            type  yang:counter32;
            description "Number of egress packets with SA transformation errors";
        } // END of out-pkts-transform-error definition.

        leaf out-pkts-control  {
            type  yang:counter32;
            description "Number of egress control plane packets";
        } // END of out-pkts-control definition.

        leaf out-pkts-untagged  {
            type  yang:counter32;
            description "Number of untagged egress packets";
        } // END of out-pkts-untagged definition.

    } // END of interface-macsec-statistic-secy-egress-state definition.
    grouping interface-macsec-statistic-secy-egress-top {
        description
            "macsec interface statistic security entity egress top grouping";
        container egress {
            config false;
            description
                "macsec interface statistics security-entity egress top container";
            container state {
                config false;
                description
                    "macsec interface statistics security-entity egress state parameters";
                uses interface-macsec-statistic-secy-egress-state;
                uses interface-macsec-statistic-secy-egress-extended-state;
            } // END of state-container definition.
        } // END of egress-container definition.
    } // END of interface-macsec-statistic-secy-egress-top definition.
    grouping interface-macsec-statistic-secy-ingress-extended-state {
        description
            "macsec interface statistic extended";
        leaf rx-pkts-unused-sa  {
            if-feature feature-list:HAVE_MACSEC_J2P_SEC_TAG_VALIDATE_STRICT_MODE_NOT_SET;
            type  yang:counter32;
            description "This is the sum of ingress unencrypted packets for all the SAs which
                        are not currently in use";
        } // END of rx-pkts-unused-sa definition.

        leaf rx-pkts-not-using-sa  {
            type  yang:counter32;
            description "This is the sum of ingress packets discarded or encrypted for all the
                        SAs which are not currently in use";
        } // END of rx-pkts-not-using-sa definition.

        leaf rx-pkts-late  {
            type  yang:counter32;
            description "Number of ingress packets discarded due invalid PN when replay
                        protected is active";
        } // END of rx-pkts-late definition.

        leaf rx-pkts-not-valid  {
            type  yang:counter32;
            description "This is the sum of ingress discarded packets that are not valid and
                        encrypted";
        } // END of rx-pkts-not-valid definition.

        leaf rx-pkts-invalid  {
            if-feature feature-list:HAVE_MACSEC_J2P_SEC_TAG_VALIDATE_STRICT_MODE_NOT_SET;
            type  yang:counter32;
            description "This is the sum of ingress packets that are invalid";
        } // END of rx-pkts-invalid definition.

        leaf rx-pkts-delayed  {
            type  yang:counter32;
            description "Number of ingress packets with the condition that the PN of the
                        packets is lower than the lower bound replay protection PN";
        } // END of rx-pkts-delayed definition.

        leaf rx-pkts-unchecked  {
            type  yang:counter32;
            description "Number of ingress packets that are unchecked because validation is
                        disabled or enabled but ICV has failed";
        } // END of rx-pkts-unchecked definition.

        leaf rx-pkts-ok  {
            type  yang:counter32;
            description "The sum of all ingress validated packets";
        } // END of rx-pkts-ok definition.

        leaf rx-octets-validated  {
            type  yang:counter32;
            description "The sum of all ingress validated packets that were integrity protected
                        but not encrypted";
        } // END of rx-octets-validated definition.

        leaf rx-octets-decrypted  {
            type  yang:counter32;
            description "The sum of all ingress validated packets that were integrity protected
                        and encrypted";
        } // END of rx-octets-decrypted definition.

        leaf rx-tcam-hit-cntr  {
            type  yang:counter32;
            description "Number of ingress packets that hit TCAM rule";
        } // END of rx-tcam-hit-cntr definition.

        leaf rx-flow-tcam-miss-cntr  {
            type  yang:counter32;
            description "Number of ingress packets when no TCAM rule is hit for the port";
        } // END of rx-flow-tcam-miss-cntr definition.

        leaf rx-sc-tcam-miss-cntr  {
            type  yang:counter32;
            description "Number of ingress packets when no TCAM rule is hit for the port";
        } // END of rx-sc-tcam-miss-cntr definition.

        leaf rx-pkts-dropped  {
            type  yang:counter32;
            description "Number of ingress packets dropped for any reasons";
        } // END of rx-pkts-dropped definition.

        leaf rx-unctrl-port-octets  {
            type  yang:counter32;
            description "This is the sum of all the octets of the frames received by the
                        Uncontrolled Port";
        } // END of rx-unctrl-port-octets definition.

        leaf rx-unctrl-port-pkts-unicast  {
            type  yang:counter32;
            description "This is the sum of all the unicast frames received by the Uncontrolled
                        Port";
        } // END of rx-unctrl-port-pkts-unicast definition.

        leaf rx-unctrl-port-pkts-multicast  {
            type  yang:counter32;
            description "This is the sum of all the multicast frames received by the
                        Uncontrolled Port";
        } // END of rx-unctrl-port-pkts-multicast definition.

        leaf rx-unctrl-port-pkts-broadcast  {
            type  yang:counter32;
            description "This is the sum of all the broadcast frames received by the
                        Uncontrolled Port";
        } // END of rx-unctrl-port-pkts-broadcast definition.

        leaf rx-unctrl-port-discards  {
            if-feature feature-list:HAVE_MACSEC_J2P_SEC_TAG_VALIDATE_STRICT_MODE_NOT_SET;
            type  yang:counter32;
            description "This is the sum of all discarded frames in the Uncontrolled Port";
        } // END of rx-unctrl-port-discards definition.

        leaf rx-ctrl-port-octets  {
            type  yang:counter32;
            description "This is the sum of all the octets of the frames received by the
                        Controlled Port";
        } // END of rx-ctrl-port-octets definition.

        leaf rx-ctrl-port-pkts-unicast  {
            type  yang:counter32;
            description "This is the sum of all the unicast frames received by the Controlled
                        Port";
        } // END of rx-ctrl-port-pkts-unicast definition.

        leaf rx-ctrl-port-pkts-multicast  {
            type  yang:counter32;
            description "This is the sum of all the multicast frames received by the Controlled
                        Port";
        } // END of rx-ctrl-port-pkts-multicast definition.

        leaf rx-ctrl-port-pkts-broadcast  {
            type  yang:counter32;
            description "This is the sum of all the broadcast frames received by the Controlled
                        Port";
        } // END of rx-ctrl-port-pkts-broadcast definition.

        leaf rx-ctrl-port-discards  {
            type  yang:counter32;
            description "This is the sum of all discarded frames in the Controlled Port";
        } // END of rx-ctrl-port-discards definition.

        leaf rx-ctrl-port-errors  {
            type  yang:counter32;
            description "This is the sum of all packets with error received by Controlled Port";
        } // END of rx-ctrl-port-errors definition.

        leaf rx-secy-untagged-pkts  {
            if-feature feature-list:HAVE_MACSEC_J2P_SEC_TAG_VALIDATE_STRICT_MODE_NOT_SET;
            type  yang:counter32;
            description "The number of received packets without the MAC security tag (SecTAG)";
        } // END of rx-secy-untagged-pkts definition.

        leaf rx-secy-no-tag-pkts  {
            type  yang:counter32;
            description "The number of received packets discarded without the MAC security tag
                        (SecTAG)";
        } // END of rx-secy-no-tag-pkts definition.

        leaf rx-secy-bad-tag-pkts  {
            type  yang:counter32;
            description "The number of received packets discarded with an invalid SecTAG or a
                        zero value PN or an invalid ICV.";
        } // END of rx-secy-bad-tag-pkts definition.

        leaf rx-secy-unknown-sci-pkts  {
            if-feature feature-list:HAVE_MACSEC_J2P_SEC_TAG_VALIDATE_STRICT_MODE_NOT_SET;
            type  yang:counter32;
            description "The number of received packets with unknown SCI";
        } // END of rx-secy-unknown-sci-pkts definition.

        leaf rx-secy-no-sci-pkts  {
            type  yang:counter32;
            description "The number of received packets discarded with unknown SCI information";
        } // END of rx-secy-no-sci-pkts definition.

        leaf rx-secy-overrun-pkts  {
            if-feature feature-list:HAVE_MACSEC_J2P_SEC_TAG_VALIDATE_STRICT_MODE_NOT_SET;
            type  yang:counter32;
            description "Number of ingress overrun packets";
        } // END of rx-secy-overrun-pkts definition.

        leaf rx-mgmt-pkts  {
            type  yang:counter32;
            description "Number of ingress management packets";
        } // END of rx-mgmt-pkts definition.

        leaf rx-unctrl-port-kay-pkts  {
            type  yang:counter32;
            description "The number of KaY packets received for MACSec flow";
        } // END of rx-unctrl-port-kay-pkts definition.

    } // END of interface-macsec-statistic-secy-ingress-extended-state definition.
    grouping interface-macsec-statistic-secy-ingress-state {
        description
            "macsec interface statistic";
        leaf in-pkts-transform-error  {
            type  yang:counter32;
            description "Number of ingress packets with SA transformation errors";
        } // END of in-pkts-transform-error definition.

        leaf in-pkts-control  {
            type  yang:counter32;
            description "Number of ingress control plane packets";
        } // END of in-pkts-control definition.

        leaf in-pkts-untagged  {
            type  yang:counter32;
            description "Number of untagged ingress packets";
        } // END of in-pkts-untagged definition.

        leaf in-pkts-no-tag  {
            type  yang:counter32;
            description "Number of ingress packets with no sectag header";
        } // END of in-pkts-no-tag definition.

        leaf in-pkts-badtag  {
            type  yang:counter32;
            description "Number of ingress packets with error in sectag header";
        } // END of in-pkts-badtag definition.

        leaf in-pkts-no-sci  {
            type  yang:counter32;
            description "Number of ingress packets with no SCI";
        } // END of in-pkts-no-sci definition.

        leaf in-pkts-unknown-sci  {
            type  yang:counter32;
            description "Number of ingress packets with unknown sci";
        } // END of in-pkts-unknown-sci definition.

        leaf in-pkts-tagged-ctrl  {
            type  yang:counter32;
            description "Number of ingress macsec tagged control plane packets";
        } // END of in-pkts-tagged-ctrl definition.

    } // END of interface-macsec-statistic-secy-ingress-state definition.
    grouping interface-macsec-statistic-secy-ingress-top {
        description
            "macsec interface statistic security entity ingress top grouping";
        container ingress {
            config false;
            description
                "macsec interface statistics security-entity ingress top container";
            container state {
                config false;
                description
                    "macsec interface statistics security-entity ingress state parameters";
                uses interface-macsec-statistic-secy-ingress-state;
                uses interface-macsec-statistic-secy-ingress-extended-state;
            } // END of state-container definition.
        } // END of ingress-container definition.
    } // END of interface-macsec-statistic-secy-ingress-top definition.
    grouping interface-macsec-statistic-secy-top {
        description
            "macsec interface statistic security entity top grouping";
        container security-entity {
            config false;
            description
                "macsec interface statistics  security-entity top container";
            uses interface-macsec-statistic-secy-ingress-top;
            uses interface-macsec-statistic-secy-egress-top;
        } // END of security-entity-container definition.
    } // END of interface-macsec-statistic-secy-top definition.
    grouping interface-macsec-statistic-top {
        description
            "macsec interface statistic per secure association top grouping";
        container statistics {
            config false;
            description
                "macsec interface statistics top container";
            uses interface-macsec-statistic-secy-top;
            uses interface-macsec-statistic-sa-top;
        } // END of statistics-container definition.
    } // END of interface-macsec-statistic-top definition.
    grouping macsec-interface-top {
        description
            "Top level container for macsec interface";

        list interface {
            key "name";
            description
                "List of macsec interfaces";
            leaf name  {
                type  leafref {
                    path  "../config/name";
                }
                description "The interface name to configure the macsec parameters.";
            } // END of name definition.

            container config {
                description
                    "Connectivity Association config parameters";
                uses macsec-interface-config;
            } // END of config-container definition.
            container state {
                config false;
                description
                    "Connectivity Association config parameters";
                uses macsec-interface-config;
            } // END of state-container definition.
            uses interface-macsec-statistic-top;
        } // End of interface-list
    } // END of macsec-interface-top definition.

    grouping  interfaces-grouping {
    description
        "Top-level container for macsec interface configuration";
    container interfaces {
        if-feature feature-list:HAVE_MACSEC;
        description
            "Top-level container for macsec interface configuration";
        uses macsec-interface-top;
    } // END of interfaces-container definition.
    } // END of interfaces-grouping definition.


}
