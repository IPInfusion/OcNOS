/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-vrf.yang
*
*/

module ipi-vrf {

    yang-version 1.1;

    namespace   "http://www.ipinfusion.com/yang/ocnos/ipi-vrf";

    prefix "ipi-vrf";

    import ipi-network-instance {
        prefix ipi-network-instance;
        revision-date 2026-08-12;
    }

    import ietf-inet-types {
        prefix inet;
        revision-date 2013-07-15;
    }

    import cml-data-types {
        prefix cml-data-types;
        revision-date 2026-05-15;
    }

    import ietf-yang-types {
        prefix yang;
        revision-date 2013-07-15;
    }

    import ipi-mpls-types {
        prefix ipi-mpls-types;
        revision-date 2026-02-03;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "IPI VRF";


    revision "2026-08-12" {
        description "Added dependentObject tags related to snmp server";
        reference " 0.14.2.";
    }

    revision "2026-04-17" {
        description "Retain evpn-stitching command's helpstring";
        reference " 0.14.1.";
    }

    revision "2026-04-10" {
        description "Make evpn-stitching command as hidden and add evpn stitching as new one";
        reference " 0.14.0.";
    }

    revision "2026-02-03" {
        description "Added not-applicable as a possible value for attribute Action-Type in FTN entry";
        reference " 0.13.5.";
    }

    revision "2025-09-23" {
        description "Added error-message tag under when tag for enable-stitching attribute";
        reference " 0.13.4.";
    }

    revision "2025-09-11" {
        description "Add support for EVPN VXLAN stitching feature";
        reference " 0.13.3.";
    }

    revision "2025-09-07" {
        description "Added maximum vrf counter";
        reference " 0.13.2.";
    }

    revision "2025-07-08" {
        description "Added streaming telemetry support";
        reference " 0.13.1.";
    }

    revision "2025-06-19" {
        description "Add a global and a counters container with attributes to display the number of VRFs in use";
        reference " 0.13.0.";
    }

    revision "2025-03-21" {
        description "Added the flags for DNS Client for sku compilation error";
        reference " 0.12.5.";
    }

    revision "2025-01-02" {
        description "Added dependentObject tag related to dns-client";
        reference " 0.12.4.";
    }

    revision "2024-12-24" {
        description "Added support to configure MTU under ip vrf";
        reference " 0.12.3.";
    }

    revision "2024-12-06" {
        description "Added new attribute to suppress operator logs for services";
        reference " 0.12.2.";
    }

    revision "2024-12-05" {
        description "Lenght validation is not happening for vrf attribute";
        reference " 0.12.1.";
    }

    revision "2024-09-19" {
        description "Added dependentObject tags related to static-routing";
        reference " 0.12.0.";
    }

    revision "2024-09-18" {
        description "Added an attribute for dscp preserve per vrf";
        reference " 0.11.0.";
    }

    revision "2024-03-11" {
        description "Add force-unset to evpn-layer3-network-id";
        reference " 0.10.0.";
    }

    revision "2023-08-08" {
        description "Added a dependentObject tag related to the smux port";
        reference " 0.9.2.";
    }

    revision "2023-05-04" {
        description "Added a dependentObject tag related to the ip address and ipv6 address";
        reference " 0.9.1.";
    }

    revision "2023-04-21" {
        description "Added a when tag in vrf container with config/vrf-name";
        reference " 0.9.0.";
    }

    revision "2023-03-20" {
        description "Added missing implicit_delete tag with respect to snmp context";
        reference " 0.8.3.";
    }

    revision "2023-02-28" {
        description "Fix VRF removal not cleaning corresponding arp entries";
        reference " 0.8.2.";
    }

    revision "2023-01-20" {
        description "Added helpstring for tunnel-select-policy";
        reference " 0.8.1.";
    }

    revision "2022-12-20" {
        description "Added missing cliprependstr tags";
        reference " 0.8.0.";
    }

    revision "2022-10-11" {
        description "Added HOSTPD flag in dependentObject tag related to the SNMP";
        reference " 0.7.3.";
    }

    revision "2022-09-13" {
        description "Added support for SNMP context";
        reference " 0.7.2.";
    }

    revision "2022-08-10" {
        description "Updated helpstring for ip parameter";
        reference " 0.7.1.";
    }

    revision "2022-07-28" {
        description "Added dependentObject to delete RIPng VRF configurations";
        reference " 0.7.0.";
    }

    revision "2022-07-13" {
        description "Deleted DB-triggers that add lo.vrf interfaces on creation of VRF";
        reference " 0.6.1.";
    }

    revision "2022-06-01" {
        description "Updated the yang file with feature";
        reference " 0.6.0.";
    }

    revision "2022-04-28" {
        description "Support for EVPN-MPLS IRB";
        reference " 0.5.0.";
    }

    revision "2021-09-03" {
        description "Update descriptions of attribute";
        reference " 0.4.0.";
    }

    revision "2021-01-27" {
        description "layer-3 network id attribute enabled";
        reference " 0.3.0.";
    }

    revision "2020-12-15" {
        description "Change to have data-types in lower case instead of camel case";
        reference " 0.2.0.";
    }

    revision "2020-08-11" {
        description "Datamodel restructuring";
        reference " 0.1.0.";
    }

    grouping network-instance-vrf-snmp-config {
        description
            "SNMP configuration for VRF";
        leaf snmp-context-name  {
            type  string {
                length "1..32";
                pattern "[^?' =,>|]+";
            }
            description "Use this attribute to set the SNMP context for VRF.";
        } // END of snmp-context-name definition.

    } // END of network-instance-vrf-snmp-config definition.
    grouping network-instance-vrf-snmp-top {
        description
            "SNMP configuration for VRF";
        container snmp {
            if-feature feature-list:HAVE_SNMP;
            description
                "SNMP configuration data for VRF";
            container config {
                description
                    "SNMP configuration data for VRF";
                uses network-instance-vrf-snmp-config;
            } // END of config-container definition.
            container state {
                config false;
                description
                    "Operational state data for SNMP configuration";
                uses network-instance-vrf-snmp-config;
            } // END of state-container definition.
        } // END of snmp-container definition.
    } // END of network-instance-vrf-snmp-top definition.
    grouping network-instance-vrf-config {
        description
            "Configuration item grouping for VRF";
        leaf vrf-name  {
            type  leafref {
                path  "/ipi-network-instance:network-instances/ipi-network-instance:network-instance/ipi-network-instance:instance-name";
            }
            description "VRF Name";
        } // END of vrf-name definition.

        leaf description  {
            type  cml-data-types:cml_line_t {
                length "1..1965";
            }
            description "VRF-specific description";
        } // END of description definition.

        leaf tunnel-select-policy  {
            if-feature feature-list:HAVE_SERVICE_MAPPING_OR_HAVE_SRV6;
            type  string {
                length "1..127";
                pattern "[^?' =,>|]+";
            }
            description "tunnel policy to be configured";
        } // END of tunnel-select-policy definition.

        leaf lsp-encap-dscp-preserve  {
            if-feature feature-list:HAVE_MPLS;
            if-feature feature-list:HAVE_DUNE;
            type  ipi-mpls-types:mpls_dscp_preserve_state_t;
            description "Enable or disable dscp preserve on the VRF";
        } // END of lsp-encap-dscp-preserve definition.

        leaf router-id  {
            type  inet:ipv4-address;
            description "VRF Router ID";
        } // END of router-id definition.

        leaf evpn-layer3-network-id  {
            if-feature feature-list:HAVE_BGP_EVPN;
            if-feature feature-list:HAVE_NVO;
            type  uint32 {
                 range "1..16777215"  {
                    description "1..16777215: Supported range 1 - 16777215";
                 }
            }
            description "L3 EVPN Identifier";
        } // END of evpn-layer3-network-id definition.

        leaf mvpn-spmsi-ipv4-prefix  {
            if-feature feature-list:HAVE_BGP_MVPN;
            type  cml-data-types:cml_ipv4_addr_prefix_t;
            description "This attribute is used to configure IP address prefix for S-PMSI
                        static IP addresses per VRF.";
        } // END of mvpn-spmsi-ipv4-prefix definition.

        leaf mtu  {
            if-feature feature-list:HAVE_BGP_EVPN;
            if-feature feature-list:HAVE_NVO;
            type  uint32 {
                 range "64..65535"  {
                    description "64..65535: Supported range 64 - 65535";
                 }
            }
            description "This attribute is used to confiure the MTU on VRF";
        } // END of mtu definition.

    } // END of network-instance-vrf-config definition.
    grouping network-instance-vrf-state {
        description
            "State item grouping for VRF";
        leaf vrf-id  {
            type  uint32;
            description "VRF ID";
        } // END of vrf-id definition.

        leaf fib-id  {
            type  uint32;
            description "VRF FIB ID";
        } // END of fib-id definition.

    } // END of network-instance-vrf-state definition.
    grouping vrf-counters-state {
        description
            "Grouping for VRF counters attributes";
        leaf total-vrfs  {
            type  yang:counter32;
            description "Total VRFs configured";
        } // END of total-vrfs definition.

        leaf maximum-vrfs  {
            type  yang:counter32;
            description "Maximum VRFs supported";
        } // END of maximum-vrfs definition.

    } // END of vrf-counters-state definition.
    grouping evpn-vxlan-stitching-config {
        description
            "Grouping for EVPN VXLAN stitching";
        leaf enable-stitching  {
            when " /ipi-network-instance:network-instances/ipi-network-instance:network-instance/ipi-network-instance:instance-type = 'vrf' ";
            type  empty;
            mandatory true;
            description "Use this attribute to enable EVPN VXLAN stitching for a specific VRF.";
        } // END of enable-stitching definition.

        leaf translation-l3vni  {
            type  uint32 {
                 range "1..16777215"  {
                    description "1..16777215: Supported range 1 - 16777215";
                 }
            }
            description "Use this attribute to override the current L3VNID with the specified
                        L3VNID for stitching routes towards DCI";
        } // END of translation-l3vni definition.

    } // END of evpn-vxlan-stitching-config definition.
    grouping evpn-stitching-vrf-top {
        description
            "Top level grouping EVPN VXLAN stitching";
        container evpn-vxlan-stitching {
            if-feature feature-list:HAVE_EVPN_VXLAN_STITCHING;
            description
                "EVPN VXLAN stitching main container";
            container config {
                presence "Enable EVPN VXLAN stitching";
                description
                    "Configuration paramters for EVPN VXLAN stitching";
                uses evpn-vxlan-stitching-config;
            } // END of config-container definition.
            container state {
                config false;
                description
                    "Runtime parameters for EVPN VXLAN stitching";
                uses evpn-vxlan-stitching-config;
            } // END of state-container definition.
        } // END of evpn-vxlan-stitching-container definition.
    } // END of evpn-stitching-vrf-top definition.

    grouping  vrf-grouping {
    description
        "Top level container for VRF";
    container vrf {
        if-feature feature-list:HAVE_VRF;
        description
            "Top level container for VRF";
        container config {
            description
                "Config container for VRF";
            uses network-instance-vrf-config;
        } // END of config-container definition.
        container state {
            config false;
            description
                "State container for VRF";
            uses network-instance-vrf-config;
            uses network-instance-vrf-state;
        } // END of state-container definition.
        uses network-instance-vrf-snmp-top;
        uses evpn-stitching-vrf-top;
    } // END of vrf-container definition.
    } // END of vrf-grouping definition.

    grouping  vrf-global-grouping {
    description
        "VRF global container";
    container vrf-global {
        if-feature feature-list:HAVE_VRF;
        description
            "VRF global container";
        container counters {
            config false;
            description
                "Container for the VRF counters";
            uses vrf-counters-state;
        } // END of counters-container definition.
    } // END of vrf-global-container definition.
    } // END of vrf-global-grouping definition.

    augment /ipi-network-instance:network-instances/ipi-network-instance:network-instance {
    when " /ipi-network-instance:network-instances/ipi-network-instance:network-instance/ipi-network-instance:instance-type = 'vrf' or /ipi-network-instance:network-instances/ipi-network-instance:network-instance/ipi-network-instance:instance-type = 'mac-vrf' ";
    // when " ipi-vrf:vrf/config/vrf-name ";
        description
            "Top level container for VRF";
        uses vrf-grouping;
    }

    uses vrf-global-grouping;

    rpc clear-default-router-id {
        if-feature feature-list:HAVE_L3;
        if-feature feature-list:HAVE_VRF;
        description "Use this RPC to update default VRF router ID for all routing processes
                    in the System";
    }

    rpc clear-vrf-router-id {
        if-feature feature-list:HAVE_VRF;
        description "Use this RPC to reset the VRF Router-id";
        input  {
            leaf vrfName  {
                type string;
                mandatory true;
                description "VRF Name";
            }
        }
    }

}
