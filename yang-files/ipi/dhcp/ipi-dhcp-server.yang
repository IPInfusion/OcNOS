/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dhcp-server.yang
*
*/

submodule ipi-dhcp-server {

    yang-version 1.1;

    belongs-to  ipi-dhcp { prefix ipi-dhcp; }

    import feature-list {
        prefix feature-list;
        revision-date 2026-09-15;
    }

    import ipi-network-instance {
        prefix ipi-network-instance;
        revision-date 2026-08-12;
    }

    import ipi-vrf {
        prefix ipi-vrf;
        revision-date 2026-08-12;
    }

    import ipi-interface {
        prefix ipi-interface;
        revision-date 2026-03-10;
    }

    import ietf-inet-types {
        prefix inet;
        revision-date 2013-07-15;
    }

    import cml-data-types {
        prefix cml-data-types;
        revision-date 2026-05-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for DHCP server configuration and operational data";


    revision "2024-08-13" {
        description "Added util function to both the DHCP server max-lease-time and default-lease-time to ensure input is positive integer";
        reference " 0.13.1.";
    }

    revision "2024-07-15" {
        description "Removed pattern tag validation from dhcp server pool name";
        reference " 0.13.0.";
    }

    revision "2024-04-15" {
        description "Added pattern tag to dhcp server pool name";
        reference " 0.12.0.";
    }

    revision "2024-03-05" {
        description "Added when tag to resolve db-sync issue";
        reference " 0.11.0.";
    }

    revision "2023-08-11" {
        description "DHCP option routers support";
        reference " 0.10.0.";
    }

    revision "2023-06-30" {
        description "DHCP Group feature";
        reference " 0.9.0.";
    }

    revision "2023-03-24" {
        description "Added when tag to resolve db-sync issue ";
        reference " 0.8.1.";
    }

    revision "2023-01-23" {
        description "Added implicit-delete to resolve db-sync issues ";
        reference " 0.8.0.";
    }

    revision "2023-01-12" {
        description "Added max-elements tag for IPv4 DHCP server pool and Ipv6 DHCP server pool ";
        reference " 0.7.2.";
    }

    revision "2022-11-16" {
        description "Updated missing cliprependstr tags";
        reference " 0.7.1.";
    }

    revision "2022-11-09" {
        description "Updated vrf grouping and included autoPopulate";
        reference " 0.7.0.";
    }

    revision "2022-09-29" {
        description "Added when tags and removed implicit_delete";
        reference " 0.6.0.";
    }

    revision "2022-09-28" {
        description "Added cli utils function to update the vrfname as default for config mode CLI";
        reference " 0.5.0.";
    }

    revision "2022-09-22" {
        description "Added implicit_delete tags for VRF objectlist";
        reference " 0.4.0.";
    }

    revision "2022-09-16" {
        description "Moved cli-utils function inside cli-tag since its required only from CLI.";
        reference " 0.3.0.";
    }

    revision "2022-09-14" {
        description "DHCP Server IPv6 Prefix option included";
        reference " 0.2.0.";
    }

    revision "2022-08-04" {
        description "DHCP Server-Initial Version";
        reference " 0.1.0.";
    }

    grouping dhcp-server-vrfs-config {
        description
            "Grouping for VRF specific attributes";
        leaf vrf-name  {
            type  leafref {
                path  "/ipi-network-instance:network-instances/ipi-network-instance:network-instance/ipi-vrf:vrf/ipi-vrf:config/ipi-vrf:vrf-name";
            }
            description "VRF name associated with this instance.";
        } // END of vrf-name definition.

    } // END of dhcp-server-vrfs-config definition.
    grouping dhcp-server-global-config {
        description
            "DHCP server global configurations";
        leaf max-lease-time  {
            type  int32;
            units "seconds";
            default "86400";
            description "Maximum length in seconds that will be assigned to a lease.If not
                        defined, the default maximum lease time is 86400.";
        } // END of max-lease-time definition.

        leaf default-lease-time  {
            type  int32;
            units "seconds";
            default "86400";
            description "Length in seconds that will be assigned to a lease if the client
                        requesting the lease does not ask for a specific expiration time. The
                        default is 86400";
        } // END of default-lease-time definition.

    } // END of dhcp-server-global-config definition.
    grouping dhcp-server-v6-global-config {
        description
            "DHCP server global configurations";
        leaf rapid-commit  {
            type  empty;
            description "Option enables the DHCP Client to obtain configuration parameters from
                        the server through a rapid two message exchange (solicit and reply).";
        } // END of rapid-commit definition.

        leaf preference  {
            type  empty;
            description "Use this to configure preference option in dhcp server.";
        } // END of preference definition.

    } // END of dhcp-server-v6-global-config definition.
    grouping dhcp-server-pool-config {
        description
            "Grouping for dhcp pool configurations";
        leaf pool-name  {
            type  string {
                length "1..63";
                pattern "[^?' =,>|]+";
            }
            description "IPv4 DHCP Server address pool name";
        } // END of pool-name definition.

        leaf host-name  {
            type  string {
                length "1..63";
                pattern "[^?' =,>|]+";
            }
            description "IPv4 DHCP Server option to provide hostname details to a DHCP client";
        } // END of host-name definition.

        leaf routers  {
            type  inet:ipv4-address;
            description "IPv4 DHCP Server option to provide routers details to a DHCP client";
        } // END of routers definition.

        leaf-list ntp-server  {
            type  inet:ipv4-address;
            description "IPv4 DHCP Server option to provide ntp-server details to a DHCP client";
        } // END of ntp-server definition.

        leaf boot-file  {
            type  string {
                length "1..63";
                pattern "[^?' =,>|]+";
            }
            description "IPv4 DHCP Server option to provide boot-file details to a DHCP client";
        } // END of boot-file definition.

        leaf tftp-server  {
            type  inet:ipv4-address;
            description "IPv4 DHCP Server option to provide tftp-server details to a DHCP
                        client";
        } // END of tftp-server definition.

        leaf-list log-server  {
            type  inet:ipv4-address;
            description "IPv4 DHCP Server option to provide log-server details to a DHCP client";
        } // END of log-server definition.

        leaf-list dns-server  {
            type  inet:ipv4-address;
            description "IPv4 DHCP Server option to provide dns name-server details to a DHCP
                        client";
        } // END of dns-server definition.

        leaf network  {
            // when " ../netmask ";
            type  inet:ipv4-address;
            description "Network part of the subnet that will be used to assign IPv4 addresses
                        to hosts";
        } // END of network definition.

        leaf netmask  {
            // when " ../network ";
            type  inet:ipv4-address;
            description "Mask part of the subnet that will be used to assign IPv4 addresses to
                        hosts";
        } // END of netmask definition.

        leaf low-address-in-range  {
            type  inet:ipv4-address;
            description "Specifies the low range of the IPv4 addresses that the DHCP server
                        should assign to DHCP clients.";
        } // END of low-address-in-range definition.

        leaf high-address-in-range  {
            // when " ../low-address-in-range ";
            type  inet:ipv4-address;
            description "Specifies the high range of the IPv4 addresses that the DHCP server
                        should assign to DHCP clients.";
        } // END of high-address-in-range definition.

    } // END of dhcp-server-pool-config definition.
    grouping dhcpv6-server-pool-config {
        description
            "Grouping for dhcpv6 pool configurations";
        leaf pool6-name  {
            type  string {
                length "1..63";
                pattern "[^?' =,>|]+";
            }
            description "IPv6 DHCP Server address pool name";
        } // END of pool6-name definition.

        leaf domain-name  {
            type  string {
                length "1..63";
                pattern "[^?' =,>|]+";
            }
            description "IPv6 DHCP Server option to provide domain-name details to a DHCP
                        client";
        } // END of domain-name definition.

        leaf vendor-options  {
            type  cml-data-types:cml_line_t {
                length "1..1965";
            }
            description "IPv6 DHCP Server option to provide vendor details to a DHCP client";
        } // END of vendor-options definition.

        leaf-list ntp-server  {
            type  inet:ipv6-address;
            description "IPv6 DHCP Server option to provide ntp-server details to a DHCP client";
        } // END of ntp-server definition.

        leaf-list dns-server  {
            type  inet:ipv6-address;
            description "IPv6 DHCP Server option to provide dns name-server details to a DHCP
                        client";
        } // END of dns-server definition.

        leaf ipv6-network  {
            // when " ../ipv6-netmask ";
            type  inet:ipv6-address;
            description "Network part of the subnet that will be used to assign IPv6 addresses
                        to hosts";
        } // END of ipv6-network definition.

        leaf ipv6-netmask  {
            // when " ../ipv6-network ";
            type  uint8 {
                 range "1..128"  {
                    description "1..128: Supported range 1 - 128";
                 }
            }
            description "Mask part of the subnet that will be used to assign IPv6 addresses to
                        hosts";
        } // END of ipv6-netmask definition.

        leaf low-address-in-range  {
            type  inet:ipv6-address;
            description "Specifies the low range of the IPv6 addresses that the DHCP server
                        should assign to DHCP clients.";
        } // END of low-address-in-range definition.

        leaf high-address-in-range  {
            // when " ../low-address-in-range ";
            type  inet:ipv6-address;
            description "Specifies the high range of the IPv6 addresses that the DHCP server
                        should assign to DHCP clients.";
        } // END of high-address-in-range definition.

        leaf temporary-address  {
            type  inet:ipv6-address;
            description "Specifies the temporary IPv6 address that the DHCP server should
                        assign to DHCP clients.";
        } // END of temporary-address definition.

        leaf ipv6-prefix-high-address  {
            type  inet:ipv6-address;
            description "Specifies the higher prefix value in IPV6 prefix range";
        } // END of ipv6-prefix-high-address definition.

        leaf ipv6-prefix-low-address  {
            // when " ../ipv6-prefix-high-address ";
            type  inet:ipv6-address;
            description "Specifies the lower prefix value in IPV6 prefix range";
        } // END of ipv6-prefix-low-address definition.

        leaf ipv6-prefix-netmask  {
            // when " ../ipv6-prefix-high-address + ../ipv6-prefix-low-address ";
            type  uint8 {
                 range "1..128"  {
                    description "1..128: Supported range 1 - 128";
                 }
            }
            description "Mask part of the ipv6 Prefix used for Prefix delegation";
        } // END of ipv6-prefix-netmask definition.

    } // END of dhcpv6-server-pool-config definition.
    grouping server-interface-config {
        description
            "Configuration data for DHCP-server on each interface";
        leaf name  {
            type  leafref {
                path  "/ipi-interface:interfaces/ipi-interface:interface/ipi-interface:name";
            }
            description "This attribute maps to physical interface on which DHCP Server can be
                        enabled";
        } // END of name definition.

        leaf enable-ipv4-server  {
            // when " !ipi-if-ip:ipv4/config/enable-dhcp-ip-address + !ipi-dhcp-relay:relay/interfaces/interface/config/ipv4-relay-interface ";
            type  empty;
            description "Interface on which IPv4 DHCP Server has to be run";
        } // END of enable-ipv4-server definition.

        leaf enable-ipv6-server  {
            // when " !ipi-dhcp-relay:relay/interfaces/interface/config/ipv6-relay-interface ";
            if-feature feature-list:HAVE_IPV6;
            type  empty;
            description "Interface on which IPv6 DHCP Server has to be run";
        } // END of enable-ipv6-server definition.

    } // END of server-interface-config definition.
    grouping server-interface-top {
        description
            "DHCP server interface level information grouping";
        container interfaces {
            description
                "Top level container for DHCP server on each interface";

            list interface {
            // when " !ipi-interface:interfaces/interface/config/enable-switchport ";
                key "name";
                description
                    "List of interfaces mapped with DHCP server";
                leaf name  {
                    type  leafref {
                        path  "../config/name";
                    }
                    description "This attribute maps to physical interface on which DHCP Server can be
                                enabled";
                } // END of name definition.

                container config {
                    description
                        "Configuration data for DHCP server on each interface";
                    uses server-interface-config;
                } // END of config-container definition.
                container state {
                    config false;
                    description
                        "Operational state data";
                    uses server-interface-config;
                } // END of state-container definition.
            } // End of interface-list
        } // END of interfaces-container definition.
    } // END of server-interface-top definition.
    grouping dhcp-v4-pools-top {
        description
            "Grouping for IPv4 DHCP server attributes";
        container dhcp-pools {
            description
                "Container for IPv4 DHCP server address pools";

            list dhcp-pool {
                key "pool-name";
                max-elements 30;
                description
                    "List of IPv4 DHCP server address pool";
                leaf pool-name  {
                    type  leafref {
                        path  "../config/pool-name";
                    }
                    description "IPv4 DHCP Server address pool name";
                } // END of pool-name definition.

                container config {
                    description
                        "Configuration data for each IPv4 DHCP address pool";
                    uses dhcp-server-pool-config;
                } // END of config-container definition.
                container state {
                    config false;
                    description
                        "Operational data for each IPv4 DHCP address pool";
                    uses dhcp-server-pool-config;
                } // END of state-container definition.
            } // End of dhcp-pool-list
        } // END of dhcp-pools-container definition.
    } // END of dhcp-v4-pools-top definition.
    grouping dhcp-v6-pools-top {
        description
            "Grouping for IPv6 DHCP server attributes";
        container dhcp6-pools {
            if-feature feature-list:HAVE_IPV6;
            description
                "Container for IPv6 DHCP server address pools";

            list dhcp6-pool {
                key "pool6-name";
                max-elements 30;
                description
                    "List of IPv6 DHCP server address pool";
                leaf pool6-name  {
                    type  leafref {
                        path  "../config/pool6-name";
                    }
                    description "IPv6 DHCP Server address pool name";
                } // END of pool6-name definition.

                container config {
                    description
                        "Configuration data for each IPv6 DHCP address pool";
                    uses dhcpv6-server-pool-config;
                } // END of config-container definition.
                container state {
                    config false;
                    description
                        "Operational data for each IPv6 DHCP address pool";
                    uses dhcpv6-server-pool-config;
                } // END of state-container definition.
            } // End of dhcp6-pool-list
        } // END of dhcp6-pools-container definition.
    } // END of dhcp-v6-pools-top definition.
    grouping dhcp-server-vrf-top {
        description
            "Top level grouping for DHCP server per VRF attributes";
        container vrfs {
            description
                "Top level container for DHCP server on each VRF";

            list vrf {
            // when " ipi-dhcp-server:server/vrfs/vrf/config + ipi-dhcp-server:server/vrfs/vrf/dhcp-pools/dhcp-pool + ipi-dhcp-server:server/vrfs/vrf/dhcp6-pools/dhcp6-pool ";
                key "vrf-name";
                description
                    "List of vrfs mapped with DHCP server";
                leaf vrf-name  {
                    type  leafref {
                        path  "../config/vrf-name";
                    }
                    description "VPN routing/forwarding Instance name";
                } // END of vrf-name definition.

                container config {
                    description
                        "configuration data for each IPv6 DHCP server address pool";
                    uses dhcp-server-vrfs-config;
                    uses dhcp-server-v6-global-config;
                    uses dhcp-server-global-config;
                } // END of config-container definition.
                container state {
                    config false;
                    description
                        "Operational data for each IPv6 DHCP server address pool";
                    uses dhcp-server-vrfs-config;
                    uses dhcp-server-v6-global-config;
                    uses dhcp-server-global-config;
                } // END of state-container definition.
                uses dhcp-v4-pools-top;
                uses dhcp-v6-pools-top;
            } // End of vrf-list
        } // END of vrfs-container definition.
    } // END of dhcp-server-vrf-top definition.

    grouping  server-grouping {
    description
        "DHCP server related operations";
    container server {
        // when " !ipi-dhcp:dhcp/global/config/disable-dhcp-feature ";
        if-feature feature-list:HAVE_HOSTPD;
        if-feature feature-list:HAVE_HOSTP_DHCP_SERVER;
        description
            "DHCP server related operations";
        uses server-interface-top;
        uses dhcp-server-vrf-top;
    } // END of server-container definition.
    } // END of server-grouping definition.


}
