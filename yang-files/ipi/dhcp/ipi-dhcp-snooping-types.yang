/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dhcp-snooping-types.yang
*
*/

module ipi-dhcp-snooping-types {

    yang-version 1.1;

    namespace   "http://www.ipinfusion.com/yang/ocnos/ipi-dhcp-snooping-types";

    prefix "ipi-dhcp-snooping-types";

    organization
        "IP Infusion Inc.";

    contact
        "Address: 3965 Freedom Circle, Suite 200, Santa Clara, CA 95054
         Phone: +1 408-400-1900
         E-mail: support@ipinfusion.com
         Web: http://www.ipinfusion.com/";

    description
        "DHCP snooping data types";


    revision "2022-06-01" {
        description "Updated the yang file with feature";
        reference " 0.2.0.";
    }

    revision "2021-12-07" {
        description "Restructured module as per open-config";
        reference " 0.1.0.";
    }



    typedef  dhcp_snooping_debug_t {
        type bits {
            bit event {
                position 0;
                description "enable event debugs";
            }
            bit rx {
                position 1;
                description "enable rx debugs";
            }
            bit tx {
                position 2;
                description "enable tx debugs";
            }
            bit packet {
                position 3;
                description "enable packet debug";
            }
        }
        description "type definition for DHCP_SNOOPING_DEBUG_T";
    }

    typedef  dhcp_snooping_binding_type_t {
        type enumeration {
            enum static {
                value 0;
                description "Static binding type";
            }
        }
        description "type definition for DHCP_SNOOPING_BINDING_TYPE_T";
    }

    typedef  dhcp_snooping_filter_type_t {
        type enumeration {
            enum ip-mac {
                value 0;
                description "DHCP snooping filter type ip-mac";
            }
        }
        description "type definition for DHCP_SNOOPING_FILTER_TYPE_T";
    }

    typedef  dhcp_snooping_validation_t {
        type enumeration {
            enum src-mac {
                value 0;
                description "source mac validation";
            }
            enum dst-mac {
                value 1;
                description "destination mac validation";
            }
            enum ip {
                value 2;
                description "arp ip address validation";
            }
        }
        description "type definition for DHCP_SNOOPING_VALIDATION_T";
    }

}
