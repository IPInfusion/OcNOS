/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dhcp-relay.yang
*
*/

submodule ipi-dhcp-relay {

    yang-version 1.1;

    belongs-to  ipi-dhcp { prefix ipi-dhcp; }

    import feature-list {
        prefix feature-list;
        revision-date 2026-09-15;
    }

    import ipi-dhcp-relay-types {
        prefix ipi-dhcp-relay-types;
        revision-date 2023-01-11;
    }

    import ietf-inet-types {
        prefix inet;
        revision-date 2013-07-15;
    }

    import ietf-yang-types {
        prefix yang;
        revision-date 2013-07-15;
    }

    import cml-data-types {
        prefix cml-data-types;
        revision-date 2026-05-15;
    }

    import ipi-interface {
        prefix ipi-interface;
        revision-date 2026-03-10;
    }

    import ipi-network-instance {
        prefix ipi-network-instance;
        revision-date 2026-08-12;
    }

    import ipi-vrf {
        prefix ipi-vrf;
        revision-date 2026-08-12;
    }

    organization
        "IP Infusion Inc.";

    contact
        "Address: 3965 Freedom Circle, Suite 200, Santa Clara, CA 95054
         Phone: +1 408-400-1900
         E-mail: support@ipinfusion.com
         Web: http://www.ipinfusion.com/";

    description
        "dhcp_relay_configuration";


    revision "2026-04-01" {
        description "Added per VRF support for clear ip dhcp realy stats and option stats";
        reference " 0.13.1.";
    }

    revision "2026-01-05" {
        description "Updated circuit-id suboption to support IP address format";
        reference " 0.13.0.";
    }

    revision "2025-12-09" {
        description "Suppressed extra CLI generation";
        reference " 0.12.7.";
    }

    revision "2025-09-22" {
        description "Added hints in helpstrings about acceptable charecters and acceptable lengths for template-name";
        reference " 0.12.6.";
    }

    revision "2025-09-18" {
        description "Added leafref tag for Option82-template-name in IPv4 DHCP relay";
        reference " 0.12.5.";
    }

    revision "2025-09-17" {
        description "Added max length and pattern to optin82-template-name";
        reference " 0.12.4.";
    }

    revision "2025-09-04" {
        description "Removed EVPN_IRB_IF_MODE while configuring IRB interface";
        reference " 0.12.3.";
    }

    revision "2025-08-25" {
        description "Added support for Option82-template-name in IPv4 DHCP relay";
        reference " 0.12.2.";
    }

    revision "2025-07-27" {
        description "Updated description for IPv6 DHCP Duplicate Clients";
        reference " 0.12.1.";
    }

    revision "2025-06-26" {
        description "Added support for Subscriber-ID for IPv4 DHCP relay";
        reference " 0.12.0.";
    }

    revision "2025-04-17" {
        description "Added support for Gi-addr and Src_IP Option in DHCP realy";
        reference " 0.11.0.";
    }

    revision "2023-12-15" {
        description "DHCPv6 Relay Prefix requirements";
        reference " 0.10.0.";
    }

    revision "2023-06-30" {
        description "DHCP Group feature";
        reference " 0.9.0.";
    }

    revision "2023-01-12" {
        description "Container has delete api which is not correct hence changed it us unset";
        reference " 0.8.7.";
    }

    revision "2023-01-11" {
        description "Incorrect if-feature flags removed";
        reference " 0.8.6.";
    }

    revision "2023-01-05" {
        description "Leafref correction for config container";
        reference " 0.8.5.";
    }

    revision "2022-12-02" {
        description "DHCP Relay Option82 CLI correction";
        reference " 0.8.4.";
    }

    revision "2022-11-21" {
        description "DHCP Relay Option82 always-on CLI updation";
        reference " 0.8.3.";
    }

    revision "2022-11-16" {
        description "Updated missing cliprependstr tags";
        reference " 0.8.2.";
    }

    revision "2022-11-09" {
        description "Updated the Top level hierarchy";
        reference " 0.8.1.";
    }

    revision "2022-11-02" {
        description "DHCP Relay Option82 always-on feature";
        reference " 0.8.0.";
    }

    revision "2022-09-12" {
        description "Updated if-feature in datamodel";
        reference " 0.7.4.";
    }

    revision "2022-08-12" {
        description "Updated if-feature in datamodel";
        reference " 0.7.3.";
    }

    revision "2022-08-10" {
        description "Debug hierarchy change";
        reference " 0.7.2.";
    }

    revision "2022-07-31" {
        description "Stop using inet:ipv4-prefix and inet:ipv6-prefix due to Cisco NSO iterop";
        reference " 0.7.1.";
    }

    revision "2022-07-30" {
        description "Updated when expressions in yang";
        reference " 0.7.0.";
    }

    revision "2022-07-15" {
        description "Added autoPopulate tags in datamodel";
        reference " 0.6.2.";
    }

    revision "2022-07-04" {
        description "Added implicit_delete tags in datamodel";
        reference " 0.6.1.";
    }

    revision "2022-06-01" {
        description "Updated the yang file with feature";
        reference " 0.6.0.";
    }

    revision "2021-11-30" {
        description "Changes to support DHCP Relay across VRF feature";
        reference " 0.5.0.";
    }

    revision "2021-09-03" {
        description "Update descriptions of attribute";
        reference " 0.4.0.";
    }

    revision "2021-06-11" {
        description "Changes to support DHCP L3VPN feature";
        reference " 0.3.0.";
    }

    revision "2020-12-15" {
        description "Change to have data-types in lower case instead of camel case";
        reference " 0.2.0.";
    }

    revision "2020-08-11" {
        description "Initial Version";
        reference " 0.1.0.";
    }

    grouping relay-global-config {
        description
            "DHCP relay global configuration data attributes group";
        leaf disable-dhcpv4-relay  {
            type  empty;
            description "Use this attribute to disable the DHCP relay global config";
        } // END of disable-dhcpv4-relay definition.

        leaf disable-dhcpv6-relay  {
            type  empty;
            description "Use this attribute to disable the DHCP relay global config";
        } // END of disable-dhcpv6-relay definition.

    } // END of relay-global-config definition.
    grouping relay-ipv4-vpn-vrf-top {
        description
            "DHCPv4 relay VPN information grouping";
        container ipv4-vpn-links {
            description
                "Top level container for IPv4 DHCP Relay VPN config";

            list ipv4-vpn-link {
            // when " ipi-dhcp-relay:relay/vrfs/vrf/ipv4-vpn-links/ipv4-vpn-link/config/interface-direction ";
                key "interface-type";
                description
                    "DHCPv4 relay vpn configs";
                leaf interface-type  {
                    type  leafref {
                        path  "../config/interface-type";
                    }
                    description "DHCP relay vpn interface type";
                } // END of interface-type definition.

                container config {
                    description
                        "Configuration data for DHCP-relay on each vpn";
                    uses ipv4-vpn-link-attrs-config;
                } // END of config-container definition.
                container state {
                    config false;
                    description
                        "Operational data for DHCP-relay on each vpn";
                    uses ipv4-vpn-link-attrs-config;
                } // END of state-container definition.
            } // End of ipv4-vpn-link-list
        } // END of ipv4-vpn-links-container definition.
    } // END of relay-ipv4-vpn-vrf-top definition.
    grouping ipv4-vpn-link-attrs-config {
        description
            "Attrs for DHCPv4-relay vpn";
        leaf interface-type  {
            type  ipi-dhcp-relay-types:dhcp_vpn_interface_type_t;
            description "DHCP relay vpn interface type";
        } // END of interface-type definition.

        leaf interface-direction  {
            type  ipi-dhcp-relay-types:dhcp_vpn_interface_direction_t;
            mandatory true;
            description "DHCP relay vpn interface direction";
        } // END of interface-direction definition.

    } // END of ipv4-vpn-link-attrs-config definition.
    grouping relay-ipv6-vpn-vrf-top {
        description
            "DHCPv6 relay VPN information grouping";
        container ipv6-vpn-links {
            description
                "Top level container for IPv6 DHCP Relay VPN config";

            list ipv6-vpn-link {
            // when " ipi-dhcp-relay:relay/vrfs/vrf/ipv6-vpn-links/ipv6-vpn-link/config/interface-direction-v6 ";
                if-feature feature-list:HAVE_IPV6;
                key "interface-type-v6";
                description
                    "DHCPv6 relay vpn configs";
                leaf interface-type-v6  {
                    type  leafref {
                        path  "../config/interface-type-v6";
                    }
                    description "DHCPv6 relay vpn interface type";
                } // END of interface-type-v6 definition.

                container config {
                    description
                        "Configuration data for DHCP-relay on each vpn";
                    uses ipv6-vpn-link-attrs-config;
                } // END of config-container definition.
                container state {
                    config false;
                    description
                        "Operational data for DHCP-relay on each vpn";
                    uses ipv6-vpn-link-attrs-config;
                } // END of state-container definition.
            } // End of ipv6-vpn-link-list
        } // END of ipv6-vpn-links-container definition.
    } // END of relay-ipv6-vpn-vrf-top definition.
    grouping ipv6-vpn-link-attrs-config {
        description
            "Attrs for DHCPv6-relay vpn";
        leaf interface-type-v6  {
            type  ipi-dhcp-relay-types:dhcp_vpn_interface_type_t;
            description "DHCPv6 relay vpn interface type";
        } // END of interface-type-v6 definition.

        leaf interface-direction-v6  {
            type  ipi-dhcp-relay-types:dhcp_vpn_interface_direction_t;
            mandatory true;
            description "DHCPv6 relay vpn interface direction";
        } // END of interface-direction-v6 definition.

    } // END of ipv6-vpn-link-attrs-config definition.
    grouping relay-ipv4-dhcp-server-top {
        description
            "DHCPv4 relay Server address grouping";
        container ipv4-dhcp-servers {
            description
                "Top level container for IPv4 DHCP Relay Server address config";

            list ipv4-dhcp-server {
                key "ip-address";
                description
                    "DHCPv4 relay server address configs";
                leaf ip-address  {
                    type  leafref {
                        path  "../config/ip-address";
                    }
                    description "IPv4 address of the DHCP server";
                } // END of ip-address definition.

                container config {
                    description
                        "Configuration data for DHCP-relay server addr";
                    uses ipv4-server-addr-attrs-config;
                } // END of config-container definition.
                container state {
                    config false;
                    description
                        "Operational data for DHCP-relay server address";
                    uses ipv4-server-addr-attrs-config;
                } // END of state-container definition.
            } // End of ipv4-dhcp-server-list
        } // END of ipv4-dhcp-servers-container definition.
    } // END of relay-ipv4-dhcp-server-top definition.
    grouping ipv4-server-addr-attrs-config {
        description
            "Attrs for DHCPv4-relay server address";
        leaf ip-address  {
            type  inet:ipv4-address;
            description "IPv4 address of the DHCP server";
        } // END of ip-address definition.

        leaf dhcpv4-server-global-vrf  {
            type  leafref {
                path  "/ipi-network-instance:network-instances/ipi-network-instance:network-instance/ipi-vrf:vrf/ipi-vrf:config/ipi-vrf:vrf-name";
            }
            description "This attributes defines the VRF in which the DHCPv4 relay server is
                        present";
        } // END of dhcpv4-server-global-vrf definition.

    } // END of ipv4-server-addr-attrs-config definition.
    grouping relay-ipv6-dhcp-server-top {
        description
            "DHCPv6 relay Server address grouping";
        container ipv6-dhcp-servers {
            if-feature feature-list:HAVE_IPV6;
            description
                "Top level container for IPv6 DHCP Relay Server address config";

            list ipv6-dhcp-server {
                key "ipv6-address";
                description
                    "DHCPv6 relay server address configs";
                leaf ipv6-address  {
                    type  leafref {
                        path  "../config/ipv6-address";
                    }
                    description "IPv6 address of the DHCP server";
                } // END of ipv6-address definition.

                container config {
                    description
                        "Configuration data for DHCP-relay server addr";
                    uses ipv6-server-addr-attrs-config;
                } // END of config-container definition.
                container state {
                    config false;
                    description
                        "Operational data for DHCP-relay server addr";
                    uses ipv6-server-addr-attrs-config;
                } // END of state-container definition.
            } // End of ipv6-dhcp-server-list
        } // END of ipv6-dhcp-servers-container definition.
    } // END of relay-ipv6-dhcp-server-top definition.
    grouping ipv6-server-addr-attrs-config {
        description
            "Attrs for DHCPv6-relay server address";
        leaf ipv6-address  {
            if-feature feature-list:HAVE_IPV6;
            type  inet:ipv6-address;
            description "IPv6 address of the DHCP server";
        } // END of ipv6-address definition.

        leaf dhcpv6-server-global-vrf  {
            type  leafref {
                path  "/ipi-network-instance:network-instances/ipi-network-instance:network-instance/ipi-vrf:vrf/ipi-vrf:config/ipi-vrf:vrf-name";
            }
            description "This attributes defines the VRF in which the DHCPv6 relay server is
                        present";
        } // END of dhcpv6-server-global-vrf definition.

    } // END of ipv6-server-addr-attrs-config definition.
    grouping relay-vrf-config {
        description
            "DHCP relay VRF level information grouping";
        leaf vrf-name  {
            type  leafref {
                path  "/ipi-network-instance:network-instances/ipi-network-instance:network-instance/ipi-vrf:vrf/ipi-vrf:config/ipi-vrf:vrf-name";
            }
            description "VRF name associated with this instance.";
        } // END of vrf-name definition.

    } // END of relay-vrf-config definition.
    grouping relay-vrf-config-attrs {
        description
            "DHCP relay VRF level information grouping";
        leaf link-selection-source-ip  {
            type  inet:ipv4-address;
            description "Enable link selection sub-option (5) in the option-82 in DHCP packet";
        } // END of link-selection-source-ip definition.

        leaf enable-option82  {
            type  empty;
            description "Enable the device to insert and remove option-82 information on DHCP
                        packets forwarded by the DHCP relay agent.";
        } // END of enable-option82 definition.

        leaf enable-option82-always-on  {
            // when " ipi-dhcp-relay:relay/vrfs/vrf/config/enable-option82 ";
            type  empty;
            description "Keep option-82 information on DHCP packets forwarded by the DHCP relay
                        agent.";
        } // END of enable-option82-always-on definition.

        leaf enable-dhcpv6-pd-route-injection  {
            if-feature feature-list:HAVE_IPV6;
            type  empty;
            description "Enable the route installation from the prefixes learned through prefix
                        delegation.";
        } // END of enable-dhcpv6-pd-route-injection definition.

        leaf enable-dhcpv6-duplicate-clients  {
            if-feature feature-list:HAVE_IPV6;
            type  empty;
            description "Specify that the DHCPv6 relay agent uses the clients incoming
                        interfaces to differentiate between the duplicate DUIDs (Interface
                        Identifier Option)";
        } // END of enable-dhcpv6-duplicate-clients definition.

        leaf remote-id  {
            // when " ipi-dhcp-relay:relay/vrfs/vrf/config/enable-option82 ";
            type  ipi-dhcp-relay-types:dhcp_remote_id_t;
            description "Remote host identifier. Use option 82 to provide the DHCP server
                        information about the DHCP client";
        } // END of remote-id definition.

        leaf ipv4-subscriber-id  {
            // when " ipi-dhcp-relay:relay/vrfs/vrf/config/enable-option82 ";
            type  string {
                length "1..255";
                pattern "[^?' =,>|]+";
            }
            description "Subscriber identifier. Use this option to allows the service provider
                        to assign/activate subscriber-specific actions";
        } // END of ipv4-subscriber-id definition.

        leaf subscriber-id  {
            type  string {
                length "1..1965";
                pattern "[^?' =,>|]+";
            }
            description "Subscriber identifier. Use this option to allows the service provider
                        to assign/activate subscriber-specific actions";
        } // END of subscriber-id definition.

        leaf option82-template-name  {
            // when " ipi-dhcp-relay:relay/vrfs/vrf/config/enable-option82 ";
            type  leafref {
                path  "/ipi-dhcp:dhcp/ipi-dhcp:option82-templates/ipi-dhcp:option82-template/ipi-dhcp:config/ipi-dhcp:template-name";
            }
            description "Apply the defined option82 template to a relay configs";
        } // END of option82-template-name definition.

    } // END of relay-vrf-config-attrs definition.
    grouping relay-interface-config {
        description
            "Configuration data for DHCP-relay on each interface";
        leaf name  {
            type  leafref {
                path  "/ipi-interface:interfaces/ipi-interface:interface/ipi-interface:name";
            }
            description "Name of the Interface";
        } // END of name definition.

        leaf ipv4-relay-interface  {
            // when " !ipi-dhcp-relay:relay/interfaces/interface/config/ipv4-uplink-interface ";
            type  empty;
            description "Enable relay on Client facing interface";
        } // END of ipv4-relay-interface definition.

        leaf gi-addr  {
            // when " ipi-dhcp-relay:relay/interfaces/interface/config/ipv4-relay-interface ";
            type  inet:ipv4-address;
            description "Configure the custom gi-addr address";
        } // END of gi-addr definition.

        leaf src-ip-addr  {
            // when " ipi-dhcp-relay:relay/interfaces/interface/config/gi-addr ";
            type  empty;
            description "Use custom gi-addr as the source address";
        } // END of src-ip-addr definition.

        leaf ipv4-uplink-interface  {
            // when " !ipi-dhcp-relay:relay/interfaces/interface/config/ipv4-relay-interface ";
            type  empty;
            description "Specify the interface as an uplink interface(Server facing)";
        } // END of ipv4-uplink-interface definition.

        leaf ipv4-group-name  {
            // when " ipi-dhcp-relay:relay/interfaces/interface/config/ipv4-uplink-interface ";
            type  string {
                length "1..63";
                pattern "[^?' =,>|]+";
            }
            description "Correlate specified interface to a specified DHCP server group.";
        } // END of ipv4-group-name definition.

        leaf ipv6-relay-interface  {
            // when " !ipi-dhcp-relay:relay/interfaces/interface/config/ipv6-uplink-interface ";
            if-feature feature-list:HAVE_IPV6;
            type  empty;
            description "Enable IPv6 relay on Client facing interface";
        } // END of ipv6-relay-interface definition.

        leaf ipv6-gi-addr  {
            // when " ipi-dhcp-relay:relay/interfaces/interface/config/ipv6-relay-interface ";
            type  inet:ipv6-address;
            description "ipv6-gi-addr to be used in the DHCP relay";
        } // END of ipv6-gi-addr definition.

        leaf ipv6-src-addr  {
            // when " ipi-dhcp-relay:relay/interfaces/interface/config/ipv6-gi-addr ";
            type  empty;
            description "Use custom gi-addr as the source address";
        } // END of ipv6-src-addr definition.

        leaf ipv6-uplink-interface  {
            // when " !ipi-dhcp-relay:relay/interfaces/interface/config/ipv6-relay-interface ";
            if-feature feature-list:HAVE_IPV6;
            type  empty;
            description "Specify the interface as an uplink interface(Server facing)";
        } // END of ipv6-uplink-interface definition.

        leaf ipv6-group-name  {
            // when " ipi-dhcp-relay:relay/interfaces/interface/config/ipv6-uplink-interface ";
            type  string {
                length "1..63";
                pattern "[^?' =,>|]+";
            }
            description "Correlate specified interface to a specified DHCPv6 server group.";
        } // END of ipv6-group-name definition.

    } // END of relay-interface-config definition.
    grouping relay-stats {
        description
            "DHCP Relay statistics";
        leaf bogus-giaddr-drops  {
            type  uint32;
            description "Packets sent to us to relay back to a client, but with a bogus giaddr";
        } // END of bogus-giaddr-drops definition.

        leaf client-packets-relayed  {
            type  uint32;
            description "Packets relayed from client to server";
        } // END of client-packets-relayed definition.

        leaf server-packet-errors  {
            type  uint32;
            description "Errors sending packets to servers";
        } // END of server-packet-errors definition.

        leaf server-packets-relayed  {
            type  uint32;
            description "Packets relayed from server to client";
        } // END of server-packets-relayed definition.

        leaf client-packet-errors  {
            type  uint32;
            description "Errors sending packets to clients";
        } // END of client-packet-errors definition.

        leaf agent-option-errors  {
            type  uint32;
            description "Number of packets forwarded without agent options because there was no
                        room";
        } // END of agent-option-errors definition.

        leaf corrupt-agent-options  {
            type  uint32;
            description "Number of packets dropped because relay agent information option was
                        bad";
        } // END of corrupt-agent-options definition.

        leaf missing-agent-option  {
            type  uint32;
            description "Number of packets dropped because no RAI option matching our ID was
                        found";
        } // END of missing-agent-option definition.

        leaf bad-circuit-id  {
            type  uint32;
            description "Circuit ID option in matching RAI option did not match any known
                        circuit ID";
        } // END of bad-circuit-id definition.

        leaf missing-circuit-id  {
            type  uint32;
            description "Circuit ID option in matching RAI option was missing";
        } // END of missing-circuit-id definition.

        leaf circuit-id  {
            type  string {
                length "0..1965";
                pattern "[^?' =,>|]*";
            }
            description "Circuit ID";
        } // END of circuit-id definition.

    } // END of relay-stats definition.
    grouping relay-delegated-prefixes {
        description
            "DHCPv6 Prefix Delegation learnt prefix details";

        list dhcpv6-delegated-prefixes {
            if-feature feature-list:HAVE_IPV6;
            key "interface-name";
            config false;
            description
                "Delegated prefix list";
            leaf interface-name  {
                type  leafref {
                    path  "../state/interface-name";
                }
                description "DHCP client facing interface, which is part of the LAN network";
            } // END of interface-name definition.

            container state {
                config false;
                description
                    "Operational state data";
                uses dhcpv6-delegated-prefixes-attrs;
            } // END of state-container definition.
        } // End of dhcpv6-delegated-prefixes-list
    } // END of relay-delegated-prefixes definition.
    grouping dhcpv6-delegated-prefixes-attrs {
        description
            "DHCPv6 Prefix Delegation learnt prefix attrs";
        leaf interface-name  {
            type  string {
                length "1..1965";
                pattern "[^?' =,>|]+";
            }
            description "DHCP client facing interface, which is part of the LAN network";
        } // END of interface-name definition.

        leaf next-hop  {
            type  inet:ipv6-address;
            description "DHCP client interface linklocal adddress";
        } // END of next-hop definition.

        leaf prefix  {
            type  cml-data-types:cml_ipv6_prefix_t;
            description "Delegated prefix";
        } // END of prefix definition.

        leaf preferred-lifetime  {
            type  uint32;
            units "seconds";
            description "Specifies how long the prefix remains preferred in seconds";
        } // END of preferred-lifetime definition.

        leaf maximum-lifetime  {
            type  uint32;
            units "seconds";
            description "Specifies how long the prefix remains validin seconds";
        } // END of maximum-lifetime definition.

        leaf prefix-start-time  {
            type  yang:date-and-time {
                pattern "\\d{4}-\\d{2}-\\d{2}T\\d{2}:\\d{2}:\\d{2}(\\.\\d+)?(Z|[\\+\\-]\\d{2}:\\d{2})";
                }
                description "The time when the prefix was learned";
            } // END of prefix-start-time definition.

            leaf prefix-expiry-time  {
                type  yang:date-and-time {
                    pattern "\\d{4}-\\d{2}-\\d{2}T\\d{2}:\\d{2}:\\d{2}(\\.\\d+)?(Z|[\\+\\-]\\d{2}:\\d{2})";
                    }
                    description "The time when the prefix would expire";
                } // END of prefix-expiry-time definition.

                leaf state  {
                    type  ipi-dhcp-relay-types:dhcp6_pd_route_state_t;
                    description "Notification route add/delete input";
                } // END of state definition.

    } // END of dhcpv6-delegated-prefixes-attrs definition.
    grouping dhcp-relay-group-config {
        description
            "Grouping for dhcp pool configurations";
        leaf group-name  {
            type  string {
                length "1..63";
                pattern "[^?' =,>|]+";
            }
            description "IPv4 DHCP Relay group name";
        } // END of group-name definition.

        leaf-list server  {
            type  inet:ipv4-address;
            description "IPv4 DHCP Relay Group server details";
        } // END of server definition.

    } // END of dhcp-relay-group-config definition.
    grouping dhcpv6-relay-group-config {
        description
            "Grouping for dhcp pool configurations";
        leaf group6-name  {
            type  string {
                length "1..63";
                pattern "[^?' =,>|]+";
            }
            description "IPv6 DHCP Relay group name";
        } // END of group6-name definition.

        leaf-list server  {
            type  inet:ipv6-address;
            description "IPv6 DHCP Relay Group server details";
        } // END of server definition.

    } // END of dhcpv6-relay-group-config definition.
    grouping dhcp-v4-groups-top {
        description
            "Grouping for IPv4 DHCP relay group attributes";
        container dhcp-groups {
            description
                "Container for IPv4 DHCP relay groups";

            list dhcp-group {
                key "group-name";
                max-elements 32;
                description
                    "List of IPv4 DHCP relay group";
                leaf group-name  {
                    type  leafref {
                        path  "../config/group-name";
                    }
                    description "IPv4 DHCP Relay group name";
                } // END of group-name definition.

                container config {
                    description
                        "Configuration data for each IPv4 DHCP relay group";
                    uses dhcp-relay-group-config;
                } // END of config-container definition.
                container state {
                    config false;
                    description
                        "Operational data for each IPv4 DHCP address group";
                    uses dhcp-relay-group-config;
                } // END of state-container definition.
            } // End of dhcp-group-list
        } // END of dhcp-groups-container definition.
    } // END of dhcp-v4-groups-top definition.
    grouping dhcp-v6-groups-top {
        description
            "Grouping for IPv6 DHCP relay group attributes";
        container dhcpv6-groups {
            if-feature feature-list:HAVE_IPV6;
            description
                "Container for IPv6 DHCP relay groups";

            list dhcpv6-group {
                key "group6-name";
                max-elements 32;
                description
                    "List of IPv6 DHCP relay group";
                leaf group6-name  {
                    type  leafref {
                        path  "../config/group6-name";
                    }
                    description "IPv6 DHCP Relay group name";
                } // END of group6-name definition.

                container config {
                    description
                        "Configuration data for each IPv6 DHCP relay group";
                    uses dhcpv6-relay-group-config;
                } // END of config-container definition.
                container state {
                    config false;
                    description
                        "Operational data for each IPv6 DHCP relay group";
                    uses dhcpv6-relay-group-config;
                } // END of state-container definition.
            } // End of dhcpv6-group-list
        } // END of dhcpv6-groups-container definition.
    } // END of dhcp-v6-groups-top definition.
    grouping relay-interface-top {
        description
            "DHCP relay interface level information grouping";
        container interfaces {
            description
                "Top level container for DHCP relay on each interface";

            list interface {
            // when " !ipi-interface:interfaces/interface/config/enable-switchport ";
                key "name";
                description
                    "List of interfaces mapped with DHCP relay";
                leaf name  {
                    type  leafref {
                        path  "../config/name";
                    }
                    description "The textual name of the interface. The value of this object should be
                                the name of the interface as assigned by the local device and should
                                be suitable for use in commands entered at the device's `console'.
                                This might be a text name, such as `le0' or a simple port number, such
                                as `1', depending on the interface naming syntax of the device. If
                                several entries in the ifTable together represent a single interface
                                as named by the device, then each will have the same value of name.
                                Note that for an agent which responds to SNMP queries concerning an
                                interface on some other (proxied) device, then the value of name for
                                such an interface is the proxied device's local name for it. If there
                                is no local name, or this object is otherwise not applicable, then
                                this object contains a zero-length string.";
                } // END of name definition.

                container config {
                    description
                        "Configuration data for DHCP relay on each interface";
                    uses relay-interface-config;
                } // END of config-container definition.
                container state {
                    config false;
                    description
                        "Operational state data";
                    uses relay-interface-config;
                } // END of state-container definition.
            } // End of interface-list
        } // END of interfaces-container definition.
    } // END of relay-interface-top definition.
    grouping relay-global-top {
        description
            "DHCP relay global level information grouping";
        container global {
            description
                "DHCP relay global level information";
            container config {
                description
                    "Configuration data for DHCP relay global level";
                uses relay-global-config;
            } // END of config-container definition.
            container state {
                config false;
                description
                    "Operational state data";
                uses relay-global-config;
            } // END of state-container definition.
        } // END of global-container definition.
    } // END of relay-global-top definition.
    grouping dhcp-relay-vrf-top {
        description
            "Top level grouping for DHCP Relay per VRF attributes";
        container vrfs {
            description
                "Top level container for DHCP Relay on each VRF";

            list vrf {
                key "vrf-name";
                description
                    "List of vrfs mapped with DHCP relay";
                leaf vrf-name  {
                    type  leafref {
                        path  "../config/vrf-name";
                    }
                    description "VPN routing/forwarding Instance name";
                } // END of vrf-name definition.

                container config {
                    description
                        "Configuration parameters relating to a VRF instance";
                    uses relay-vrf-config;
                    uses relay-vrf-config-attrs;
                } // END of config-container definition.
                container state {
                    config false;
                    description
                        "Operational state data";
                    uses relay-vrf-config;
                    uses relay-vrf-config-attrs;
                    uses relay-stats;
                } // END of state-container definition.
                uses relay-ipv4-vpn-vrf-top;
                uses relay-ipv6-vpn-vrf-top;
                uses relay-delegated-prefixes;
                uses relay-ipv4-dhcp-server-top;
                uses relay-ipv6-dhcp-server-top;
                uses dhcp-v4-groups-top;
                uses dhcp-v6-groups-top;
            } // End of vrf-list
        } // END of vrfs-container definition.
    } // END of dhcp-relay-vrf-top definition.

    grouping  relay-grouping {
    description
        "DHCP relay related operations";
    container relay {
        // when " !ipi-dhcp:dhcp/global/config/disable-dhcp-feature ";
        if-feature feature-list:HAVE_HOSTPD;
        if-feature feature-list:HAVE_HOSTP_DHCP_RELAY;
        description
            "DHCP relay related operations";
        uses relay-global-top;
        uses relay-interface-top;
        uses dhcp-relay-vrf-top;
    } // END of relay-container definition.
    } // END of relay-grouping definition.


}
