/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dhcp-snooping-interface.yang
*
*/

submodule ipi-dhcp-snooping-interface {

    yang-version 1.1;

    belongs-to  ipi-dhcp { prefix ipi-dhcp; }

    import feature-list {
        prefix feature-list;
        revision-date 2026-09-15;
    }

    import cml-data-types {
        prefix cml-data-types;
        revision-date 2026-05-15;
    }

    import ietf-inet-types {
        prefix inet;
        revision-date 2013-07-15;
    }

    import ipi-interface {
        prefix ipi-interface;
        revision-date 2026-03-10;
    }

    import ipi-dhcp-snooping-types {
        prefix ipi-dhcp-snooping-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "DHCP Snooping configurations for interfaces";


    revision "2024-02-18" {
        description "Added flag for when tag for container verify,config";
        reference " 0.7.1.";
    }

    revision "2024-02-12" {
        description "Removed implicit_delete tag and added when tag for container verify,config";
        reference " 0.7.0.";
    }

    revision "2023-08-17" {
        description "Added implicit_delete tag for container verify,config";
        reference " 0.6.0.";
    }

    revision "2023-04-21" {
        description "Added implicit_delete tag for container interfaces, trust, config";
        reference " 0.5.0.";
    }

    revision "2023-01-11" {
        description "Incorrect if-feature flags removed";
        reference " 0.4.0.";
    }

    revision "2022-08-10" {
        description "Debug hierarchy change";
        reference " 0.3.0.";
    }

    revision "2022-06-01" {
        description "Updated the yang file with feature";
        reference " 0.2.0.";
    }

    revision "2021-12-07" {
        description "Restructured module as per open-config, initial version for interfaces";
        reference " 0.1.0.";
    }

    grouping dhcp-snooping-interfaces-bridge-binding-ipv6-state {
        description
            "Grouping for DHCP snooping bridges source binding ipv6 address";
        leaf ip-address  {
            type  inet:ipv6-address;
            description "This attribute returns the IPv6 address binded";
        } // END of ip-address definition.

    } // END of dhcp-snooping-interfaces-bridge-binding-ipv6-state definition.
    grouping dhcp-snooping-interfaces-bridge-binding-ipv4-state {
        description
            "Grouping for DHCP snooping bridges source binding ipv4 address";
        leaf ip-address  {
            type  inet:ipv4-address;
            description "This attribute returns the IPv4 address binded";
        } // END of ip-address definition.

    } // END of dhcp-snooping-interfaces-bridge-binding-ipv4-state definition.
    grouping dhcp-snooping-interfaces-binding-info-state {
        description
            "Grouping for DHCP snooping interfaces binding attributes";
        leaf interface  {
            type  string {
                length "1..1965";
                pattern "[^?' =,>|]+";
            }
            description "This attribute to returns counters for interface snooping binding.";
        } // END of interface definition.

        leaf filter-type  {
            type  ipi-dhcp-snooping-types:dhcp_snooping_filter_type_t;
            description "This attribute to returns DHCP snooping filter-type configured on
                        interface.";
        } // END of filter-type definition.

        leaf vlan-id  {
            type  uint16;
            description "This attribute to returns DHCP snooping VLAN-ID on interface.";
        } // END of vlan-id definition.

        leaf mac-address  {
            type  cml-data-types:cml_mac_addr_t {
                length "1..1965";
            }
            description "This attribute to returns DHCP snooping MAC address on interface.";
        } // END of mac-address definition.

    } // END of dhcp-snooping-interfaces-binding-info-state definition.
    grouping dhcp-snooping-interfaces-binding-info-ipv4 {
        description
            "Grouping for DHCP snooping interfaces IPv4 binding info";
        container ipv4-entries {
            config false;
            description
                "DHCP snooping binding info by interfaces configured with IPv4
                        addresses";

            list ipv4-entry {
                key "ip-address";
                config false;
                description
                    "List of DHCP snooping binding ipv4 entries by interfaces";
                leaf ip-address  {
                    type  leafref {
                        path  "../state/ip-address";
                    }
                    description "This attribute returns the IPv4 address binded";
                } // END of ip-address definition.

                container state {
                    config false;
                    description
                        "Operational state data";
                    uses dhcp-snooping-interfaces-binding-info-state;
                    uses dhcp-snooping-interfaces-bridge-binding-ipv4-state;
                } // END of state-container definition.
            } // End of ipv4-entry-list
        } // END of ipv4-entries-container definition.
    } // END of dhcp-snooping-interfaces-binding-info-ipv4 definition.
    grouping dhcp-snooping-interfaces-binding-info-ipv6 {
        description
            "Grouping for DHCP snooping interfaces IPv6 binding info";
        container ipv6-entries {
            if-feature feature-list:HAVE_IPV6;
            config false;
            description
                "DHCP snooping binding info by interfaces configured with IPv6
                        addresses";

            list ipv6-entry {
                key "ip-address";
                config false;
                description
                    "List of DHCP snooping binding ipv6 entries by interfaces";
                leaf ip-address  {
                    type  leafref {
                        path  "../state/ip-address";
                    }
                    description "This attribute returns the IPv6 address binded";
                } // END of ip-address definition.

                container state {
                    config false;
                    description
                        "Operational state data";
                    uses dhcp-snooping-interfaces-binding-info-state;
                    uses dhcp-snooping-interfaces-bridge-binding-ipv6-state;
                } // END of state-container definition.
            } // End of ipv6-entry-list
        } // END of ipv6-entries-container definition.
    } // END of dhcp-snooping-interfaces-binding-info-ipv6 definition.
    grouping dhcp-snooping-interfaces-binding-info-top {
        description
            "Grouping for DHCP snooping interfaces binding info";
        container snooping-binding-info {
            config false;
            description
                "DHCP snooping binding info by interfaces";
            uses dhcp-snooping-interfaces-binding-info-ipv4;
            uses dhcp-snooping-interfaces-binding-info-ipv6;
        } // END of snooping-binding-info-container definition.
    } // END of dhcp-snooping-interfaces-binding-info-top definition.
    grouping dhcp-snooping-interfaces-source-binding-info-ipv4 {
        description
            "Grouping for DHCP snooping source interfaces IPv4 binding info";
        container ipv4-entries {
            config false;
            description
                "DHCP source binding info by interfaces configured with IPv4 addresses";

            list ipv4-entry {
                key "ip-address";
                config false;
                description
                    "List of DHCP snooping source binding ipv4 entries by interfaces";
                leaf ip-address  {
                    type  leafref {
                        path  "../state/ip-address";
                    }
                    description "This attribute returns the IPv4 address binded";
                } // END of ip-address definition.

                container state {
                    config false;
                    description
                        "Operational state data";
                    uses dhcp-snooping-interfaces-binding-info-state;
                    uses dhcp-snooping-interfaces-bridge-binding-ipv4-state;
                } // END of state-container definition.
            } // End of ipv4-entry-list
        } // END of ipv4-entries-container definition.
    } // END of dhcp-snooping-interfaces-source-binding-info-ipv4 definition.
    grouping dhcp-snooping-interfaces-source-binding-info-ipv6 {
        description
            "Grouping for DHCP snooping source interfaces IPv6 binding info";
        container ipv6-entries {
            if-feature feature-list:HAVE_IPV6;
            config false;
            description
                "DHCP source binding info by interfaces configured with IPv6 addresses";

            list ipv6-entry {
                key "ip-address";
                config false;
                description
                    "List of DHCP snooping source binding ipv6 entries by interfaces";
                leaf ip-address  {
                    type  leafref {
                        path  "../state/ip-address";
                    }
                    description "This attribute returns the IPv6 address binded";
                } // END of ip-address definition.

                container state {
                    config false;
                    description
                        "Operational state data";
                    uses dhcp-snooping-interfaces-binding-info-state;
                    uses dhcp-snooping-interfaces-bridge-binding-ipv6-state;
                } // END of state-container definition.
            } // End of ipv6-entry-list
        } // END of ipv6-entries-container definition.
    } // END of dhcp-snooping-interfaces-source-binding-info-ipv6 definition.
    grouping dhcp-snooping-interfaces-source-binding-info-top {
        description
            "Grouping for DHCP snooping source interfaces binding info";
        container source-binding-info {
            config false;
            description
                "DHCP source binding info by interfaces";
            uses dhcp-snooping-interfaces-source-binding-info-ipv4;
            uses dhcp-snooping-interfaces-source-binding-info-ipv6;
        } // END of source-binding-info-container definition.
    } // END of dhcp-snooping-interfaces-source-binding-info-top definition.
    grouping dhcp-snooping-verify-config {
        description
            "Grouping for DHCP snooping verify on interfaces attributes";
        leaf verify-snooping-vlan  {
            type  empty;
            mandatory true;
            description "Use this command to enable the IPSG feature at the interface level.";
        } // END of verify-snooping-vlan definition.

        leaf verify-access-group-mode  {
            // when " ipi-dhcp-snooping-interface:interfaces/interface/verify/config/verify-snooping-vlan ";
            type  empty;
            description "Use this command to enable the snooping access-group on the interface
                        level.";
        } // END of verify-access-group-mode definition.

    } // END of dhcp-snooping-verify-config definition.
    grouping dhcp-snooping-verify-top {
        description
            "Grouping for DHCP snooping verify on interfaces configurations";
        container verify {
            description
                "DHCP snooping verify on interfaces configurations";
            container config {
                presence "Configure verify-snooping-vlan data";
                description
                    "Configuration data";
                uses dhcp-snooping-verify-config;
            } // END of config-container definition.
            container state {
                config false;
                description
                    "Operational state data";
                uses dhcp-snooping-verify-config;
            } // END of state-container definition.
        } // END of verify-container definition.
    } // END of dhcp-snooping-verify-top definition.
    grouping dhcp-snooping-trust-config {
        description
            "Grouping for DHCP snooping trust interfaces attributes";
        leaf snooping-trust  {
            type  empty;
            description "Use this command to enable the snooping trust on the interface level.";
        } // END of snooping-trust definition.

    } // END of dhcp-snooping-trust-config definition.
    grouping dhcp-snooping-trust-top {
        description
            "Grouping for DHCP snooping trust interfaces configurations";
        container trust {
            description
                "DHCP snooping trust interfaces configurations";
            container config {
                description
                    "Configuration data";
                uses dhcp-snooping-trust-config;
            } // END of config-container definition.
            container state {
                config false;
                description
                    "Operational state data";
                uses dhcp-snooping-trust-config;
            } // END of state-container definition.
        } // END of trust-container definition.
    } // END of dhcp-snooping-trust-top definition.
    grouping dhcp-snooping-interfaces-config {
        description
            "Grouping for DHCP snooping interfaces attributes";
        leaf name  {
            type  leafref {
                path  "/ipi-interface:interfaces/ipi-interface:interface/ipi-interface:name";
            }
            description "Use this command to configured interface name.";
        } // END of name definition.

    } // END of dhcp-snooping-interfaces-config definition.

    grouping  interfaces-grouping {
    description
        "DHCP snooping interfaces configuration";
    container interfaces {
        if-feature feature-list:HAVE_DHCP_SNOOP;
        if-feature feature-list:HAVE_L2;
        description
            "DHCP snooping interfaces configuration";

        list interface {
        // when " ipi-interface:interfaces/interface/config/enable-switchport == '1' + ipi-dhcp-snooping:snooping/snooping-bridges/snooping-bridge/bridge-id ";
            key "name";
            description
                "List of DHCP snooping interfaces";
            leaf name  {
                type  leafref {
                    path  "../config/name";
                }
                description "Use this command to configured interface name.";
            } // END of name definition.

            container config {
                description
                    "Configuration data";
                uses dhcp-snooping-interfaces-config;
            } // END of config-container definition.
            container state {
                config false;
                description
                    "Operational state data";
                uses dhcp-snooping-interfaces-config;
            } // END of state-container definition.
            uses dhcp-snooping-trust-top;
            uses dhcp-snooping-verify-top;
            uses dhcp-snooping-interfaces-binding-info-top;
            uses dhcp-snooping-interfaces-source-binding-info-top;
        } // End of interface-list
    } // END of interfaces-container definition.
    } // END of interfaces-grouping definition.


}
