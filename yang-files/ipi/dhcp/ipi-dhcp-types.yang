/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dhcp-types.yang
*
*/

module ipi-dhcp-types {

    yang-version 1.1;

    namespace   "http://www.ipinfusion.com/yang/ocnos/ipi-dhcp-types";

    prefix "ipi-dhcp-types";

    organization
        "IP Infusion Inc.";

    contact
        "Address: 3965 Freedom Circle, Suite 200, Santa Clara, CA 95054
         Phone: +1 408-400-1900
         E-mail: support@ipinfusion.com
         Web: http://www.ipinfusion.com/";

    description
        "Datamodel for ipi-dhcp types.";


    revision "2026-01-05" {
        description "Updated circuit-id suboption to support IP address format";
        reference " 0.1.3.";
    }

    revision "2025-09-22" {
        description "Added hints in helpstrings about acceptable charecters and acceptable lengths for circuit-id and remote-id";
        reference " 0.1.2.";
    }

    revision "2025-09-11" {
        description "Policy action help string modified.Adding max length of 144 for circuit-id and remote-id.";
        reference " 0.1.1.";
    }

    revision "2025-08-27" {
        description "Initial Version";
        reference " 0.1.0.";
    }



    typedef  dhcp_option82_template_circuit_id_cml_string64_t {
        type string {
            length 2..144;
            pattern "([a-zA-Z0-9_-]+|(([0-9]|[1-9][0-9]|1[0-9]{2}|2[0-4][0-9]|25[0-5])\\.){3}([0-9]|[1-9][0-9]|1[0-9]{2}|2[0-4][0-9]|25[0-5])|[a-fA-F0-9:]+)";
        }
        description "type definition for DHCP_OPTION82_TEMPLATE_CIRCUIT_ID_CML_STRING64_T";
    }

    typedef  dhcp_option82_template_remote_id_cml_string64_t {
        type string {
            length 2..144;
            pattern "[a-zA-Z0-9_-]+";
        }
        description "type definition for DHCP_OPTION82_TEMPLATE_REMOTE_ID_CML_STRING64_T";
    }

    typedef  dhcp_option82_template_policy_t {
        type enumeration {
            enum drop {
                value 1;
                description "Drop the Dhcp packet";
            }
            enum keep {
                value 2;
                description "Keep the Option 82 information";
            }
            enum replace {
                value 3;
                description "Replace the Option 82 information";
            }
        }
        description "type definition for DHCP_OPTION82_TEMPLATE_POLICY_T";
    }

    typedef  dhcp_option82_template_circuit_id_t {
        type enumeration {
            enum hostname-interface-vlanname {
                value 1;
                description "Use hostname and interface name and VLAN as circuit-id";
            }
            enum hostname-relayinterface {
                value 2;
                description "Use hostname and relay interface name as circuit-id";
            }
            enum interface-vlanname {
                value 3;
                description "Use interface and VLAN as circuit-id";
            }
        }
        description "type definition for DHCP_OPTION82_TEMPLATE_CIRCUIT_ID_T";
    }

    typedef  dhcp_option82_template_circuit_id_union_t {
        type union {
            type dhcp_option82_template_circuit_id_t {

            }
            type dhcp_option82_template_circuit_id_cml_string64_t {

            }
        }
        description "type definition for DHCP_OPTION82_TEMPLATE_CIRCUIT_ID_UNION_T";
    }

    typedef  dhcp_option82_template_remote_id_t {
        type enumeration {
            enum hostname {
                value 4;
                description "Use hostname as remote-id";
            }
        }
        description "type definition for DHCP_OPTION82_TEMPLATE_REMOTE_ID_T";
    }

    typedef  dhcp_option82_template_remote_id_union_t {
        type union {
            type dhcp_option82_template_remote_id_t {

            }
            type dhcp_option82_template_remote_id_cml_string64_t {

            }
        }
        description "type definition for DHCP_OPTION82_TEMPLATE_REMOTE_ID_UNION_T";
    }

}
