/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dhcp.yang
*
*/

module ipi-dhcp {

    yang-version 1.1;

    namespace   "http://www.ipinfusion.com/yang/ocnos/ipi-dhcp";

    prefix "ipi-dhcp";

    import cml-data-types {
        prefix cml-data-types;
        revision-date 2026-05-15;
    }

    import ipi-dhcp-relay-types {
        prefix ipi-dhcp-relay-types;
        revision-date 2023-01-11;
    }

    import ietf-inet-types {
        prefix inet;
        revision-date 2013-07-15;
    }

    import ipi-dhcp-types {
        prefix ipi-dhcp-types;
        revision-date 2026-01-05;
    }

    import ipi-dhcp-snooping-types {
        prefix ipi-dhcp-snooping-types;
        revision-date 2022-06-01;
    }

    import feature-list {
        prefix feature-list;
        revision-date 2026-09-15;
    }

    include ipi-dhcp-client { revision-date 2025-04-14;}
    include ipi-dhcp-relay { revision-date 2026-04-01;}
    include ipi-dhcp-server { revision-date 2024-08-13;}
    include ipi-dhcp-snooping { revision-date 2026-01-05;}
    include ipi-dhcp-snooping-interface { revision-date 2024-02-18;}
    organization
        "IP Infusion Inc.";

    contact
        "Address: 3965 Freedom Circle, Suite 200, Santa Clara, CA 95054
         Phone: +1 408-400-1900
         E-mail: support@ipinfusion.com
         Web: http://www.ipinfusion.com/";

    description
        "Feature_dhcp_configuration";


    revision "2026-04-01" {
        description "Added per VRF support for clear ip dhcp realy stats and option stats";
        reference " 0.22.1.";
    }

    revision "2026-01-05" {
        description "Updated circuit-id suboption to support IP address format";
        reference " 0.22.0.";
    }

    revision "2025-12-09" {
        description "Suppressed extra CLI generation";
        reference " 0.21.8.";
    }

    revision "2025-09-22" {
        description "Added hints in helpstrings about acceptable charecters and acceptable lengths for template-name";
        reference " 0.21.7.";
    }

    revision "2025-09-18" {
        description "Added leafref tag for Option82-template-name in IPv4 DHCP relay";
        reference " 0.21.6.";
    }

    revision "2025-09-17" {
        description "Updated cli-sequence for vlan snooping option82-template";
        reference " 0.21.5.";
    }

    revision "2025-09-11" {
        description "Policy action help string modified, Adding max length of 144 for circuit-id and remote-id in types.xml";
        reference " 0.21.4.";
    }

    revision "2025-09-04" {
        description "Removed EVPN_IRB_IF_MODE while configuring IRB interface";
        reference " 0.21.3.";
    }

    revision "2025-08-27" {
        description "Added support for DHCP option82 template creation.";
        reference " 0.21.2.";
    }

    revision "2025-08-25" {
        description "CLI impletementation for DHCP option82 template support";
        reference " 0.21.2.";
    }

    revision "2025-07-27" {
        description "Updated description for IPv6 DHCP Duplicate Clients";
        reference " 0.21.1.";
    }

    revision "2025-06-26" {
        description "Added support for Subscriber-ID for IPv4 DHCP Relay Option";
        reference " 0.21.0.";
    }

    revision "2025-04-17" {
        description "Added support for Gi-addr and Src_IP Option in DHCP realy";
        reference " 0.20.1.";
    }

    revision "2025-04-14" {
        description "Fix compilation warnings";
        reference " 0.20.0.";
    }

    revision "2024-08-13" {
        description "Added util function to both the DHCP server max-lease-time and default-lease-time to ensure input is positive integer";
        reference " 0.19.1.";
    }

    revision "2024-07-15" {
        description "Removed pattern tag validation from dhcp server pool name";
        reference " 0.19.0.";
    }

    revision "2024-04-15" {
        description "Added pattern tag to dhcp server pool name";
        reference " 0.18.0.";
    }

    revision "2024-03-26" {
        description "Added when tag for interfaces config";
        reference " 0.17.1.";
    }

    revision "2024-03-05" {
        description "Added when tag to resolve db-sync issue";
        reference " 0.17.0.";
    }

    revision "2024-02-18" {
        description "Added flag for when tag for container verify,config";
        reference " 0.16.3.";
    }

    revision "2024-02-12" {
        description "Removed implicit_delete tag and added when tag for container verify,config";
        reference " 0.16.2.";
    }

    revision "2024-01-18" {
        description "DHCPv6 Learnt prefix list";
        reference " 0.16.1.";
    }

    revision "2023-12-18" {
        description "DHCPv6 Relay Prefix requirements";
        reference " 0.16.0.";
    }

    revision "2023-08-17" {
        description "Added implicit_delete tag for container verify,config";
        reference " 0.15.0.";
    }

    revision "2023-08-11" {
        description "Added option routers";
        reference " 0.14.0.";
    }

    revision "2023-06-30" {
        description "DHCP Group feature";
        reference " 0.13.0.";
    }

    revision "2023-04-21" {
        description "Added implicit_delete tag for container interfaces, trust, config";
        reference " 0.12.6.";
    }

    revision "2023-04-13" {
        description "updated dhcp-client submodule";
        reference " 0.12.5.";
    }

    revision "2023-03-24" {
        description "updated DHCP server submodule";
        reference " 0.12.4.";
    }

    revision "2023-02-14" {
        description "Removed if-feature to fix SKU build failure in dhcp-client module";
        reference " 0.12.3.";
    }

    revision "2023-02-10" {
        description "Included if-feature to fix SKU build failure in dhcp-client module";
        reference " 0.12.2.";
    }

    revision "2023-01-30" {
        description "Included if-feature to fix SKU build failure";
        reference " 0.12.1.";
    }

    revision "2023-01-23" {
        description "Updated DHCP Server submodule";
        reference " 0.12.0.";
    }

    revision "2023-01-16" {
        description "Updated DHCP server sub module";
        reference " 0.11.9.";
    }

    revision "2023-01-12" {
        description "Updated DHCP relay sub module";
        reference " 0.11.8.";
    }

    revision "2023-01-11" {
        description "Incorrect if-feature flags removed";
        reference " 0.11.7.";
    }

    revision "2023-01-05" {
        description "Leafref correction for config container";
        reference " 0.11.6.";
    }

    revision "2022-12-02" {
        description "Updated DHCP Relay submodule";
        reference " 0.11.5.";
    }

    revision "2022-11-21" {
        description "Updated DHCP Relay/Client submodule";
        reference " 0.11.4.";
    }

    revision "2022-11-16" {
        description "Updated cli prependstr tag in dhcp-server submodule";
        reference " 0.11.2.";
    }

    revision "2022-11-09" {
        description "Updated DHCP Relay/Client submodule";
        reference " 0.11.1.";
    }

    revision "2022-11-08" {
        description "Depcrating Static Source-guard CLIs";
        reference " 0.11.3.";
    }

    revision "2022-11-02" {
        description "DHCP Relay Option82 always-on feature";
        reference " 0.11.0.";
    }

    revision "2022-09-29" {
        description "Updated DHCP Server submodule";
        reference " 0.10.8.";
    }

    revision "2022-09-28" {
        description "Updated DHCP Server submodule";
        reference " 0.10.7.";
    }

    revision "2022-09-22" {
        description "Updated DHCP Server submodule";
        reference " 0.10.6.";
    }

    revision "2022-09-16" {
        description "Update if-feature in DHCP Relay submodule";
        reference " 0.10.5.";
    }

    revision "2022-09-14" {
        description "Updated DHCP Server submodule";
        reference " 0.10.4.";
    }

    revision "2022-08-12" {
        description "Added DHCP Server submodule";
        reference " 0.10.3.";
    }

    revision "2022-08-10" {
        description "Debug hierarchy change added for sub-module ipi-dhcp-snooping";
        reference " 0.10.2.";
    }

    revision "2022-07-31" {
        description "Stop using inet:ipv4-prefix and inet:ipv6-prefix due to Cisco NSO iterop";
        reference " 0.10.1.";
    }

    revision "2022-07-30" {
        description "Updated when expressions in yang";
        reference " 0.10.0.";
    }

    revision "2022-07-15" {
        description "Updated in its sub-module ipi-dhcp-relay";
        reference " 0.9.2.";
    }

    revision "2022-07-04" {
        description "Updated in its sub-module ipi-dhcp-relay";
        reference " 0.9.1.";
    }

    revision "2022-06-01" {
        description "Updated the yang file with feature";
        reference " 0.9.0.";
    }

    revision "2021-12-10" {
        description "Add import to DHCP snooping types yang file";
        reference " 0.8.0.";
    }

    revision "2021-12-07" {
        description "Add dhcp-snooping as a sub-module.";
        reference " 0.7.0.";
    }

    revision "2021-11-30" {
        description "Updated in its sub-module ipi-dhcp-relay";
        reference " 0.6.0.";
    }

    revision "2021-11-17" {
        description "Updated in its sub-module ipi-dhcp-client";
        reference " 0.5.0.";
    }

    revision "2021-09-03" {
        description "Update descriptions of attribute";
        reference " 0.4.0.";
    }

    revision "2021-06-11" {
        description "Changes to support DHCP L3VPN feature";
        reference " 0.3.0.";
    }

    revision "2021-04-01" {
        description "Included new attributes as part of DHCPv6 Relay PD Auto Route injection feature";
        reference " 0.3.0.";
    }

    revision "2020-12-15" {
        description "Change to have data-types in lower case instead of camel case";
        reference " 0.2.0.";
    }

    revision "2020-08-11" {
        description "Initial Version";
        reference " 0.1.0.";
    }

    grouping dhcp-option82-template-top {
        description
            "Top level grouping of option82-templates";
        container option82-templates {
            description
                "Container for option82-templates";

            list option82-template {
                key "template-name";
                max-elements 64;
                description
                    "List of option82 templates";
                leaf template-name  {
                    type  leafref {
                        path  "../config/template-name";
                    }
                    description "This attribute specifies the option82 template name";
                } // END of template-name definition.

                container config {
                    description
                        "Config container for DHCP option82-template";
                    uses dhcp-option82-templates-config;
                } // END of config-container definition.
                container state {
                    config false;
                    description
                        "State container for DHCP option82-template";
                    uses dhcp-option82-templates-config;
                } // END of state-container definition.
            } // End of option82-template-list
        } // END of option82-templates-container definition.
    } // END of dhcp-option82-template-top definition.
    grouping dhcp-option82-templates-config {
        description
            "Grouping of option82-templates";
        leaf template-name  {
            type  string {
                length "1..128";
                pattern "[a-zA-Z0-9][^?' =,>|]*";
            }
            description "Use this attribute to set the option82 template name";
        } // END of template-name definition.

        leaf policy-action  {
            type  ipi-dhcp-types:dhcp_option82_template_policy_t;
            description "Use this attribute to set policy action";
        } // END of policy-action definition.

        leaf circuit-id  {
            type  ipi-dhcp-types:dhcp_option82_template_circuit_id_union_t;
            description "Use this attribute to set circuit-id.";
        } // END of circuit-id definition.

        leaf remote-id  {
            type  ipi-dhcp-types:dhcp_option82_template_remote_id_union_t;
            description "Use this attribute to set remote-id";
        } // END of remote-id definition.

    } // END of dhcp-option82-templates-config definition.
    grouping dhcp-feature-config {
        description
            "Configuration data for feature-dhcp for client and relay";
        leaf disable-dhcp-feature  {
            type  empty;
            description "Disable the DHCP client and DHCP relay on the device.";
        } // END of disable-dhcp-feature definition.

    } // END of dhcp-feature-config definition.
    grouping dhcp-global-top {
        description
            "DHCP global level information grouping";
        container global {
            description
                "DHCP global level information";
            container config {
                description
                    "Configurationd data for feature DHCP";
                uses dhcp-feature-config;
            } // END of config-container definition.
            container state {
                config false;
                description
                    "Operational state data";
                uses dhcp-feature-config;
            } // END of state-container definition.
        } // END of global-container definition.
    } // END of dhcp-global-top definition.

    grouping  dhcp-grouping {
    description
        "Enable feature dhcp";
    container dhcp {
        if-feature feature-list:HAVE_DHCP_CLIENT_OR_HAVE_HOSTPD_OR_HAVE_DHCP_SNOOP;
        description
            "Enable feature dhcp";
        uses dhcp-global-top;
        uses dhcp-option82-template-top;
        uses relay-grouping;
        uses client-grouping;
        uses server-grouping;
        uses snooping-grouping;
    } // END of dhcp-container definition.
    } // END of dhcp-grouping definition.

    uses dhcp-grouping;

    rpc clear-relay-stats {
        if-feature feature-list:HAVE_HOSTPD;
        if-feature feature-list:HAVE_HOSTP_DHCP_RELAY;
        if-feature feature-list:HAVE_DHCP_CLIENT_OR_HAVE_HOSTPD_OR_HAVE_DHCP_SNOOP;
        description "Use this RPC to clear dhcp relay statistics";
        input  {
            leaf vrf-name  {
                type string;
                mandatory true;
                description "VPN routing/forwarding Instance name";
            }
        }
    }

    rpc clear-relay-option-stats {
        if-feature feature-list:HAVE_HOSTPD;
        if-feature feature-list:HAVE_HOSTP_DHCP_RELAY;
        if-feature feature-list:HAVE_DHCP_CLIENT_OR_HAVE_HOSTPD_OR_HAVE_DHCP_SNOOP;
        description "Use this RPC to clear dhcp relay option82 statistics";
        input  {
            leaf vrf-name  {
                type string;
                mandatory true;
                description "VPN routing/forwarding Instance name";
            }
        }
    }

    rpc clear-dhcpv6-pd-route {
        if-feature feature-list:HAVE_HOSTPD;
        if-feature feature-list:HAVE_HOSTP_DHCP_RELAY;
        if-feature feature-list:HAVE_DHCP_CLIENT_OR_HAVE_HOSTPD_OR_HAVE_DHCP_SNOOP;
        description "Use this RPC to clear the DHCP routes";
        input  {
            leaf vrf-name  {
                type string;
                mandatory true;
                description "VPN routing/forwarding Instance name";
            }
        }
    }

    rpc dhcp-snooping-write-database {
        if-feature feature-list:HAVE_DHCP_SNOOP;
        if-feature feature-list:HAVE_L2;
        if-feature feature-list:HAVE_DHCP_CLIENT_OR_HAVE_HOSTPD_OR_HAVE_DHCP_SNOOP;
        description "Save DHCP snooping bind table";
        input  {
            leaf bridge-id  {
                type string {
                    pattern "([1-9]|[12][0-9]|3[0-2])";
                }
                mandatory true;
                description "Bridge group number";
            }
        }
    }

    rpc dhcp-snooping-renew-database {
        if-feature feature-list:HAVE_DHCP_SNOOP;
        if-feature feature-list:HAVE_L2;
        if-feature feature-list:HAVE_DHCP_CLIENT_OR_HAVE_HOSTPD_OR_HAVE_DHCP_SNOOP;
        description "Rebuild DHCP snooping bind table entries for IPv4 and IPv6";
        input  {
            leaf bridge-id  {
                type string {
                    pattern "([1-9]|[12][0-9]|3[0-2])";
                }
                mandatory true;
                description "Bridge group number";
            }
        }
    }

    rpc dhcp-snooping-write-source-binding-database {
        if-feature feature-list:HAVE_DHCP_SNOOP;
        if-feature feature-list:HAVE_L2;
        if-feature feature-list:HAVE_DHCP_CLIENT_OR_HAVE_HOSTPD_OR_HAVE_DHCP_SNOOP;
        description "Save DHCP snooping source guard bind table";
        input  {
            leaf bridge-id  {
                type string {
                    pattern "([1-9]|[12][0-9]|3[0-2])";
                }
                mandatory true;
                description "Bridge group number";
            }
        }
    }

    rpc dhcp-snooping-renew-source-database {
        if-feature feature-list:HAVE_DHCP_SNOOP;
        if-feature feature-list:HAVE_L2;
        if-feature feature-list:HAVE_DHCP_CLIENT_OR_HAVE_HOSTPD_OR_HAVE_DHCP_SNOOP;
        description "Rebuild DHCP snooping source guard bind table entries for IPv4 and
                    IPv6";
        input  {
            leaf bridge-id  {
                type string {
                    pattern "([1-9]|[12][0-9]|3[0-2])";
                }
                mandatory true;
                description "Bridge group number";
            }
        }
    }

    rpc dhcp-snooping-clear-source-binding-database {
        if-feature feature-list:HAVE_DHCP_SNOOP;
        if-feature feature-list:HAVE_L2;
        if-feature feature-list:HAVE_DHCP_CLIENT_OR_HAVE_HOSTPD_OR_HAVE_DHCP_SNOOP;
        description "Clear DHCP snooping source guard binding table entries";
        input  {
            leaf bridge-id  {
                type string {
                    pattern "([1-9]|[12][0-9]|3[0-2])";
                }
                mandatory true;
                description "Bridge group number";
            }
        }
    }

    rpc dhcp-snooping-clear-database {
        if-feature feature-list:HAVE_DHCP_SNOOP;
        if-feature feature-list:HAVE_L2;
        if-feature feature-list:HAVE_DHCP_CLIENT_OR_HAVE_HOSTPD_OR_HAVE_DHCP_SNOOP;
        description "Clear DHCP snooping binding table entries";
        input  {
            leaf bridge-id  {
                type string {
                    pattern "([1-9]|[12][0-9]|3[0-2])";
                }
                mandatory true;
                description "Bridge group number";
            }
        }
    }

    rpc dhcp-snooping-terminal-debug-on {
        if-feature feature-list:HAVE_DHCP_SNOOP;
        if-feature feature-list:HAVE_L2;
        if-feature feature-list:HAVE_DHCP_CLIENT_OR_HAVE_HOSTPD_OR_HAVE_DHCP_SNOOP;
        description "DHCP snooping enable debug terminal";
        input  {
            leaf terminal-debug-options  {
                type ipi-dhcp-snooping-types:dhcp_snooping_debug_t;
                mandatory true;
                description "Enable debug on DHCP snooping feature";
            }
        }
    }

    rpc dhcp-snooping-terminal-debug-off {
        if-feature feature-list:HAVE_DHCP_SNOOP;
        if-feature feature-list:HAVE_L2;
        if-feature feature-list:HAVE_DHCP_CLIENT_OR_HAVE_HOSTPD_OR_HAVE_DHCP_SNOOP;
        description "DHCP snooping disable debug terminal";
        input  {
            leaf terminal-debug-options  {
                type ipi-dhcp-snooping-types:dhcp_snooping_debug_t;
                mandatory true;
                description "Disable debug on DHCP snooping feature";
            }
        }
    }

    notification dhcpv6-relay-pd-route {
        if-feature feature-list:HAVE_HOSTPD;
        if-feature feature-list:HAVE_HOSTP_DHCP_RELAY;

        description "Notification when PD injected routes are added/deleted.";

        leaf severity {
            type cml-data-types:cml_notif_severity_t;
            description "Notification severity level (value: INFO)";
        }

        leaf eventClass {
            type cml-data-types:cml_notif_class_t;
            description "Notification event class (value: STATE)";
        }

        leaf vrf-name {
            type  string;
        description
            "VPN routing/forwarding Instance name";
        }

        leaf interface-name {
            type  string;
        description
            "DHCP client facing interface, which is part of the LAN network";
        }

        leaf state {
            type ipi-dhcp-relay-types:dhcp6_pd_route_state_t;
        description
            "Notification route add/delete input";
        }

        leaf prefix {
            type cml-data-types:cml_ipv6_prefix_t;
        description
            "Delegated prefix";
        }

        leaf next-hop {
            type  inet:ipv6-address;
        description
            "DHCP client interface linklocal adddress";
        }
    }

}
