/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-dhcp-snooping.yang
*
*/

submodule ipi-dhcp-snooping {

    yang-version 1.1;

    belongs-to  ipi-dhcp { prefix ipi-dhcp; }

    import feature-list {
        prefix feature-list;
        revision-date 2026-09-15;
    }

    import cml-data-types {
        prefix cml-data-types;
        revision-date 2026-05-15;
    }

    import ietf-inet-types {
        prefix inet;
        revision-date 2013-07-15;
    }

    import ietf-yang-types {
        prefix yang;
        revision-date 2013-07-15;
    }

    import ipi-interface {
        prefix ipi-interface;
        revision-date 2026-03-10;
    }

    import ipi-network-instance {
        prefix ipi-network-instance;
        revision-date 2026-08-12;
    }

    import ipi-dhcp-snooping-types {
        prefix ipi-dhcp-snooping-types;
        revision-date 2022-06-01;
    }

    include ipi-dhcp-snooping-interface { revision-date 2024-02-18;}
    organization
        "IP Infusion Inc.";

    contact
        "Address: 3965 Freedom Circle, Suite 200, Santa Clara, CA 95054
         Phone: +1 408-400-1900
         E-mail: support@ipinfusion.com
         Web: http://www.ipinfusion.com/";

    description
        "DHCP Snooping configurations";


    revision "2026-01-05" {
        description "Updated circuit-id suboption to support IP address format";
        reference " 0.6.3.";
    }

    revision "2025-09-22" {
        description "Added hints in helpstrings about acceptable charecters and acceptable lengths for template-name";
        reference " 0.6.2.";
    }

    revision "2025-09-17" {
        description "Updated cli-sequence for vlan snooping option82-template";
        reference " 0.6.1.";
    }

    revision "2024-08-25" {
        description "Added support for option82-tempalate-name in DHCP snooping";
        reference " 0.6.0.";
    }

    revision "2023-09-18" {
        description "Updated leaf name as validate-mac";
        reference " 0.5.1.";
    }

    revision "2023-01-11" {
        description "Incorrect if-feature flags removed";
        reference " 0.5.0.";
    }

    revision "2022-11-08" {
        description "Depcrating Static Source-guard CLIs";
        reference " 0.4.0.";
    }

    revision "2022-08-10" {
        description "Debug hierarchy change";
        reference " 0.3.0.";
    }

    revision "2022-06-01" {
        description "Updated the yang file with feature";
        reference " 0.2.2.";
    }

    revision "2021-12-10" {
        description "Add support to debug terminal";
        reference " 0.2.1.";
    }

    revision "2021-12-07" {
        description "Restructured module as per open-config";
        reference " 0.2.0.";
    }

    revision "2018-06-21" {
        description "Initial Version";
        reference " 0.1.0.";
    }

    grouping dhcp-snooping-bridge-arp-inspection-config {
        description
            "Grouping for DHCP snooping bridges arp inspection attributes";
        leaf enable  {
            type  empty;
            mandatory true;
            description "Use this command to enable/disable arp-inspection on the bridge.";
        } // END of enable definition.

        leaf validate-mac  {
            type  ipi-dhcp-snooping-types:dhcp_snooping_validation_t;
            description "Use this command to enable validation of the source-mac,
                        destination-mac, or IP address field in the ARP packet payload.";
        } // END of validate-mac definition.

        leaf vlan-range  {
            type  cml-data-types:cml_range_t;
            description "Use this command to enable ARP inspection on the VLAN in a bridge.";
        } // END of vlan-range definition.

    } // END of dhcp-snooping-bridge-arp-inspection-config definition.
    grouping dhcp-snooping-bridge-arp-inspection-counters {
        description
            "Grouping for DHCP snooping bridges counters";
        container counters {
            config false;
            description
                "DHCP snooping counters";
            leaf forwarded  {
                type  yang:counter32;
                description "This attribute to returns counters for ARP inspection forwarded.";
            } // END of forwarded definition.

            leaf dropped  {
                type  yang:counter32;
                description "This attribute to returns counters for ARP inspection dropped.";
            } // END of dropped definition.

        } // END of counters-container definition.
    } // END of dhcp-snooping-bridge-arp-inspection-counters definition.
    grouping dhcp-snooping-bridge-arp-inspection-top {
        description
            "Grouping for DHCP snooping bridges arp inspection";
        container arp-inspection {
            description
                "DHCP snooping arp inspection";
            container config {
                presence "Configure arp-inspection";
                description
                    "Configuration data";
                uses dhcp-snooping-bridge-arp-inspection-config;
            } // END of config-container definition.
            container state {
                config false;
                description
                    "Operational state data";
                uses dhcp-snooping-bridge-arp-inspection-config;
                uses dhcp-snooping-bridge-arp-inspection-counters;
            } // END of state-container definition.
        } // END of arp-inspection-container definition.
    } // END of dhcp-snooping-bridge-arp-inspection-top definition.
    grouping dhcp-snooping-bridge-source-mac-address-interface-config {
        description
            "Grouping for DHCP snooping interface attributes for source MAC address";
        leaf if-name  {
            type  leafref {
                path  "/ipi-interface:interfaces/ipi-interface:interface/ipi-interface:name";
            }
            mandatory true;
            description "Use this attribute to set the interface name";
        } // END of if-name definition.

    } // END of dhcp-snooping-bridge-source-mac-address-interface-config definition.
    grouping dhcp-snooping-bridge-ipv4-address-config {
        description
            "Grouping for DHCP snooping IPv4 address attributes";
        leaf ipv4-address  {
            type  inet:ipv4-address;
            mandatory true;
            description "Use this attribute to set the IPv4 address";
        } // END of ipv4-address definition.

    } // END of dhcp-snooping-bridge-ipv4-address-config definition.
    grouping dhcp-snooping-bridge-ipv6-address-config {
        description
            "Grouping for DHCP snooping IPv6 address attributes";
        leaf ipv6-address  {
            type  inet:ipv6-address;
            mandatory true;
            description "Use this attribute to set the ipv6 address";
        } // END of ipv6-address definition.

    } // END of dhcp-snooping-bridge-ipv6-address-config definition.
    grouping dhcp-snooping-bridge-mac-address-config {
        description
            "Grouping for DHCP snooping MAC address attributes";
        leaf mac-address  {
            type  cml-data-types:cml_mac_addr_t {
                length "1..1965";
                pattern "[0-9a-fA-F]{4}\\.[0-9a-f]{4}\\.[0-9a-f]{4}";
            }
            description "Use this attribute to set the MAC address";
        } // END of mac-address definition.

    } // END of dhcp-snooping-bridge-mac-address-config definition.
    grouping dhcp-snooping-bridge-binding-info-state {
        description
            "Grouping for DHCP snooping bridge binding info attributes";
        leaf mac-address  {
            type  cml-data-types:cml_mac_addr_t {
                length "1..1965";
            }
            description "This attribute returns the DHCP snooping binding mac-address";
        } // END of mac-address definition.

        leaf lease-time  {
            type  uint32;
            description "This attribute returns the lease-time";
        } // END of lease-time definition.

        leaf type  {
            type  ipi-dhcp-snooping-types:dhcp_snooping_binding_type_t;
            description "This attribute returns the DHCP snooping binding type";
        } // END of type definition.

        leaf if-name  {
            type  string {
                length "1..1965";
                pattern "[^?' =,>|]+";
            }
            description "This attribute returns the dhcp-snooping binding interface name";
        } // END of if-name definition.

    } // END of dhcp-snooping-bridge-binding-info-state definition.
    grouping dhcp-snooping-bridge-binding-ipv6-state {
        description
            "Grouping for DHCP snooping bridges source binding ipv6 address";
        leaf ip-address  {
            type  inet:ipv6-address;
            description "This attribute returns the IPv6 address binded";
        } // END of ip-address definition.

    } // END of dhcp-snooping-bridge-binding-ipv6-state definition.
    grouping dhcp-snooping-bridge-binding-ipv4-state {
        description
            "Grouping for DHCP snooping bridges source binding IPv4 address";
        leaf ip-address  {
            type  inet:ipv4-address;
            description "This attribute returns the IPv4 address binded";
        } // END of ip-address definition.

    } // END of dhcp-snooping-bridge-binding-ipv4-state definition.
    grouping dhcp-snooping-bridge-binding-info-top {
        description
            "Grouping for DHCP snooping bridges source binding info";
        container snooping-binding-info {
            config false;
            description
                "DHCP snooping binding info by source binding";

            list ipv4 {
                key "mac-address ip-address";
                config false;
                description
                    "List of IPv4 and MAC addresses binded";
                leaf mac-address  {
                    type  leafref {
                        path  "../state/mac-address";
                    }
                    description "This attribute returns the mac-address binded";
                } // END of mac-address definition.

                leaf ip-address  {
                    type  leafref {
                        path  "../state/ip-address";
                    }
                    description "This attribute returns the ip-address binded";
                } // END of ip-address definition.

                container state {
                    config false;
                    description
                        "Operational state data";
                    uses dhcp-snooping-bridge-binding-info-state;
                    uses dhcp-snooping-bridge-binding-ipv4-state;
                } // END of state-container definition.
            } // End of ipv4-list

            list ipv6 {
                if-feature feature-list:HAVE_IPV6;
                key "mac-address ip-address";
                config false;
                description
                    "List of ipv6 and MAC addresses binded";
                leaf mac-address  {
                    type  leafref {
                        path  "../state/mac-address";
                    }
                    description "This attribute returns the mac-address binded";
                } // END of mac-address definition.

                leaf ip-address  {
                    type  leafref {
                        path  "../state/ip-address";
                    }
                    description "This attribute returns the ip-address binded";
                } // END of ip-address definition.

                container state {
                    config false;
                    description
                        "Operational state data";
                    uses dhcp-snooping-bridge-binding-info-state;
                    uses dhcp-snooping-bridge-binding-ipv6-state;
                } // END of state-container definition.
            } // End of ipv6-list
        } // END of snooping-binding-info-container definition.
    } // END of dhcp-snooping-bridge-binding-info-top definition.
    grouping dhcp-snooping-bridge-config {
        description
            "Grouping for DHCP snooping bridges attributes";
        leaf snooping-enable  {
            type  empty;
            mandatory true;
            description "Enable DHCP snooping feature";
        } // END of snooping-enable definition.

        leaf bridge-id  {
            type  leafref {
                path  "/ipi-network-instance:network-instances/ipi-network-instance:network-instance/ipi-network-instance:instance-name";
            }
            description "Bridge group number";
        } // END of bridge-id definition.

        leaf verify-mac-address  {
            // when " ipi-dhcp-snooping:snooping/snooping-bridges/snooping-bridge/config/snooping-enable ";
            type  empty;
            description "Use this command to enable MAC address verification.";
        } // END of verify-mac-address definition.

        leaf option-82-enable  {
            // when " ipi-dhcp-snooping:snooping/snooping-bridges/snooping-bridge/config/snooping-enable ";
            type  empty;
            description "Use this command to insert interface and VLAN name in the option 82
                        field in DHCP packets.";
        } // END of option-82-enable definition.

        leaf write-delay  {
            // when " ipi-dhcp-snooping:snooping/snooping-bridges/snooping-bridge/config/snooping-enable ";
            type  uint32 {
                 range "20..86400"  {
                    description "20..86400: Supported range 20 - 86400";
                 }
            }
            units "seconds";
            default "300";
            description "Configure DHCP snooping database write delay in multiples of 10
                        seconds";
        } // END of write-delay definition.

        leaf strict-validation  {
            // when " ipi-dhcp-snooping:snooping/snooping-bridges/snooping-bridge/config/snooping-enable ";
            type  empty;
            description "Use this command to enable strict validation of DHCP packets.";
        } // END of strict-validation definition.

    } // END of dhcp-snooping-bridge-config definition.
    grouping dhcp-snooping-bridge-binding-entry-config {
        description
            "Grouping for DHCP snooping bridges binding entry attributes";
        leaf vlan-id  {
            type  uint16 {
                 range "1..4094"  {
                    description "1..4094: Supported range 1 - 4094";
                 }
            }
            description "Use this attribute to set the vlan-id";
        } // END of vlan-id definition.

    } // END of dhcp-snooping-bridge-binding-entry-config definition.
    grouping dhcp-snooping-bridge-binding-statistics {
        description
            "Grouping for DHCP snooping binding statistics";
        leaf static-entries-ipv4  {
            type  yang:counter32;
            description "This attribute returns the number of static entries for IPv4";
        } // END of static-entries-ipv4 definition.

        leaf dynamic-entries-ipv4  {
            type  yang:counter32;
            description "This attribute returns the number of dynamic entries for IPv4";
        } // END of dynamic-entries-ipv4 definition.

        leaf static-entries-ipv6  {
            if-feature feature-list:HAVE_IPV6;
            type  yang:counter32;
            description "This attribute returns the number of static entries for IPv6";
        } // END of static-entries-ipv6 definition.

        leaf dynamic-entries-ipv6  {
            if-feature feature-list:HAVE_IPV6;
            type  yang:counter32;
            description "This attribute returns the number of dynamic entries for IPv6";
        } // END of dynamic-entries-ipv6 definition.

    } // END of dhcp-snooping-bridge-binding-statistics definition.
    grouping dhcp-snooping-bridge-binding-statistics-top {
        description
            "Grouping for DHCP snooping binding statistics";
        container statistics {
            config false;
            description
                "DHCP snooping binding info by interfaces";
            uses dhcp-snooping-bridge-binding-statistics;
        } // END of statistics-container definition.
    } // END of dhcp-snooping-bridge-binding-statistics-top definition.
    grouping dhcp-snooping-bridge-interface-config {
        description
            "Grouping for DHCP snooping interface attributes";
        leaf if-name  {
            type  leafref {
                path  "/ipi-interface:interfaces/ipi-interface:interface/ipi-interface:name";
            }
            mandatory true;
            description "Use this attribute to set the interface name";
        } // END of if-name definition.

    } // END of dhcp-snooping-bridge-interface-config definition.
    grouping dhcp-snooping-bridge-option82-template-top {
        description
            "Top level grouping for vlan-option82 template mapping";
        container vlan-option82-template-mappings {
            description
                "Top level container for vlan-option82 template mapping";

            list vlan-option82-template-mapping {
                key "vlan-range";
                description
                    "List of vlan option82 template mappings";
                leaf vlan-range  {
                    type  leafref {
                        path  "../config/vlan-range";
                    }
                    description "vlan-range on which DHCP snooping needs to be enabled..";
                } // END of vlan-range definition.

                container config {
                    presence "yes";
                    description
                        "Configuration data";
                    uses dhcp-snooping-bridge-option82-template-config;
                } // END of config-container definition.
                container state {
                    config false;
                    description
                        "Operational state data";
                    uses dhcp-snooping-bridge-option82-template-config;
                } // END of state-container definition.
            } // End of vlan-option82-template-mapping-list
        } // END of vlan-option82-template-mappings-container definition.
    } // END of dhcp-snooping-bridge-option82-template-top definition.
    grouping dhcp-snooping-bridge-option82-template-config {
        description
            "Grouping for DHCP snooping bridges option82 attributes";
        leaf option82-template-name  {
            type  string {
                length "1..32";
                pattern "[a-zA-Z0-9_-]+";
            }
            description "option82 template name to map to vlan.";
        } // END of option82-template-name definition.

        leaf vlan-range  {
            type  cml-data-types:cml_range_t;
            description "vlan-range on which DHCP snooping needs to be enabled..";
        } // END of vlan-range definition.

    } // END of dhcp-snooping-bridge-option82-template-config definition.
    grouping dhcp-snooping-bridge-mac-address-ipv4-top {
        description
            "Grouping for DHCP snooping bridge MAC address configuration";
        container mac-addresses-ipv4 {
            description
                "DHCP snooping MAC addresses configuration";

            list mac-address-ipv4 {
                key "mac-address";
                description
                    "List of MAC addresses";
                leaf mac-address  {
                    type  leafref {
                        path  "../config/mac-address";
                    }
                    description "Use this attribute to set the MAC address";
                } // END of mac-address definition.

                container config {
                    description
                        "Configuration data";
                    uses dhcp-snooping-bridge-mac-address-config;
                    uses dhcp-snooping-bridge-ipv4-address-config;
                    uses dhcp-snooping-bridge-interface-config;
                } // END of config-container definition.
                container state {
                    config false;
                    description
                        "Operational state data";
                    uses dhcp-snooping-bridge-mac-address-config;
                    uses dhcp-snooping-bridge-ipv4-address-config;
                    uses dhcp-snooping-bridge-interface-config;
                } // END of state-container definition.
            } // End of mac-address-ipv4-list
        } // END of mac-addresses-ipv4-container definition.
    } // END of dhcp-snooping-bridge-mac-address-ipv4-top definition.
    grouping dhcp-snooping-bridge-mac-address-ipv6-top {
        description
            "Grouping for DHCP snooping bridge MAC address configuration";
        container mac-addresses-ipv6 {
            if-feature feature-list:HAVE_IPV6;
            description
                "DHCP snooping MAC addresses configuration";

            list mac-address-ipv6 {
                key "mac-address";
                description
                    "List of MAC addresses";
                leaf mac-address  {
                    type  leafref {
                        path  "../config/mac-address";
                    }
                    description "Use this attribute to set the MAC address";
                } // END of mac-address definition.

                container config {
                    description
                        "Configuration data";
                    uses dhcp-snooping-bridge-mac-address-config;
                    uses dhcp-snooping-bridge-ipv6-address-config;
                    uses dhcp-snooping-bridge-interface-config;
                } // END of config-container definition.
                container state {
                    config false;
                    description
                        "Operational state data";
                    uses dhcp-snooping-bridge-mac-address-config;
                    uses dhcp-snooping-bridge-ipv6-address-config;
                    uses dhcp-snooping-bridge-interface-config;
                } // END of state-container definition.
            } // End of mac-address-ipv6-list
        } // END of mac-addresses-ipv6-container definition.
    } // END of dhcp-snooping-bridge-mac-address-ipv6-top definition.
    grouping dhcp-snooping-bridge-vlans-top {
        description
            "Grouping for DHCP snooping bridges VLANs configuration";
        container vlans {
            description
                "DHCP snooping bridge VLANs configuration";

            list vlan {
                key "vlan-id";
                description
                    "List of DHCP snooping VLANs";
                leaf vlan-id  {
                    type  leafref {
                        path  "../config/vlan-id";
                    }
                    description "Use this attribute to set the vlan-id";
                } // END of vlan-id definition.

                container config {
                    description
                        "Configuration data";
                    uses dhcp-snooping-bridge-binding-entry-config;
                } // END of config-container definition.
                container state {
                    config false;
                    description
                        "Operational state data";
                    uses dhcp-snooping-bridge-binding-entry-config;
                    uses dhcp-snooping-bridge-binding-statistics-top;
                } // END of state-container definition.
                uses dhcp-snooping-bridge-mac-address-ipv4-top;
                uses dhcp-snooping-bridge-mac-address-ipv6-top;
                uses dhcp-snooping-bridge-binding-info-top;
            } // End of vlan-list
        } // END of vlans-container definition.
    } // END of dhcp-snooping-bridge-vlans-top definition.
    grouping dhcp-snooping-bridge-top {
        description
            "Grouping for DHCP snooping bridges configuration";
        container snooping-bridges {
            description
                "Snooping bridges configuration";

            list snooping-bridge {
            // when " ipi-dhcp-snooping:snooping/snooping-bridges/snooping-bridge/config/snooping-enable ";
                key "bridge-id";
                description
                    "List of DHCP snooping bridges";
                leaf bridge-id  {
                    type  leafref {
                        path  "../config/bridge-id";
                    }
                    description "Bridge group number";
                } // END of bridge-id definition.

                container config {
                    presence "Configure snooping-bridge";
                    description
                        "Configuration data";
                    uses dhcp-snooping-bridge-config;
                } // END of config-container definition.
                container state {
                    config false;
                    description
                        "Operational state data";
                    uses dhcp-snooping-bridge-config;
                } // END of state-container definition.
                uses dhcp-snooping-bridge-arp-inspection-top;
                uses dhcp-snooping-bridge-option82-template-top;
                uses dhcp-snooping-bridge-vlans-top;
            } // End of snooping-bridge-list
        } // END of snooping-bridges-container definition.
    } // END of dhcp-snooping-bridge-top definition.
    grouping dhcp-snooping-debug-config {
        description
            "Grouping for DHCP snooping debug attributes";
        leaf options  {
            type  ipi-dhcp-snooping-types:dhcp_snooping_debug_t;
            description "Use this attribute to debug the DHCP snooping feature.";
        } // END of options definition.

    } // END of dhcp-snooping-debug-config definition.
    grouping dhcp-snooping-debug-terminal-state {
        description
            "Grouping for terminal debug operational state";
        leaf terminal-debug-status  {
            type  ipi-dhcp-snooping-types:dhcp_snooping_debug_t;
            description "Use this attribute to debug the DHCP snooping feature in terminal.";
        } // END of terminal-debug-status definition.

    } // END of dhcp-snooping-debug-terminal-state definition.
    grouping dhcp-snooping-debug-top {
        description
            "Grouping for DHCP snooping debug configuration";
        container debug {
            description
                "Debugging functions";
            container config {
                description
                    "Configuration data";
                uses dhcp-snooping-debug-config;
            } // END of config-container definition.
            container state {
                config false;
                description
                    "Operational state data";
                uses dhcp-snooping-debug-config;
                uses dhcp-snooping-debug-terminal-state;
            } // END of state-container definition.
        } // END of debug-container definition.
    } // END of dhcp-snooping-debug-top definition.

    grouping  snooping-grouping {
    description
        "DHCP snooping configurations";
    container snooping {
        if-feature feature-list:HAVE_DHCP_SNOOP;
        if-feature feature-list:HAVE_L2;
        description
            "DHCP snooping configurations";
        uses dhcp-snooping-debug-top;
        uses dhcp-snooping-bridge-top;
        uses interfaces-grouping;
    } // END of snooping-container definition.
    } // END of snooping-grouping definition.


}
