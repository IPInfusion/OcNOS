/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mac-list.yang
*
*/

module ipi-mac-list {

    yang-version 1.1;

    namespace   "http://www.ipinfusion.com/yang/ocnos/ipi-mac-list";

    prefix "ipi-mac-list";

    import ipi-mac-list-types {
        prefix ipi-mac-list-types;
        revision-date 2025-08-05;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-mac-list";


    revision "2025-11-20" {
        description "Added utilfunc for mac-address and mac-addr-mask";
        reference " 0.1.1.";
    }

    revision "2025-08-05" {
        description "Initial Version";
        reference " 0.1.0.";
    }

    grouping mac-list-common {
        description
            "Configuration data for mac-lists";
        leaf mac-list-name  {
            type  string {
                length "1..1965";
                pattern "[a-zA-Z0-9][^?' =,>|]*";
            }
            description "Name of the MAC list";
        } // END of mac-list-name definition.

    } // END of mac-list-common definition.
    grouping sequence-entry {
        description
            "Configuration data for mac-list sequence";
        leaf sequence-id  {
            type  uint32 {
                 range "1..4294967295"  {
                    description "1..4294967295: Supported range 1 - 4294967295";
                 }
            }
            description "Sequence number of the MAC list";
        } // END of sequence-id definition.

    } // END of sequence-entry definition.
    grouping mac-list-seq {
        description
            "Configuration data for mac-list sequence";
        leaf action  {
            type  ipi-mac-list-types:mac_list_action_t;
            description "Action to be taken - Permit or Deny";
        } // END of action definition.

        leaf mac-addr  {
            type  ipi-mac-list-types:maclist_mac_addr_t {
                length "1..1965";
            }
            description "Mac Address";
        } // END of mac-addr definition.

        leaf mac-addr-mask  {
            type  ipi-mac-list-types:maclist_mac_mask_t {
                length "1..1965";
            }
            description "Mac Address Mask";
        } // END of mac-addr-mask definition.

    } // END of mac-list-seq definition.
    grouping mac-list-sequence {
        description
            "Configuration data for mac-list sequence";
        container mac-entries {
            description
                "List of sequences";

            list mac-entry {
                key "sequence-id";
                description
                    "List of sequences";
                leaf sequence-id  {
                    type  leafref {
                        path  "../config/sequence-id";
                    }
                    description "Sequence number of the MAC list";
                } // END of sequence-id definition.

                container config {
                    description
                        "Configuration data for mac-list sequence";
                    uses sequence-entry;
                } // END of config-container definition.
                container state {
                    config false;
                    description
                        "Operational state data";
                    uses sequence-entry;
                } // END of state-container definition.
                uses mac-list-network;
            } // End of mac-entry-list
        } // END of mac-entries-container definition.
    } // END of mac-list-sequence definition.
    grouping mac-list-network {
        description
            "mac-list network information";
        container mac {
            description
                "mac-list network information";

            list entry {
                key "action mac-addr mac-addr-mask";
                description
                    "mac-list network information";
                leaf action  {
                    type  leafref {
                        path  "../config/action";
                    }
                    description "Action to be taken - Permit or Deny";
                } // END of action definition.

                leaf mac-addr  {
                    type  leafref {
                        path  "../config/mac-addr";
                    }
                    description "Mac Address";
                } // END of mac-addr definition.

                leaf mac-addr-mask  {
                    type  leafref {
                        path  "../config/mac-addr";
                    }
                    description "Mac Address Mask";
                } // END of mac-addr-mask definition.

                container config {
                    description
                        "Configuration data for mac-list sequence";
                    uses mac-list-seq;
                } // END of config-container definition.
                container state {
                    config false;
                    description
                        "Operational state data";
                    uses mac-list-seq;
                } // END of state-container definition.
            } // End of entry-list
        } // END of mac-container definition.
    } // END of mac-list-network definition.
    grouping mac-list-top {
        description
            "Top level grouping for mac-list";

        list mac-address {
            key "mac-list-name";
            description
                "mac-list configurations";
            leaf mac-list-name  {
                type  leafref {
                    path  "../config/mac-list-name";
                }
                description "mac-list name";
            } // END of mac-list-name definition.

            container config {
                description
                    "Configuration data for MAC list";
                uses mac-list-common;
            } // END of config-container definition.
            container state {
                config false;
                description
                    "Operational state data";
                uses mac-list-common;
            } // END of state-container definition.
            uses mac-list-sequence;
        } // End of mac-address-list
    } // END of mac-list-top definition.

    grouping  mac-addresses-grouping {
    description
        "Mac-list information";
    container mac-addresses {
        description
            "Mac-list information";
        uses mac-list-top;
    } // END of mac-addresses-container definition.
    } // END of mac-addresses-grouping definition.

    uses mac-addresses-grouping;

}
