/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mac-list-types.yang
*
*/

module ipi-mac-list-types {

    yang-version 1.1;

    namespace   "http://www.ipinfusion.com/yang/ocnos/ipi-mac-list-types";

    prefix "ipi-mac-list-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-mac-list-types";


    revision "2025-08-05" {
        description "Initial Version";
        reference " 0.1.0.";
    }



    typedef  mac_list_action_t {
        type enumeration {
            enum deny {
                value 1;
                description "Specify packets to reject";
            }
            enum permit {
                value 2;
                description "Specify packets to forward";
            }
        }
        description "type definition for MAC_LIST_ACTION_T";
    }

    typedef  maclist_mac_addr_t {
        type string {
            pattern "[0-9a-fA-F]{4}\\.[0-9a-fA-F]{4}\\.[0-9a-fA-F]{4}";
        }
        description "type definition for MACLIST_MAC_ADDR_T";
    }

    typedef  maclist_mac_mask_t {
        type string {
            pattern "[0-9a-fA-F]{4}\\.[0-9a-fA-F]{4}\\.[0-9a-fA-F]{4}";
        }
        description "type definition for MACLIST_MAC_MASK_T";
    }

}
