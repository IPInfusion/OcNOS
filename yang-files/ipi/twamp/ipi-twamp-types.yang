/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-twamp-types.yang
*
*/

module ipi-twamp-types {

    yang-version 1.1;

    namespace   "http://www.ipinfusion.com/yang/ocnos/ipi-twamp-types";

    prefix "ipi-twamp-types";

    import cml-data-types {
        prefix cml-data-types;
        revision-date 2026-05-15;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Two-Way Active Measurement Protocol (TWAMP) types";


    revision "2025-10-20" {
        description "Improved CLI validation for twamp session sender-ip and reflector-ip to accept all valid input formats";
        reference " 0.5.3.";
    }

    revision "2025-09-17" {
        description "Added validation for hostname and IPv4 address formats to the TWAMP_HOSTPNAME_T data type";
        reference " 0.5.2.";
    }

    revision "2025-05-01" {
        description "Removed the HAVE_TWAMP from the managedObjectClass top level and added it at the datatype to be able to use the datatypes in IGP TE module";
        reference " 0.5.1.";
    }

    revision "2025-03-22" {
        description "Added datatype for TWAMP Session for IPv4 and HOSTNAME inputs";
        reference " 0.5.0.";
    }

    revision "2023-05-12" {
        description "Added a new type for start time";
        reference " 0.4.0.";
    }

    revision "2022-07-05" {
        description "Added a new type for source UDP port";
        reference " 0.3.0.";
    }

    revision "2022-06-01" {
        description "Updated the yang file with feature";
        reference " 0.2.0.";
    }

    revision "2021-09-10" {
        description "Restructured module in accordance with OpenConfig style";
        reference " 0.1.0.";
    }



    typedef  twamp_dscp_class_type_t {
        type enumeration {
            enum default {
                value 0;
                description "Default dscp (000000) decimal value 0";
            }
            enum cs1 {
                value 8;
                description "CS1 (precedence 1) dscp (001000) decimal value 8";
            }
            enum af11 {
                value 10;
                description "AF11 dscp (001010) decimal value 10";
            }
            enum af12 {
                value 12;
                description "AF12 dscp (001100) decimal value 12";
            }
            enum af13 {
                value 14;
                description "AF13 dscp (001110) decimal value 14";
            }
            enum cs2 {
                value 16;
                description "CS2 (precedence 2) dscp (010000) decimal value 16";
            }
            enum af21 {
                value 18;
                description "AF21 dscp (010010) decimal value 18";
            }
            enum af22 {
                value 20;
                description "AF22 dscp (010100) decimal value 20";
            }
            enum af23 {
                value 22;
                description "AF23 dscp (010110) decimal value 22";
            }
            enum cs3 {
                value 24;
                description "CS3 (precedence 3) dscp (011000) decimal value 24";
            }
            enum af31 {
                value 26;
                description "AF31 dscp (011010) decimal value 26";
            }
            enum af32 {
                value 28;
                description "AF32 dscp (011100) decimal value 28";
            }
            enum af33 {
                value 30;
                description "AF33 dscp (011110) decimal value 30";
            }
            enum cs4 {
                value 32;
                description "CS4 (precedence 4) dscp (100000) decimal value 32";
            }
            enum af41 {
                value 34;
                description "AF41 dscp (100010) decimal value 34";
            }
            enum af42 {
                value 36;
                description "AF42 dscp (100100) decimal value 36";
            }
            enum af43 {
                value 38;
                description "AF43 dscp (100110) decimal value 38";
            }
            enum cs5 {
                value 40;
                description "CS5 (precedence 5) dscp (101000) decimal value 40";
            }
            enum ef {
                value 46;
                description "EF dscp (101110) decimal value 46";
            }
            enum cs6 {
                value 48;
                description "CS6 (precedence 6) dscp (110000) decimal value 48";
            }
            enum cs7 {
                value 56;
                description "CS7 (precedence 7) dscp (111000) decimal value 56";
            }
        }
        description "type definition for TWAMP_DSCP_CLASS_TYPE_T";
    }

    typedef  twamp_dscp_t {
        type union {
            type twamp_dscp_class_type_t {

            }
            type int8 {
                range "0..63";

            }
        }
        description "type definition for TWAMP_DSCP_T";
    }

    typedef  twamp_default_udp_port_t {
        type enumeration {
            enum 862 {
                value 862;
                description "Default UDP Port";
            }
        }
        description "type definition for TWAMP_DEFAULT_UDP_PORT_T";
    }

    typedef  twamp_empty_udp_port_t {
        type enumeration {
            enum 0 {
                value 0;
                description "No source port filtering";
            }
        }
        description "type definition for TWAMP_EMPTY_UDP_PORT_T";
    }

    typedef  twamp_udp_port_t {
        type union {
            type twamp_default_udp_port_t {

            }
            type uint16 {
                range "1025..65535";

            }
        }
        description "type definition for TWAMP_UDP_PORT_T";
    }

    typedef  twamp_ref_src_udp_port_t {
        type union {
            type twamp_empty_udp_port_t {

            }
            type twamp_default_udp_port_t {

            }
            type uint16 {
                range "1025..65535";

            }
        }
        description "type definition for TWAMP_REF_SRC_UDP_PORT_T";
    }

    typedef  twamp_debug_t {
        type enumeration {
            enum twamp {
                value 1;
                description "TWAMP Two-may Active Measurement Protocol ";
            }
        }
        description "type definition for TWAMP_DEBUG_T";
    }

    typedef  twamp_hostname_t {
        type union {
            type inet:ipv4-address {

            }
            type inet:ipv6-address {

            }
            type cml-data-types:cml_host_string_t {

            }
        }
        description "type definition for TWAMP_HOSTNAME_T";
    }

    typedef  twamp_date_time_t {
        type string {
            pattern "([0-9]|[01][0-9]|2[0123]):([0-9]|[012345][0-9]):([0-9]|[012345][0-9]) (([12][0-9])|(3[01])|([0][1-9])) ((([a-z])|([A-Z])){2,8}) ((199[5-9])|(20[012][0-9])|(203[0-5]))";
        }
        description "type definition for TWAMP_DATE_TIME_T";
    }

    typedef  twamp_hostpname_t {
        type union {
            type string {

            }
            type inet:ipv4-address {

            }
        }
        description "type definition for TWAMP_HOSTPNAME_T";
    }

}
