/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-twamp-client.yang
*
*/

submodule ipi-twamp-client {

    yang-version 1.1;

    belongs-to  ipi-twamp { prefix ipi-twamp; }

    import feature-list {
        prefix feature-list;
        revision-date 2026-09-15;
    }

    import ipi-twamp-types {
        prefix ipi-twamp-types;
        revision-date 2025-10-20;
    }

    import ietf-yang-types {
        prefix yang;
        revision-date 2013-07-15;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Two-Way Active Measurement Protocol (TWAMP)";


    revision "2025-10-20" {
        description "Improved CLI validation for twamp session sender-ip and reflector-ip to accept all valid input formats";
        reference " 0.4.1.";
    }

    revision "2025-09-18" {
        description "Increased maximum-sessions range to scaled up values on Q2";
        reference " 0.4.0.";
    }

    revision "2025-09-17" {
        description "Added validation for hostname and IPv4 address formats to the TWAMP_HOSTPNAME_T data type";
        reference " 0.3.2.";
    }

    revision "2025-02-13" {
        description "Limited session name to 128 characters long";
        reference " 0.3.1.";
    }

    revision "2025-02-03" {
        description "Added SNMP Traps support for TWAMP";
        reference " 0.3.0.";
    }

    revision "2025-01-22" {
        description "Fixed checking the value of the control admin state when creating a session";
        reference " 0.2.3.";
    }

    revision "2025-01-20" {
        description "Correct twamp session attributes description";
        reference " 0.2.2.";
    }

    revision "2024-12-12" {
        description "Added ignore snmp generation tag";
        reference " 0.2.1.";
    }

    revision "2024-11-21" {
        description "Fixed maximum values ranges for sessions and connections to start from 1 instead of 0";
        reference " 0.2.0.";
    }

    revision "2024-03-27" {
        description "Added pattern checking for connection and session names";
        reference " 0.1.3.";
    }

    revision "2023-09-06" {
        description "Added Reset CLI for the dead sessions";
        reference " 0.1.2.";
    }

    revision "2023-08-31" {
        description "Remove unnecessary import";
        reference " 0.1.1.";
    }

    revision "2023-05-12" {
        description "Initial Version";
        reference " 0.1.0.";
    }

    grouping twamp-client-global-config {
        description
            "Grouping for twamp client global configurations";
        leaf enable  {
            type  empty;
            mandatory true;
            description "Enables TWAMP Client";
        } // END of enable definition.

        leaf maximum-sessions  {
            type  uint16 {
                 range "1..2000"  {
                    description "1..2000: Supported range 1 - 2000";
                 }
            }
            description "Maximum number of test sessions for the whole client node (default =
                        64)";
        } // END of maximum-sessions definition.

        leaf maximum-connections  {
            type  uint8 {
                 range "1..64"  {
                    description "1..64: Supported range 1 - 64";
                 }
            }
            description "The maximum number of connections that can be created systemwide";
        } // END of maximum-connections definition.

        leaf maximum-sessions-per-connection  {
            type  uint16 {
                 range "1..2000"  {
                    description "1..2000: Supported range 1 - 2000";
                 }
            }
            description "Maximum number of test sessions per connection (default = 1)";
        } // END of maximum-sessions-per-connection definition.

    } // END of twamp-client-global-config definition.
    grouping twamp-client-connection-config {
        description
            "Grouping for twamp client connection configurations";
        leaf connection-name  {
            type  string {
                length "1..1965";
                pattern "[a-zA-Z0-9_-]*";
            }
            description "Create twamp connection name";
        } // END of connection-name definition.

        leaf server-address  {
            type  ipi-twamp-types:twamp_hostname_t;
            description "Configure twamp server address to connect with client";
        } // END of server-address definition.

        leaf server-port  {
            // when " ../server-address ";
            type  ipi-twamp-types:twamp_udp_port_t;
            description "Configure twamp server port to connect with client";
        } // END of server-port definition.

        leaf vrf-name  {
            type  string {
                length "1..1965";
                pattern "[^?' =,>|]+";
            }
            description "Use this attribute to set the connection VRF name";
        } // END of vrf-name definition.

    } // END of twamp-client-connection-config definition.
    grouping twamp-client-connection-state {
        description
            "Grouping for twamp client connection state params";
        leaf client-port  {
            type  uint32;
            description "Use this attribute to display the client port";
        } // END of client-port definition.

        leaf client-address  {
            type  inet:ip-address;
            description "IP address of the client";
        } // END of client-address definition.

        leaf connection-time  {
            type  yang:date-and-time {
                pattern "\\d{4}-\\d{2}-\\d{2}T\\d{2}:\\d{2}:\\d{2}(\\.\\d+)?(Z|[\\+\\-]\\d{2}:\\d{2})";
                }
                description "Time when the connection was established";
            } // END of connection-time definition.

            leaf last-activity-time  {
                type  yang:date-and-time {
                    pattern "\\d{4}-\\d{2}-\\d{2}T\\d{2}:\\d{2}:\\d{2}(\\.\\d+)?(Z|[\\+\\-]\\d{2}:\\d{2})";
                    }
                    description "Time of the last activity that happened on the connection";
                } // END of last-activity-time definition.

                leaf connection-state  {
                    type  string {
                        length "1..1965";
                        pattern "[^?' =,>|]+";
                    }
                    description "State of the connection with the client";
                } // END of connection-state definition.

                leaf nb-session-requested  {
                    type  yang:counter32;
                    description "Number of session requests received on the connection";
                } // END of nb-session-requested definition.

                leaf nb-sessions-accepted  {
                    type  yang:counter32;
                    description "Number of accepted sessions on the connection";
                } // END of nb-sessions-accepted definition.

    } // END of twamp-client-connection-state definition.
    grouping twamp-client-session-config {
        description
            "Grouping for twamp client global configurations";
        leaf session-name  {
            type  string {
                length "1..128";
                pattern "[a-zA-Z0-9_-]*";
            }
            description "Create twamp session name";
        } // END of session-name definition.

        leaf sender-port  {
            type  uint32 {
                 range "1025..65535"  {
                    description "1025..65535: Supported range 1025 - 65535";
                 }
            }
            description "Configure twamp server port to connect with client";
        } // END of sender-port definition.

        leaf receiver-port  {
            type  uint32 {
                 range "1025..65535"  {
                    description "1025..65535: Supported range 1025 - 65535";
                 }
            }
            description "Configure twamp server port to connect with client";
        } // END of receiver-port definition.

        leaf sender-address  {
            type  ipi-twamp-types:twamp_hostname_t;
            description "Configure twamp sender address to connect with client";
        } // END of sender-address definition.

        leaf receiver-address  {
            type  ipi-twamp-types:twamp_hostname_t;
            description "Configure twamp receiver address to connect with client";
        } // END of receiver-address definition.

        leaf start-time  {
            type  ipi-twamp-types:twamp_date_time_t {
                length "1..1965";
            }
            description "Configure twamp start time to connect with client";
        } // END of start-time definition.

        leaf interface-name  {
            type  string {
                length "1..1965";
                pattern "[^?' =,>|]+";
            }
            description "Use this attribute to set the session VRF name";
        } // END of interface-name definition.

    } // END of twamp-client-session-config definition.
    grouping twamp-client-session-state {
        description
            "Grouping of TWAMP client session state";
        leaf requested-receiver-port  {
            type  uint32;
            description "Use this attribute to display the port requested by server";
        } // END of requested-receiver-port definition.

        leaf session-id  {
            type  string {
                length "1..1965";
                pattern "[^?' =,>|]+";
            }
            description "session id of the server";
        } // END of session-id definition.

    } // END of twamp-client-session-state definition.
    grouping twamp-client-session-top {
        description
            "Grouping TWAMP client session config";
        container sessions {
            description
                "TWAMP client sessions";

            list session {
            // when " ipi-twamp:twamp/light/control/config/administrative-state == 1 ";
                key "session-name";
                description
                    "List of Twamp client sessions";
                leaf session-name  {
                    type  leafref {
                        path  "../config/session-name";
                    }
                    description "Sets client connection Name";
                } // END of session-name definition.

                container config {
                    description
                        "Configuration data for TWAMP Light Session Reflector Ip address";
                    uses twamp-client-session-config;
                } // END of config-container definition.
                container state {
                    config false;
                    description
                        "operational state data for TWAMP Light Session Reflector IP address";
                    uses twamp-client-session-config;
                    uses twamp-client-session-state;
                } // END of state-container definition.
            } // End of session-list
        } // END of sessions-container definition.
    } // END of twamp-client-session-top definition.
    grouping twamp-client-connection-top {
        description
            "Grouping TWAMP client connection config";
        container connections {
            description
                "TWAMP client connections";

            list connection {
                key "connection-name vrf-name";
                description
                    "List of Twamp client connections";
                leaf connection-name  {
                    type  leafref {
                        path  "../config/connection-name";
                    }
                    description "Sets client connection Name";
                } // END of connection-name definition.

                leaf vrf-name  {
                    type  leafref {
                        path  "../config/vrf-name";
                    }
                    description "Use this attribute to set the Connection VRF name";
                } // END of vrf-name definition.

                container config {
                    description
                        "Configuration data for TWAMP Light Session Reflector Ip address";
                    uses twamp-client-connection-config;
                } // END of config-container definition.
                container state {
                    config false;
                    description
                        "operational state data for TWAMP Light Session Reflector IP address";
                    uses twamp-client-connection-config;
                    uses twamp-client-connection-state;
                } // END of state-container definition.
                uses twamp-client-session-top;
            } // End of connection-list
        } // END of connections-container definition.
    } // END of twamp-client-connection-top definition.

    grouping  client-grouping {
    description
        "Twamp client container for global configs";
    container client {
        if-feature feature-list:HAVE_TWAMP;
        description
            "Twamp client container for global configs";
        container config {
            presence "yes";
            description
                "Configuration data for TWAMP client gloabl configuration";
            uses twamp-client-global-config;
        } // END of config-container definition.
        container state {
            config false;
            description
                "Operational state data for TWAMP client global configuration";
            uses twamp-client-global-config;
        } // END of state-container definition.
        uses twamp-client-connection-top;
    } // END of client-container definition.
    } // END of client-grouping definition.


}
