/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-twamp-session.yang
*
*/

submodule ipi-twamp-session {

    yang-version 1.1;

    belongs-to  ipi-twamp { prefix ipi-twamp; }

    import feature-list {
        prefix feature-list;
        revision-date 2026-09-15;
    }

    import cml-data-types {
        prefix cml-data-types;
        revision-date 2026-05-15;
    }

    import ietf-yang-types {
        prefix yang;
        revision-date 2013-07-15;
    }

    import ipi-twamp-types {
        prefix ipi-twamp-types;
        revision-date 2025-10-20;
    }

    import ipi-network-instance {
        prefix ipi-network-instance;
        revision-date 2026-08-12;
    }

    import ipi-vrf {
        prefix ipi-vrf;
        revision-date 2026-08-12;
    }

    organization
        "IP Infusion Inc.";

    contact
        "Address: 3965 Freedom Circle, Suite 200, Santa Clara, CA 95054
         Phone: +1 408-400-1900
         E-mail: support@ipinfusion.com
         Web: http://www.ipinfusion.com/";

    description
        "This module provides TWAMP Session configuration";


    revision "2025-11-10" {
        description "Removed pattern tag from vrf-name";
        reference " 0.2.5.";
    }

    revision "2025-10-20" {
        description "Improved CLI validation for twamp session sender-ip and reflector-ip to accept all valid input formats";
        reference " 0.2.4.";
    }

    revision "2025-09-18" {
        description "Adjusted helpstring for burst count";
        reference " 0.2.3.";
    }

    revision "2025-09-17" {
        description "Added validation for hostname and IPv4 address formats to the TWAMP_HOSTPNAME_T data type";
        reference " 0.2.2.";
    }

    revision "2025-06-20" {
        description "Increased the burst-count attribute range";
        reference " 0.2.1.";
    }

    revision "2025-06-16" {
        description "Added twamp-light control as a dependentObject for twamp-session";
        reference " 0.2.0.";
    }

    revision "2025-05-15" {
        description "Default value of the VRF set to default";
        reference " 0.1.4.";
    }

    revision "2025-05-02" {
        description "Fixed types for time value leaves";
        reference " 0.1.3.";
    }

    revision "2025-03-26" {
        description "Removed CLI shut all";
        reference " 0.1.2.";
    }

    revision "2025-03-22" {
        description "Updated sender-ip and reflector-ip datatype and added pattern for vrf-name";
        reference " 0.1.1.";
    }

    revision "2025-03-13" {
        description "Initial Version";
        reference " 0.1.0.";
    }

    grouping twamp-session-parameters-config {
        description
            "TWAMP Session parameters configuration";
        leaf reflector-ip  {
            type  ipi-twamp-types:twamp_hostpname_t;
            description "Use this attribute to set the reflector IP.";
        } // END of reflector-ip definition.

        leaf reflector-port  {
            type  ipi-twamp-types:twamp_udp_port_t;
            default "862";
            description "Use this attribute to set the reflector port.";
        } // END of reflector-port definition.

        leaf sender-ip  {
            type  ipi-twamp-types:twamp_hostpname_t;
            description "Use this attribute to set the sender IP.";
        } // END of sender-ip definition.

        leaf sender-port  {
            type  ipi-twamp-types:twamp_udp_port_t;
            default "862";
            description "Use this attribute to set the sender port.";
        } // END of sender-port definition.

        leaf vrf-name  {
            type  leafref {
                path  "/ipi-network-instance:network-instances/ipi-network-instance:network-instance/ipi-vrf:vrf/ipi-vrf:config/ipi-vrf:vrf-name";
            }
            description "Set the VRF name for this TWAMP Session.";
        } // END of vrf-name definition.

        leaf vpn-net-interface  {
            type  string {
                length "1..32";
                pattern "[^?' =,>|]+";
            }
            description "Set the VPN network interface for this TWAMP Session.";
        } // END of vpn-net-interface definition.

        leaf dscp  {
            type  string {
                length "1..8";
                pattern "[^?' =,>|]+";
            }
            default "0";
            description "Use this attribute to classify traffic based on the Differentiated
                        Services Code Point (DSCP) value. The DSCP value range is
                        0-63.Warning: In CLI show running, DSCP values with well-known names
                        (ex.: af11, cs0) will be displayed as such.On Netconf, DSCP values
                        will always be numeric. The string type allow up to 8 characters on
                        well-known name.";
        } // END of dscp definition.

        leaf burst-interval  {
            type  uint16 {
                 range "1000..15000"  {
                    description "1000..15000: Supported range 1000 - 15000";
                 }
            }
            units "milliseconds";
            default "3000";
            description "Configure the burst interval";
        } // END of burst-interval definition.

        leaf burst-count  {
            type  uint8 {
                 range "1..10"  {
                    description "1..10: Supported range 1 - 10";
                 }
            }
            default "3";
            description "Configure the burst-count";
        } // END of burst-count definition.

        leaf interval  {
            type  uint16 {
                 range "30..3600"  {
                    description "30..3600: Supported range 30 - 3600";
                 }
            }
            units "seconds";
            default "30";
            description "Configure the computation interval";
        } // END of interval definition.

    } // END of twamp-session-parameters-config definition.
    grouping twamp-session-parameters-top {
        description
            "TWAMP Session parameters top level configuration";
        container parameters {
            description
                "TWAMP Session parameters configuration";
            container config {
                description
                    "Configuration data for TWAMP Session parameters";
                uses twamp-session-parameters-config;
            } // END of config-container definition.
            container state {
                config false;
                description
                    "Operational state data for TWAMP Session parameters";
                uses twamp-session-parameters-config;
            } // END of state-container definition.
        } // END of parameters-container definition.
    } // END of twamp-session-parameters-top definition.
    grouping twamp-session-notification-config {
        description
            "desc";
        leaf enabled  {
            type  empty;
            description "Enable the notifications for advertising via NETCONF/SNMP Traps when
                        thresholds are crossed";
        } // END of enabled definition.

        leaf threshold  {
            type  uint8 {
                 range "1..100"  {
                    description "1..100: Supported range 1 - 100";
                 }
            }
            units "percentage";
            default "30";
            description "Configure the notifications advertisement threshold";
        } // END of threshold definition.

        leaf minimum-change  {
            type  uint16 {
                 range "0..10000"  {
                    description "0..10000: Supported range 0 - 10000";
                 }
            }
            units "microseconds";
            default "1000";
            description "Configure the notifications advertisement minimum-change in
                        microseconds (default=1000)";
        } // END of minimum-change definition.

    } // END of twamp-session-notification-config definition.
    grouping twamp-session-notification-top {
        description
            "TWAMP Session notification top level configuration";
        container notification {
            description
                "TWAMP Session notification configuration";
            container config {
                description
                    "Configuration data";
                uses twamp-session-notification-config;
            } // END of config-container definition.
            container state {
                config false;
                description
                    "Operational state data";
                uses twamp-session-notification-config;
            } // END of state-container definition.
        } // END of notification-container definition.
    } // END of twamp-session-notification-top definition.
    grouping twamp-session-statistics-last-calculated-state {
        description
            "TWAMP Session statistics last calculated runtime attributes";
        leaf calculation-time  {
            type  yang:date-and-time {
                pattern "\\d{4}-\\d{2}-\\d{2}T\\d{2}:\\d{2}:\\d{2}(\\.\\d+)?(Z|[\\+\\-]\\d{2}:\\d{2})";
                }
                description "This attribute represents the time at which a calculation was made";
            } // END of calculation-time definition.

            leaf minimum-delay  {
                type  uint64;
                units "microseconds";
                description "This attribute represents the minimum delay value";
            } // END of minimum-delay definition.

            leaf maximum-delay  {
                type  uint64;
                units "microseconds";
                description "This attribute represents the maximum delay value";
            } // END of maximum-delay definition.

            leaf average-delay  {
                type  uint64;
                units "microseconds";
                description "This attribute represents the average delay value";
            } // END of average-delay definition.

            leaf minimum-delay-variation  {
                type  uint64;
                units "microseconds";
                description "This attribute represents the minimum delay variation value";
            } // END of minimum-delay-variation definition.

            leaf maximum-delay-variation  {
                type  uint64;
                units "microseconds";
                description "This attribute represents the maximum delay variation value";
            } // END of maximum-delay-variation definition.

            leaf average-delay-variation  {
                type  uint64;
                units "microseconds";
                description "This attribute represents the average delay variation value";
            } // END of average-delay-variation definition.

            leaf packets-sent  {
                type  yang:counter64;
                description "This attribute represents the amount of sent packets in a measurement
                            interval";
            } // END of packets-sent definition.

            leaf packets-received  {
                type  yang:counter64;
                description "This attribute represents the amount of received packets in a
                            measurement interval";
            } // END of packets-received definition.

            leaf packets-timeout  {
                type  yang:counter64;
                description "This attribute represents the amount of lost packets in a measurement
                            interval";
            } // END of packets-timeout definition.

            leaf packet-loss  {
                type  decimal64 {
                     fraction-digits 4;                }
                description "This attribute represents the percentage of lost packets in a
                            measurement interval";
            } // END of packet-loss definition.

    } // END of twamp-session-statistics-last-calculated-state definition.
    grouping twamp-session-statistics-last-notified-state {
        description
            "TWAMP Session statistics last notified runtime attributes";
        leaf time-notified-packet-loss  {
            type  yang:date-and-time {
                pattern "\\d{4}-\\d{2}-\\d{2}T\\d{2}:\\d{2}:\\d{2}(\\.\\d+)?(Z|[\\+\\-]\\d{2}:\\d{2})";
                }
                description "This attribute represents the time at which the packet loss was
                            notified";
            } // END of time-notified-packet-loss definition.

            leaf packet-loss  {
                type  decimal64 {
                     fraction-digits 4;                }
                description "This attribute represents the amount of lost packets for a Session
                            that has been notified";
            } // END of packet-loss definition.

            leaf time-notified-average-delay  {
                type  yang:date-and-time {
                    pattern "\\d{4}-\\d{2}-\\d{2}T\\d{2}:\\d{2}:\\d{2}(\\.\\d+)?(Z|[\\+\\-]\\d{2}:\\d{2})";
                    }
                    description "This attribute represents the time at which the average delay was
                                notified";
                } // END of time-notified-average-delay definition.

                leaf average-delay  {
                    type  yang:counter64;
                    units "microseconds";
                    description "This attribute represents the average delay value that has been
                                notified";
                } // END of average-delay definition.

    } // END of twamp-session-statistics-last-notified-state definition.
    grouping twamp-session-statistics-packets-state {
        description
            "TWAMP Session statistics packets runtime attributes";
        leaf packets-sent  {
            type  yang:counter64;
            description "This attribute represents the amount of sent packets for a session";
        } // END of packets-sent definition.

        leaf packets-received  {
            type  yang:counter64;
            description "This attribute represents the amount of received packets for a session";
        } // END of packets-received definition.

        leaf packet-loss  {
            type  decimal64 {
                 fraction-digits 4;            }
            description "This attribute represents the amount of lost packets for a session";
        } // END of packet-loss definition.

    } // END of twamp-session-statistics-packets-state definition.
    grouping twamp-session-statistics-common-state {
        description
            "TWAMP Session statistics common runtime attributes";
        leaf minimum  {
            type  uint64;
            units "microseconds";
            description "This attribute represents the minimum value within the statistics";
        } // END of minimum definition.

        leaf maximum  {
            type  uint64;
            units "microseconds";
            description "This attribute represents the maximum value within the statistics";
        } // END of maximum definition.

        leaf average  {
            type  uint64;
            units "microseconds";
            description "This attribute represents the average value within the statistics";
        } // END of average definition.

    } // END of twamp-session-statistics-common-state definition.
    grouping twamp-session-statistics-state {
        description
            "TWAMP Session statistics runtime attributes";
        leaf start-time  {
            type  yang:date-and-time {
                pattern "\\d{4}-\\d{2}-\\d{2}T\\d{2}:\\d{2}:\\d{2}(\\.\\d+)?(Z|[\\+\\-]\\d{2}:\\d{2})";
                }
                description "This attribute represents the start time of a Test Session";
            } // END of start-time definition.

            leaf elapsed-time  {
                type  uint32;
                units "milliseconds";
                description "This attribute represents the elapsed time of a Test Session";
            } // END of elapsed-time definition.

    } // END of twamp-session-statistics-state definition.
    grouping twamp-session-statistics-last-calculated-top {
        description
            "TWAMP Session statistics for last calculated";
        container last-calculated {
            config false;
            description
                "Operational state data";
            uses twamp-session-statistics-last-calculated-state;
        } // END of last-calculated-container definition.
    } // END of twamp-session-statistics-last-calculated-top definition.
    grouping twamp-session-statistics-last-notified-top {
        description
            "TWAMP Session statistics for last notified";
        container last-notified {
            config false;
            description
                "Operational state data";
            uses twamp-session-statistics-last-notified-state;
        } // END of last-notified-container definition.
    } // END of twamp-session-statistics-last-notified-top definition.
    grouping twamp-session-statistics-packets-top {
        description
            "TWAMP Session statistics for packet";
        container packets {
            config false;
            description
                "Operational state data";
            uses twamp-session-statistics-packets-state;
        } // END of packets-container definition.
    } // END of twamp-session-statistics-packets-top definition.
    grouping twamp-session-statistics-round-trip-delay-top {
        description
            "TWAMP Session statistics for round-trip delay";
        container round-trip-delay {
            config false;
            description
                "Operational state data";
            uses twamp-session-statistics-common-state;
        } // END of round-trip-delay-container definition.
    } // END of twamp-session-statistics-round-trip-delay-top definition.
    grouping twamp-session-statistics-forward-delay-top {
        description
            "TWAMP Session statistics for forward delay";
        container round-forward-delay {
            config false;
            description
                "Operational state data";
            uses twamp-session-statistics-common-state;
        } // END of round-forward-delay-container definition.
    } // END of twamp-session-statistics-forward-delay-top definition.
    grouping twamp-session-statistics-reverse-delay-top {
        description
            "TWAMP Session statistics for reverse delay";
        container reverse-delay {
            config false;
            description
                "Operational state data";
            uses twamp-session-statistics-common-state;
        } // END of reverse-delay-container definition.
    } // END of twamp-session-statistics-reverse-delay-top definition.
    grouping twamp-session-statistics-round-trip-delay-variation-top {
        description
            "TWAMP Session statistics for round trip delay variation";
        container round-trip-delay-variation {
            config false;
            description
                "Operational state data";
            uses twamp-session-statistics-common-state;
        } // END of round-trip-delay-variation-container definition.
    } // END of twamp-session-statistics-round-trip-delay-variation-top definition.
    grouping twamp-session-statistics-forward-delay-variation-top {
        description
            "TWAMP Session statistics for forward delay variation";
        container forward-delay-variation {
            config false;
            description
                "Operational state data";
            uses twamp-session-statistics-common-state;
        } // END of forward-delay-variation-container definition.
    } // END of twamp-session-statistics-forward-delay-variation-top definition.
    grouping twamp-session-statistics-reverse-delay-variation-top {
        description
            "TWAMP Session statistics for reverse delay variation";
        container reverse-delay-variation {
            config false;
            description
                "Operational state data";
            uses twamp-session-statistics-common-state;
        } // END of reverse-delay-variation-container definition.
    } // END of twamp-session-statistics-reverse-delay-variation-top definition.
    grouping twamp-session-statistics-top {
        description
            "TWAMP Session statistics top level runtime attributes";
        container statistics {
            config false;
            description
                "TWAMP Session statistics data";
            container state {
                config false;
                description
                    "TWAMP Session statistics data";
                uses twamp-session-statistics-state;
                uses twamp-session-statistics-last-calculated-top;
                uses twamp-session-statistics-last-notified-top;
                uses twamp-session-statistics-packets-top;
                uses twamp-session-statistics-round-trip-delay-top;
                uses twamp-session-statistics-forward-delay-top;
                uses twamp-session-statistics-reverse-delay-top;
                uses twamp-session-statistics-round-trip-delay-variation-top;
                uses twamp-session-statistics-forward-delay-variation-top;
                uses twamp-session-statistics-reverse-delay-variation-top;
            } // END of state-container definition.
        } // END of statistics-container definition.
    } // END of twamp-session-statistics-top definition.
    grouping twamp-session-config {
        description
            "TWAMP Session configuration";
        leaf session-name  {
            type  string {
                length "1..32";
                pattern "[^?' =,>|]+";
            }
            description "TWAMP Session name";
        } // END of session-name definition.

        leaf enabled  {
            type  empty;
            description "Use this attribute to shut/unshut a TWAMP Session";
        } // END of enabled definition.

        leaf description  {
            type  cml-data-types:cml_line_t {
                length "1..32";
            }
            description "Use this attribute to add a description to TWAMP Session";
        } // END of description definition.

    } // END of twamp-session-config definition.
    grouping twamp-session-top {
        description
            "TWAMP Session configuration";

        list session {
        // when " ipi-twamp:twamp/light/control/config/enable ";
            key "session-name";
            description
                "TWAMP Session list";
            leaf session-name  {
                type  leafref {
                    path  "../config/session-name";
                }
                description "TWAMP End-to-End Session name";
            } // END of session-name definition.

            container config {
                description
                    "Configuration data for TWAMP Session";
                uses twamp-session-config;
            } // END of config-container definition.
            container state {
                config false;
                description
                    "Operational state data for TWAMP Session";
                uses twamp-session-config;
            } // END of state-container definition.
            uses twamp-session-parameters-top;
            uses twamp-session-notification-top;
            uses twamp-session-statistics-top;
        } // End of session-list
    } // END of twamp-session-top definition.

    grouping  sessions-grouping {
    description
        "Container for all TWAMP Session configuration";
    container sessions {
        if-feature feature-list:HAVE_TWAMP;
        description
            "Container for all TWAMP Session configuration";
        uses twamp-session-top;
    } // END of sessions-container definition.
    } // END of sessions-grouping definition.


}
