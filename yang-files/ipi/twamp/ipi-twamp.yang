/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-twamp.yang
*
*/

module ipi-twamp {

    yang-version 1.1;

    namespace   "http://www.ipinfusion.com/yang/ocnos/ipi-twamp";

    prefix "ipi-twamp";

    import cml-data-types {
        prefix cml-data-types;
        revision-date 2026-05-15;
    }

    import ietf-yang-types {
        prefix yang;
        revision-date 2013-07-15;
    }

    import ipi-twamp-types {
        prefix ipi-twamp-types;
        revision-date 2025-10-20;
    }

    import ietf-inet-types {
        prefix inet;
        revision-date 2013-07-15;
    }

    import ipi-network-instance {
        prefix ipi-network-instance;
        revision-date 2026-08-12;
    }

    import ipi-vrf {
        prefix ipi-vrf;
        revision-date 2026-08-12;
    }

    import feature-list {
        prefix feature-list;
        revision-date 2026-09-15;
    }

    include ipi-twamp-client { revision-date 2025-10-20;}
    include ipi-twamp-session { revision-date 2025-11-10;}
    organization
        "IP Infusion Inc.";

    contact
        "Address: 3965 Freedom Circle, Suite 200, Santa Clara, CA 95054
         Phone: +1 408-400-1900
         E-mail: support@ipinfusion.com
         Web: http://www.ipinfusion.com/";

    description
        "Two-Way Active Measurement Protocol (TWAMP)";


    revision "2025-11-10" {
        description "Removed pattern tag from vrf-name";
        reference " 0.16.8.";
    }

    revision "2025-11-03" {
        description "Overall-packet-rate structure and notifications added";
        reference " 0.16.7.";
    }

    revision "2025-10-20" {
        description "Improved CLI validation for twamp session sender-ip and reflector-ip to accept all valid input formats";
        reference " 0.16.6.";
    }

    revision "2025-09-18" {
        description "Increased server maximum-sessions range to scaled up values on Q2";
        reference " 0.16.5.";
    }

    revision "2025-09-17" {
        description "Added validation for hostname and IPv4 address formats to the TWAMP_HOSTPNAME_T data type";
        reference " 0.16.4.";
    }

    revision "2025-08-27" {
        description "Updated reflector-port to show default value when configured by user";
        reference " 0.16.3.";
    }

    revision "2025-08-11" {
        description "Increased the twamp-session burst-count attribute range and added rate alarm notifications";
        reference " 0.16.2.";
    }

    revision "2025-07-30" {
        description "Updated default values for sender-ip-address, sender-udp-port and upstream-intf leaves";
        reference " 0.16.2.";
    }

    revision "2025-07-14" {
        description "Updated sender-ip-address and sender-udp-port leaves";
        reference " 0.16.1.";
    }

    revision "2025-06-16" {
        description "Added twamp-session as a dependentObject for twamp-light control";
        reference " 0.16.0.";
    }

    revision "2025-06-12" {
        description "Adjusted the reflector name regex to support adding the . character in the name (to accomodate customer config upgrade)";
        reference " 0.15.8.";
    }

    revision "2025-05-15" {
        description "Default value of the VRF set to default";
        reference " 0.15.8.";
    }

    revision "2025-05-02" {
        description "Fixed types for time value leaves";
        reference " 0.15.7.";
    }

    revision "2025-05-01" {
        description "Modified the ipi-twamp-types if-feature level so it can be used in igp te datamodel";
        reference " 0.15.6.";
    }

    revision "2025-03-26" {
        description "Updated TWAMP Session datamodel";
        reference " 0.15.5.";
    }

    revision "2025-03-22" {
        description "Added pattern verification for reflector attributes";
        reference " 0.15.4.";
    }

    revision "2025-03-13" {
        description "Added support for upstream interface for TWAMP";
        reference " 0.15.3.";
    }

    revision "2025-02-25" {
        description "Insert dependentObject directive";
        reference " 0.15.2.";
    }

    revision "2025-02-13" {
        description "Limited session name to 128 characters long";
        reference " 0.15.1.";
    }

    revision "2025-02-03" {
        description "Added SNMP Traps support for TWAMP";
        reference " 0.15.0.";
    }

    revision "2025-01-22" {
        description "Fixed checking the value of the control admin state in the twamp client when creating a session";
        reference " 0.14.6.";
    }

    revision "2025-01-20" {
        description "Correct twamp session attributes description";
        reference " 0.14.5.";
    }

    revision "2025-01-15" {
        description "Removed unnecessary vrf cli under config-twamp-light-ref";
        reference " 0.14.4.";
    }

    revision "2025-01-14" {
        description "Revert the flag CML_RESET_INSTANCE added in 0.1.42";
        reference " 0.14.3.";
    }

    revision "2024-12-18" {
        description "Added CML_RESET_INSTANCE for name and vrf-name attribute under session container";
        reference " 0.14.2.";
    }

    revision "2024-12-12" {
        description "Added ignore snmp generation tag";
        reference " 0.14.1.";
    }

    revision "2024-11-21" {
        description "Fixed maximum values ranges for sessions and connections to start from 1 instead of 0 in the client submodule";
        reference " 0.14.0.";
    }

    revision "2024-03-27" {
        description "Added pattern checking for connection and session names in twamp client";
        reference " 0.13.4.";
    }

    revision "2023-10-11" {
        description "Set reflector session parameters to CML_INITIALIZED";
        reference " 0.13.3.";
    }

    revision "2023-09-06" {
        description "Added Reset CLI for the TWAMP client dead sessions";
        reference " 0.13.2.";
    }

    revision "2023-08-31" {
        description "Remove unnecessary import";
        reference " 0.13.1.";
    }

    revision "2023-05-12" {
        description "Added datatype for twamp client module";
        reference " 0.13.0.";
    }

    revision "2022-10-20" {
        description "Fixed a cli generation problem related to vrf-name";
        reference " 0.11.0.";
    }

    revision "2022-10-18" {
        description "Added TWAMP server implementation";
        reference " 0.12.0.";
    }

    revision "2022-10-15" {
        description "Modified the vrf-name attribute to be as RDN and add ipi-vrf dependency";
        reference " 0.10.0.";
    }

    revision "2022-08-22" {
        description "Added delay-threshold and notification";
        reference " 0.9.0.";
    }

    revision "2022-08-10" {
        description "Debug hierarchy change";
        reference " 0.8.0.";
    }

    revision "2022-07-08" {
        description "Increased the test-session max-elements from 8 to 64";
        reference " 0.7.0.";
    }

    revision "2022-07-05" {
        description "Changed the data type for the reflector source UDP port";
        reference " 0.6.0.";
    }

    revision "2022-06-01" {
        description "Updated the yang file with feature";
        reference " 0.5.0.";
    }

    revision "2022-03-17" {
        description "Added sender ip and port in reflector session";
        reference " 0.4.0.";
    }

    revision "2022-01-31" {
        description "Added VRF name handling for both test-session and reflector";
        reference " 0.3.0.";
    }

    revision "2022-01-28" {
        description "Introduced Multiple Reflector Session";
        reference " 0.2.0.";
    }

    revision "2021-09-10" {
        description "Restructured module in accordance with OpenConfig style";
        reference " 0.1.0.";
    }

    revision "2020-02-20" {
        description "Initial Version";
        reference "Initial Version";
    }

    grouping twamp-session-reflector-config {
        description
            "Grouping for TWAMP Light Session Reflector configuration data";
        leaf enable  {
            type  empty;
            mandatory true;
            description "Enables TWAMP Light Session Reflector";
        } // END of enable definition.

        leaf administrative-state  {
            type  cml-data-types:cml_enable_disable_t;
            default "disable";
            description "Sets TWAMP Light Session Reflector administrative state";
        } // END of administrative-state definition.

    } // END of twamp-session-reflector-config definition.
    grouping twamp-session-reflector-address-top {
        description
            "TWAMP session reflector address grouping";
        container sessions {
            description
                "TWAMP reflector sessions";

            list session {
            when " /ipi-twamp:twamp/ipi-twamp:light/ipi-twamp:session-reflector/ipi-twamp:config/ipi-twamp:enable ";
                key "name vrf-name";
                description
                    "List of TWAMP Light Reflector sessions";
                leaf name  {
                    type  leafref {
                        path  "../config/name";
                    }
                    description "Sets Reflector Session Name";
                } // END of name definition.

                leaf vrf-name  {
                    type  leafref {
                        path  "../config/vrf-name";
                    }
                    description "Use this attribute to set the Reflector VRF name";
                } // END of vrf-name definition.

                container config {
                    description
                        "Configuration data for TWAMP Light Session Reflector Ip address";
                    uses twamp-session-reflector-address-config;
                } // END of config-container definition.
                container state {
                    config false;
                    description
                        "operational state data for TWAMP Light Session Reflector IP address";
                    uses twamp-session-reflector-address-config;
                } // END of state-container definition.
            } // End of session-list
        } // END of sessions-container definition.
    } // END of twamp-session-reflector-address-top definition.
    grouping twamp-session-reflector-address-config {
        description
            "Grouping for TWAMP Light Session Reflector configuration data";
        leaf name  {
            type  string {
                length "1..128";
                pattern "[a-zA-Z0-9][a-zA-Z0-9_.-]*";
            }
            description "Sets Reflector Session Name";
        } // END of name definition.

        leaf reflector-ip-address  {
            type  ipi-twamp-types:twamp_hostname_t;
            mandatory true;
            description "Set TWAMP Reflector Session IP address";
        } // END of reflector-ip-address definition.

        leaf reflector-udp-port  {
            type  ipi-twamp-types:twamp_udp_port_t;
            default "862";
            description "Use this attribute to set Reflector UDP Port";
        } // END of reflector-udp-port definition.

        leaf sender-ip-address  {
            type  ipi-twamp-types:twamp_hostname_t;
            default "NULL";
            description "Set TWAMP Reflector Session sender IP address";
        } // END of sender-ip-address definition.

        leaf sender-udp-port  {
            type  ipi-twamp-types:twamp_ref_src_udp_port_t;
            default "0";
            description "Use this attribute to set the sender UDP Port";
        } // END of sender-udp-port definition.

        leaf vrf-name  {
            type  string {
                length "1..32";
                pattern "[a-zA-Z0-9_-]*";
            }
            description "Use this attribute to set the Reflector VRF name";
        } // END of vrf-name definition.

        leaf upstream-intf  {
            type  string {
                length "1..32";
                pattern "[^?' =,>|]+";
            }
            default "NULL";
            description "Use this attribute to set the VPN Network Interface for the reflector";
        } // END of upstream-intf definition.

    } // END of twamp-session-reflector-address-config definition.
    grouping twamp-session-reflector-top {
        description
            "Grouping for TWAMP Session Reflector";
        container session-reflector {
            description
                "Configuration data for TWAMP Light Session Reflector";
            container config {
                presence "yes";
                description
                    "Configuration data for TWAMP Light Session Reflector";
                uses twamp-session-reflector-config;
            } // END of config-container definition.
            container state {
                config false;
                description
                    "operational state data for TWAMP Light Reflector Session";
                uses twamp-session-reflector-config;
            } // END of state-container definition.
            uses twamp-session-reflector-address-top;
        } // END of session-reflector-container definition.
    } // END of twamp-session-reflector-top definition.
    grouping twamp-control-test-session-statistics-common {
        description
            "Grouping for TWAMP Light Test Session Statistics common operational
                        state data. When attribute is not present, it might indicate that the
                        clock is not in sync between Sender and Reflector";
        leaf minimum  {
            type  uint64;
            units "microseconds";
            description "This attribute represents the minimum value within the statistics";
        } // END of minimum definition.

        leaf maximum  {
            type  uint64;
            units "microseconds";
            description "This attribute represents the maximum value within the statistics";
        } // END of maximum definition.

        leaf average  {
            type  uint64;
            units "microseconds";
            description "This attribute represents the average value within the statistics";
        } // END of average definition.

    } // END of twamp-control-test-session-statistics-common definition.
    grouping twamp-control-test-session-statistics-round-trip-delay {
        description
            "Grouping for Test Session Statistics Round-trip Delay operational
                        state data";
        container round-trip-delay {
            config false;
            description
                "Test Session Statistics Round-trip Delay";
            uses twamp-control-test-session-statistics-common;
        } // END of round-trip-delay-container definition.
    } // END of twamp-control-test-session-statistics-round-trip-delay definition.
    grouping twamp-control-test-session-statistics-forward-delay {
        description
            "Grouping for Test Session Statistics Forward Delay operational state
                        data";
        container forward-delay {
            config false;
            description
                "Test Session Statistics Forward Delay";
            uses twamp-control-test-session-statistics-common;
        } // END of forward-delay-container definition.
    } // END of twamp-control-test-session-statistics-forward-delay definition.
    grouping twamp-control-test-session-statistics-reverse-delay {
        description
            "Grouping for Test Session Statistics Reverse Delay operational state
                        data";
        container reverse-delay {
            config false;
            description
                "Test Session Statistics Reverse Delay";
            uses twamp-control-test-session-statistics-common;
        } // END of reverse-delay-container definition.
    } // END of twamp-control-test-session-statistics-reverse-delay definition.
    grouping twamp-control-test-session-statistics-round-trip-delay-variation {
        description
            "Grouping for Test Session Statistics Round-trip Delay Variation
                        operational state data";
        container round-trip-delay-variation {
            config false;
            description
                "Test Session Statistics Round-trip Delay Variation";
            uses twamp-control-test-session-statistics-common;
        } // END of round-trip-delay-variation-container definition.
    } // END of twamp-control-test-session-statistics-round-trip-delay-variation definition.
    grouping twamp-control-test-session-statistics-forward-delay-variation {
        description
            "Grouping for Test Session Statistics Forward Delay Variation
                        operational state data";
        container forward-delay-variation {
            config false;
            description
                "Test Session Statistics Forward Delay Variation";
            uses twamp-control-test-session-statistics-common;
        } // END of forward-delay-variation-container definition.
    } // END of twamp-control-test-session-statistics-forward-delay-variation definition.
    grouping twamp-control-test-session-statistics-reverse-delay-variation {
        description
            "Grouping for Test Session Statistics Reverse Delay Variation
                        operational state data";
        container reverse-delay-variation {
            config false;
            description
                "Test Session Statistics Reverse Delay Variation";
            uses twamp-control-test-session-statistics-common;
        } // END of reverse-delay-variation-container definition.
    } // END of twamp-control-test-session-statistics-reverse-delay-variation definition.
    grouping twamp-control-test-session-statistics-state {
        description
            "Grouping for TWAMP Light Control Test Session statistics operational
                        state data";
        container statistics {
            config false;
            description
                "Operational state data for TWAMP Light Control Test Session statistics";
            leaf packets-sent  {
                type  yang:counter64;
                description "This attribute represents the amount of sent packets for a Test
                            Session";
            } // END of packets-sent definition.

            leaf packets-received  {
                type  yang:counter64;
                description "This attribute represents the amount of received packets for a Test
                            Session";
            } // END of packets-received definition.

            leaf packet-loss  {
                type  decimal64 {
                     fraction-digits 4;                }
                description "This attribute represents the amount of lost packets for a Test
                            Session";
            } // END of packet-loss definition.

            uses twamp-control-test-session-statistics-round-trip-delay;
            uses twamp-control-test-session-statistics-forward-delay;
            uses twamp-control-test-session-statistics-reverse-delay;
            uses twamp-control-test-session-statistics-round-trip-delay-variation;
            uses twamp-control-test-session-statistics-forward-delay-variation;
            uses twamp-control-test-session-statistics-reverse-delay-variation;
        } // END of statistics-container definition.
    } // END of twamp-control-test-session-statistics-state definition.
    grouping twamp-control-test-session-state {
        description
            "Grouping for TWAMP Light Control Test Session operational state data";
        leaf start-time  {
            type  yang:date-and-time {
                pattern "\\d{4}-\\d{2}-\\d{2}T\\d{2}:\\d{2}:\\d{2}(\\.\\d+)?(Z|[\\+\\-]\\d{2}:\\d{2})";
                }
                description "This attribute represents the start time of a Test Session";
            } // END of start-time definition.

            leaf elapsed-time  {
                type  uint32;
                units "milliseconds";
                description "This attribute represents the elapsed time of a Test Session";
            } // END of elapsed-time definition.

        uses twamp-control-test-session-statistics-state;
    } // END of twamp-control-test-session-state definition.
    grouping twamp-control-test-session-config {
        description
            "Grouping for TWAMP Light Control Test Session configuration data";
        leaf session-name  {
            type  string {
                length "1..128";
                pattern "[^?' =,>|]+";
            }
            description "Use this attribute to set test session name";
        } // END of session-name definition.

        leaf sender-ip-address  {
            type  ipi-twamp-types:twamp_hostname_t;
            mandatory true;
            description "Use this attribute to set test session sender IP address";
        } // END of sender-ip-address definition.

        leaf sender-udp-port  {
            // when " ipi-twamp:twamp/light/control/test-sessions/test-session/config/sender-ip-address ";
            type  ipi-twamp-types:twamp_udp_port_t;
            mandatory true;
            description "Use this attribute to set test session sender UDP port";
        } // END of sender-udp-port definition.

        leaf reflector-ip-address  {
            type  ipi-twamp-types:twamp_hostname_t;
            mandatory true;
            description "Use this attribute to set test session reflector IP address";
        } // END of reflector-ip-address definition.

        leaf reflector-udp-port  {
            // when " ipi-twamp:twamp/light/control/test-sessions/test-session/config/reflector-ip-address ";
            type  ipi-twamp-types:twamp_udp_port_t;
            mandatory true;
            description "Use this attribute to set test session reflector UDP port";
        } // END of reflector-udp-port definition.

        leaf dscp-value  {
            type  ipi-twamp-types:twamp_dscp_t;
            description "Use this attribute to set test session DSCP value";
        } // END of dscp-value definition.

        leaf vrf-name  {
            type  string {
                length "1..1965";
                pattern "[^?' =,>|]+";
            }
            description "Use this attribute to set the session VRF name";
        } // END of vrf-name definition.

    } // END of twamp-control-test-session-config definition.
    grouping twamp-control-test-sessions-top {
        description
            "Grouping for TWAMP Control Test Sessions";
        container test-sessions {
            description
                "Container for TWAMP Light Control Test Sessions list";

            list test-session {
            when " /ipi-twamp:twamp/ipi-twamp:light/ipi-twamp:control/ipi-twamp:config/ipi-twamp:enable ";
                key "session-name vrf-name";
                max-elements 64;
                description
                    "List of TWAMP Light Control Test Session";
                leaf session-name  {
                    type  leafref {
                        path  "../config/session-name";
                    }
                    description "Test Session name associated with this instance";
                } // END of session-name definition.

                leaf vrf-name  {
                    type  leafref {
                        path  "../config/vrf-name";
                    }
                    description "Use this attribute to set the session VRF name";
                } // END of vrf-name definition.

                container config {
                    description
                        "Configuration data for TWAMP Light Control Test Session";
                    uses twamp-control-test-session-config;
                } // END of config-container definition.
                container state {
                    config false;
                    description
                        "Operational state data for TWAMP Light Control Test Session";
                    uses twamp-control-test-session-config;
                    uses twamp-control-test-session-state;
                } // END of state-container definition.
            } // End of test-session-list
        } // END of test-sessions-container definition.
    } // END of twamp-control-test-sessions-top definition.
    grouping twamp-control-config {
        description
            "Grouping for TWAMP Light Control configuration data";
        leaf enable  {
            type  empty;
            mandatory true;
            description "Enables TWAMP Light Control";
        } // END of enable definition.

        leaf administrative-state  {
            type  cml-data-types:cml_enable_disable_t;
            default "disable";
            description "Sets TWAMP Light Control administrative state";
        } // END of administrative-state definition.

    } // END of twamp-control-config definition.
    grouping twamp-control-top {
        description
            "Grouping for TWAMP Light Control";
        container control {
            description
                "TWAMP Light Control";
            container config {
                presence "yes";
                description
                    "Configuration data for TWAMP Light Control";
                uses twamp-control-config;
            } // END of config-container definition.
            container state {
                config false;
                description
                    "Operational state data for TWAMP Light Control";
                uses twamp-control-config;
            } // END of state-container definition.
            uses twamp-control-test-sessions-top;
        } // END of control-container definition.
    } // END of twamp-control-top definition.
    grouping twamp-server-admin-top {
        description
            "Grouping for TWAMP Server admin configuration";
        container admin {
            description
                "TWAMP Server Admin Configuration";
            container config {
                presence "yes";
                description
                    "Admin status configuration data for TWAMP Server";
                uses twamp-server-admin-config;
            } // END of config-container definition.
            container state {
                config false;
                description
                    "Operational state data for TWAMP Server admin status data";
                uses twamp-server-admin-config;
            } // END of state-container definition.
        } // END of admin-container definition.
    } // END of twamp-server-admin-top definition.
    grouping twamp-server-state {
        description
            "Grouping for TWAMP Server operational state data";
        leaf nb-connections  {
            type  yang:counter32;
            description "This attribute represents the number of connections to the TWAMP
                        server";
        } // END of nb-connections definition.

        leaf nb-sessions  {
            type  yang:counter32;
            description "This attribute represents the number of sessions accepted by the
                        server";
        } // END of nb-sessions definition.

        leaf nb-running-sessions  {
            type  yang:counter32;
            description "This attribute represents the number of running sessions on the server";
        } // END of nb-running-sessions definition.

    } // END of twamp-server-state definition.
    grouping twamp-server-connections-top {
        description
            "Grouping for TWAMP Server connections";
        container connections {
            config false;
            description
                "Operational state data for TWAMP Server connections";

            list connection {
                key "connection-id";
                config false;
                description
                    "Top level list for client connections to the TWAMP server";
                leaf connection-id  {
                    type  leafref {
                        path  "../state/connection-id";
                    }
                    description "Connection ID";
                } // END of connection-id definition.

                container state {
                    config false;
                    description
                        "State level container for all client connections to the TWAMP server";
                    uses twamp-server-connection-state;
                } // END of state-container definition.
            } // End of connection-list
        } // END of connections-container definition.
    } // END of twamp-server-connections-top definition.
    grouping twamp-server-sessions-top {
        description
            "Grouping for TWAMP Server sessions";
        container sessions {
            config false;
            description
                "Operational state data for TWAMP Server sessions";

            list session {
                key "session-id";
                config false;
                description
                    "Top level list for sessions accepted by the TWAMP server";
                leaf session-id  {
                    type  leafref {
                        path  "../state/session-id";
                    }
                    description "Session ID";
                } // END of session-id definition.

                container state {
                    config false;
                    description
                        "State level container for all sessions accepted by the TWAMP server";
                    uses twamp-server-session-state;
                } // END of state-container definition.
            } // End of session-list
        } // END of sessions-container definition.
    } // END of twamp-server-sessions-top definition.
    grouping twamp-server-session-state {
        description
            "Operational parameters for TWAMP sessions";
        leaf session-id  {
            type  string {
                length "1..1965";
                pattern "[^?' =,>|]+";
            }
            description "Session ID";
        } // END of session-id definition.

        leaf connection-id  {
            type  uint32;
            description "Connection ID";
        } // END of connection-id definition.

        leaf session-state  {
            type  string {
                length "1..1965";
                pattern "[^?' =,>|]+";
            }
            description "Session state";
        } // END of session-state definition.

        leaf sender-address  {
            type  inet:ip-address;
            description "IP address of the TWAMP sender";
        } // END of sender-address definition.

        leaf sender-port  {
            type  uint16;
            description "Port used by the sender";
        } // END of sender-port definition.

        leaf receiver-address  {
            type  inet:ip-address;
            description "IP address of the TWAMP receiver";
        } // END of receiver-address definition.

        leaf receiver-port  {
            type  uint16;
            description "Port used by the receiver";
        } // END of receiver-port definition.

        leaf receiver-vrf  {
            type  string {
                length "1..1965";
                pattern "[^?' =,>|]+";
            }
            description "VRF where the receiver is running";
        } // END of receiver-vrf definition.

        leaf start-time  {
            type  yang:date-and-time {
                pattern "\\d{4}-\\d{2}-\\d{2}T\\d{2}:\\d{2}:\\d{2}(\\.\\d+)?(Z|[\\+\\-]\\d{2}:\\d{2})";
                }
                description "Start-Time requested by the client for the session";
            } // END of start-time definition.

            leaf timeout  {
                type  uint32;
                description "Timeout requested for the session";
            } // END of timeout definition.

    } // END of twamp-server-session-state definition.
    grouping twamp-server-connection-state {
        description
            "Operational parameters for TWAMP client connections";
        leaf connection-id  {
            type  uint32;
            description "Connection ID";
        } // END of connection-id definition.

        leaf client-address  {
            type  inet:ip-address;
            description "IP address of the client";
        } // END of client-address definition.

        leaf client-port  {
            type  uint16;
            description "Port used by the client";
        } // END of client-port definition.

        leaf client-vrf  {
            type  string {
                length "1..1965";
                pattern "[^?' =,>|]+";
            }
            description "VRF where the client is connected";
        } // END of client-vrf definition.

        leaf connection-state  {
            type  string {
                length "1..1965";
                pattern "[^?' =,>|]+";
            }
            description "State of the connection with the client";
        } // END of connection-state definition.

        leaf connection-time  {
            type  yang:date-and-time {
                pattern "\\d{4}-\\d{2}-\\d{2}T\\d{2}:\\d{2}:\\d{2}(\\.\\d+)?(Z|[\\+\\-]\\d{2}:\\d{2})";
                }
                description "Time when the connection was established";
            } // END of connection-time definition.

            leaf last-activity-time  {
                type  yang:date-and-time {
                    pattern "\\d{4}-\\d{2}-\\d{2}T\\d{2}:\\d{2}:\\d{2}(\\.\\d+)?(Z|[\\+\\-]\\d{2}:\\d{2})";
                    }
                    description "Time of the last activity that happened on the connection";
                } // END of last-activity-time definition.

                leaf nb-session-requests  {
                    type  yang:counter32;
                    description "Number of session requests received on the connection";
                } // END of nb-session-requests definition.

                leaf nb-accepted-sessions  {
                    type  yang:counter32;
                    description "Number of accepted sessions on the connection";
                } // END of nb-accepted-sessions definition.

    } // END of twamp-server-connection-state definition.
    grouping twamp-server-config {
        description
            "Grouping for TWAMP Server configuration data";
        leaf port  {
            type  ipi-twamp-types:twamp_udp_port_t;
            description "Use this attribute to set Server TCP Port";
        } // END of port definition.

        leaf max-connection-duration  {
            type  uint8 {
                 range "0..120"  {
                    description "0..120: Supported range 0 - 120";
                 }
            }
            description "Set the maximum connection duration in hours, 0 to disable";
        } // END of max-connection-duration definition.

        leaf max-connections  {
            type  uint8 {
                 range "1..32"  {
                    description "1..32: Supported range 1 - 32";
                 }
            }
            description "Set the maximum connections";
        } // END of max-connections definition.

        leaf max-connections-per-client  {
            type  uint8 {
                 range "1..4"  {
                    description "1..4: Supported range 1 - 4";
                 }
            }
            description "Set the maximum number of connections per client";
        } // END of max-connections-per-client definition.

        leaf maximum-sessions  {
            type  uint16 {
                 range "1..2000"  {
                    description "1..2000: Supported range 1 - 2000";
                 }
            }
            description "Set the maximum number of test sessions for the server";
        } // END of maximum-sessions definition.

        leaf maximum-sessions-per-connection  {
            type  uint16 {
                 range "1..2000"  {
                    description "1..2000: Supported range 1 - 2000";
                 }
            }
            description "Set the maximum number of test sessions per client connection";
        } // END of maximum-sessions-per-connection definition.

        leaf inactivity-timeout  {
            type  uint8 {
                 range "0..30"  {
                    description "0..30: Supported range 0 - 30";
                 }
            }
            description "Set the control packet idle timeout value in minutes, 0 to disable";
        } // END of inactivity-timeout definition.

        leaf-list vrf-name  {
            type  leafref {
                path  "/ipi-network-instance:network-instances/ipi-network-instance:network-instance/ipi-vrf:vrf/ipi-vrf:config/ipi-vrf:vrf-name";
            }
            description "Use this attribute to add a custom vrf to the list of VRFs where the
                        twamp server is listening";
        } // END of vrf-name definition.

    } // END of twamp-server-config definition.
    grouping twamp-server-admin-config {
        description
            "Grouping for TWAMP Server admin configuration data";
        leaf enable  {
            type  empty;
            mandatory true;
            description "Enables TWAMP Server";
        } // END of enable definition.

        leaf administrative-state  {
            type  cml-data-types:cml_enable_disable_t;
            default "disable";
            description "Sets TWAMP Server administrative state";
        } // END of administrative-state definition.

    } // END of twamp-server-admin-config definition.
    grouping twamp-light-top {
        description
            "twamp-light-top";
        container light {
            description
                "TWAMP Light implementation";
            uses twamp-control-top;
            uses twamp-session-reflector-top;
        } // END of light-container definition.
    } // END of twamp-light-top definition.
    grouping twamp-server-top {
        description
            "twamp-server-top";
        container server {
            description
                "TWAMP Server implementation";
            container config {
                description
                    "Configuration data for TWAMP Server";
                uses twamp-server-config;
            } // END of config-container definition.
            container state {
                config false;
                description
                    "Operational state data for TWAMP Server";
                uses twamp-server-config;
                uses twamp-server-state;
            } // END of state-container definition.
            uses twamp-server-connections-top;
            uses twamp-server-sessions-top;
            uses twamp-server-admin-top;
        } // END of server-container definition.
    } // END of twamp-server-top definition.
    grouping twamp-overall-packet-rate-state {
        description
            "Grouping for TWAMP overall packet rate state";
        leaf packet-sending-rate  {
            type  uint32;
            units "pps";
            description "TWAMP packet sending rate";
        } // END of packet-sending-rate definition.

        leaf senders-rate  {
            type  uint32;
            units "pps";
            description "TWAMP senders rate";
        } // END of senders-rate definition.

        leaf reflectors-rate  {
            type  uint32;
            units "pps";
            description "TWAMP reflectors rate";
        } // END of reflectors-rate definition.

        leaf max-sending-rate  {
            type  uint32;
            units "pps";
            description "TWAMP maximum supported sending rate";
        } // END of max-sending-rate definition.

        leaf max-sending-rate-crossed  {
            type  boolean;
            description "TWAMP maximum supported sending rate crossed";
        } // END of max-sending-rate-crossed definition.

    } // END of twamp-overall-packet-rate-state definition.
    grouping twamp-overall-packet-rate-top {
        description
            "Grouping for TWAMP overall packet rate";
        container overall-packet-rate {
            description
                "Operational state data for TWAMP overall packet rate";
            container state {
                config false;
                description
                    "Operational state data for TWAMP overall packet rate";
                uses twamp-overall-packet-rate-state;
            } // END of state-container definition.
        } // END of overall-packet-rate-container definition.
    } // END of twamp-overall-packet-rate-top definition.
    grouping twamp-debug-config {
        description
            "Grouping for debug configuration for TWAMP";
        leaf options  {
            type  ipi-twamp-types:twamp_debug_t;
            description "Use this attribute to debug the twamp session";
        } // END of options definition.

    } // END of twamp-debug-config definition.
    grouping twamp-debug-terminal-state {
        description
            "Grouping for terminal debug operational state";
        leaf terminal-debug-status  {
            type  ipi-twamp-types:twamp_debug_t;
            description "Terminal debug option";
        } // END of terminal-debug-status definition.

    } // END of twamp-debug-terminal-state definition.
    grouping twamp-debug-top {
        description
            "Grouping for debug top";
        container debug {
            description
                "Debug Flags";
            container config {
                description
                    "Debug flags for configuration";
                uses twamp-debug-config;
            } // END of config-container definition.
            container state {
                config false;
                description
                    "Debug flags state information";
                uses twamp-debug-config;
                uses twamp-debug-terminal-state;
            } // END of state-container definition.
        } // END of debug-container definition.
    } // END of twamp-debug-top definition.

    grouping  twamp-grouping {
    description
        "Two-Way Active Measurement Protocol (TWAMP) data model";
    container twamp {
        if-feature feature-list:HAVE_TWAMP;
        description
            "Two-Way Active Measurement Protocol (TWAMP) data model";
        uses twamp-light-top;
        uses twamp-debug-top;
        uses twamp-server-top;
        uses twamp-overall-packet-rate-top;
        uses client-grouping;
        uses sessions-grouping;
    } // END of twamp-container definition.
    } // END of twamp-grouping definition.

    uses twamp-grouping;

    rpc twamp-client-start-connection {
        if-feature feature-list:HAVE_TWAMP;
        description "Start TWAMP client connection";
        input  {
            leaf connection-name  {
                type string {
                    length "1..128";
                }
                mandatory true;
                description "Sets client connection Name";
            }
            leaf vrf-name  {
                type string;
                default "default";
                description "Use this attribute to set the connection VRF name";
            }
            leaf packet-count  {
                type uint32 {
                    range "0..1000000";
                }
                mandatory true;
                description "Two-may Active Measurement Protocol client connection pkt count";
            }
        }
    }

    rpc twamp-client-stop-connection {
        if-feature feature-list:HAVE_TWAMP;
        description "Stop TWAMP client connection";
        input  {
            leaf connection-name  {
                type string {
                    length "1..128";
                }
                mandatory true;
                description "Sets client connection Name";
            }
            leaf vrf-name  {
                type string;
                default "default";
                description "Use this attribute to set the connection VRF name";
            }
        }
    }

    rpc twamp-client-reset-session {
        if-feature feature-list:HAVE_TWAMP;
        description "Reset TWAMP client session";
        input  {
            leaf connection-name  {
                type string {
                    length "1..128";
                }
                mandatory true;
                description "The client connection Name where the session will be reset";
            }
            leaf session-name  {
                type string {
                    length "1..128";
                }
                mandatory true;
                description "The client session that will be reset";
            }
            leaf vrf-name  {
                type string;
                default "default";
                description "Use this attribute to set the connection VRF name";
            }
        }
    }

    rpc twamp-session-clear-measurement {
        if-feature feature-list:HAVE_TWAMP;
        description "Clear and restart the TWAMP Session measurement";
        input  {
            leaf session-name  {
                type string {
                    length "1..32";
                }
                mandatory true;
                description "Session name";
            }
        }
    }

    rpc twamp-session-clear-measurement-all {
        if-feature feature-list:HAVE_TWAMP;
        description "Clear and restart all the TWAMP Sessions measurement";
    }

    rpc twamp-test-session-start {
        if-feature feature-list:HAVE_TWAMP;
        description "Start TWAMP Light Control Test Session";
        input  {
            leaf session-name  {
                type string {
                    length "1..128";
                }
                mandatory true;
                description "Test Session name";
            }
            leaf packet-count  {
                type uint16 {
                    range "1..65535";
                }
                mandatory true;
                description "Number of packets to send";
            }
            leaf packet-interval  {
                type uint16 {
                    range "500..10000";
                }
                default "1000";
                description "Interval between each packet";
            }
            leaf delay-threshold  {
                type uint32 {
                    range "0..1000000";
                }
                default "0";
                description "Delay threshold in microseconds. If crossed, a notification will be
                            sent.";
            }
        }
    }

    rpc twamp-test-session-stop {
        if-feature feature-list:HAVE_TWAMP;
        description "Stop TWAMP Light Control Test Session";
        input  {
            leaf session-name  {
                type string {
                    length "1..128";
                }
                mandatory true;
                description "Test Session name";
            }
        }
    }

    rpc twamp-terminal-debug-on {
        if-feature feature-list:HAVE_TWAMP;
        description "Enable TWAMP debug categories";
        input  {
            leaf terminal-debug-options  {
                type ipi-twamp-types:twamp_debug_t;
                mandatory true;
                description "Two-may Active Measurement Protocol TWAMP debug categories";
            }
        }
    }

    rpc twamp-terminal-debug-off {
        if-feature feature-list:HAVE_TWAMP;
        description "Enable TWAMP debug categories";
        input  {
            leaf terminal-debug-options  {
                type ipi-twamp-types:twamp_debug_t;
                mandatory true;
                description "Two-may Active Measurement Protocol TWAMP debug categories";
            }
        }
    }

    notification twamp-server-client-connected {
        if-feature feature-list:HAVE_TWAMP;

        description "Indicates when a remote Client connected to the TWAMP Server.";

        leaf severity {
            type cml-data-types:cml_notif_severity_t;
            description "Notification severity level (value: MINOR)";
        }

        leaf eventClass {
            type cml-data-types:cml_notif_class_t;
            description "Notification event class (value: STATE)";
        }

        leaf connection-id {
            type  uint32;
        description
            "Connection ID";
        }

        leaf client-address {
            type  inet:ip-address;
        description
            "IP address of the client";
        }

        leaf client-port {
            type  uint16;
        description
            "Port used by the client";
        }

        leaf client-vrf {
            type  string;
        description
            "VRF where the client is connected";
        }
    }

    notification twamp-server-client-disconnected {
        if-feature feature-list:HAVE_TWAMP;

        description "Indicates when a remote Client disconnected from the TWAMP Server.";

        leaf severity {
            type cml-data-types:cml_notif_severity_t;
            description "Notification severity level (value: MINOR)";
        }

        leaf eventClass {
            type cml-data-types:cml_notif_class_t;
            description "Notification event class (value: STATE)";
        }

        leaf connection-id {
            type  uint32;
        description
            "Connection ID";
        }

        leaf client-address {
            type  inet:ip-address;
        description
            "IP address of the client";
        }

        leaf client-port {
            type  uint16;
        description
            "Port used by the client";
        }

        leaf client-vrf {
            type  string;
        description
            "VRF where the client is connected";
        }
    }

    notification twamp-server-session-accepted {
        if-feature feature-list:HAVE_TWAMP;

        description "Indicates that a Session from the connection-id has been Accepted in the TWAMP Server.";

        leaf severity {
            type cml-data-types:cml_notif_severity_t;
            description "Notification severity level (value: MINOR)";
        }

        leaf eventClass {
            type cml-data-types:cml_notif_class_t;
            description "Notification event class (value: STATE)";
        }

        leaf session-id {
            type  string;
        description
            "Session ID";
        }

        leaf connection-id {
            type  uint32;
        description
            "Connection ID";
        }

        leaf sender-address {
            type  inet:ip-address;
        description
            "IP address of the TWAMP sender";
        }

        leaf sender-port {
            type  uint16;
        description
            "Port used by the sender";
        }

        leaf receiver-address {
            type  inet:ip-address;
        description
            "IP address of the TWAMP receiver";
        }

        leaf receiver-port {
            type  uint16;
        description
            "Port used by the receiver";
        }

        leaf receiver-vrf {
            type  string;
        description
            "VRF where the receiver is running";
        }
    }

    notification twamp-server-sessions-started {
        if-feature feature-list:HAVE_TWAMP;

        description "Indicates that a Session from the connection-id has been Started in the TWAMP Server.";

        leaf severity {
            type cml-data-types:cml_notif_severity_t;
            description "Notification severity level (value: MINOR)";
        }

        leaf eventClass {
            type cml-data-types:cml_notif_class_t;
            description "Notification event class (value: STATE)";
        }

        leaf session-id {
            type  string;
        description
            "Session ID";
        }

        leaf connection-id {
            type  uint32;
        description
            "Connection ID";
        }
    }

    notification twamp-server-sessions-stopped {
        if-feature feature-list:HAVE_TWAMP;

        description "Indicates that a Session from the connection-id has been Stopped in the TWAMP Server.";

        leaf severity {
            type cml-data-types:cml_notif_severity_t;
            description "Notification severity level (value: MINOR)";
        }

        leaf eventClass {
            type cml-data-types:cml_notif_class_t;
            description "Notification event class (value: STATE)";
        }

        leaf session-id {
            type  string;
        description
            "Session ID";
        }

        leaf connection-id {
            type  uint32;
        description
            "Connection ID";
        }
    }

    notification twamp-server-client-inactivity-timeout {
        if-feature feature-list:HAVE_TWAMP;

        description "TWAMP Client reached the inactivity timeout and will be disconnected from TWAMP Server.";

        leaf severity {
            type cml-data-types:cml_notif_severity_t;
            description "Notification severity level (value: MINOR)";
        }

        leaf eventClass {
            type cml-data-types:cml_notif_class_t;
            description "Notification event class (value: STATE)";
        }

        leaf connection-id {
            type  uint32;
        description
            "Connection ID";
        }

        leaf last-activity-time {
            type  yang:date-and-time;
        description
            "Time of the last activity that happened on the connection";
        }
    }

    notification twamp-server-client-maximum-connection-duration-timeout {
        if-feature feature-list:HAVE_TWAMP;

        description "TWAMP Client reached the maximum connection duration with the TWAMP Server and Client will be disconnected.";

        leaf severity {
            type cml-data-types:cml_notif_severity_t;
            description "Notification severity level (value: MINOR)";
        }

        leaf eventClass {
            type cml-data-types:cml_notif_class_t;
            description "Notification event class (value: STATE)";
        }

        leaf connection-id {
            type  uint32;
        description
            "Connection ID";
        }

        leaf connection-time {
            type  yang:date-and-time;
        description
            "Time when the connection was established";
        }
    }

    notification twamp-server-maximum-connections-exceeded {
        if-feature feature-list:HAVE_TWAMP;

        description "Indicates that the maximum number of Connections allowed has been exceeded on TWAMP Server.";

        leaf severity {
            type cml-data-types:cml_notif_severity_t;
            description "Notification severity level (value: MINOR)";
        }

        leaf eventClass {
            type cml-data-types:cml_notif_class_t;
            description "Notification event class (value: STATE)";
        }

        leaf max-connections {
            type  uint8;
        description
            "Set the maximum connections";
        }
    }

    notification twamp-server-maximum-sessions-exceeded {
        if-feature feature-list:HAVE_TWAMP;

        description "Indicates that the maximum number of Sessions allowed has been exceeded on TWAMP Server.";

        leaf severity {
            type cml-data-types:cml_notif_severity_t;
            description "Notification severity level (value: MINOR)";
        }

        leaf eventClass {
            type cml-data-types:cml_notif_class_t;
            description "Notification event class (value: STATE)";
        }

        leaf maximum-sessions {
            type  uint16;
        description
            "Set the maximum number of test sessions for the server";
        }
    }

    notification twamp-server-maximum-connections-per-client-exceeded {
        if-feature feature-list:HAVE_TWAMP;

        description "The TWAMP Client reached the maximum allowed connections with the TWAMP Server.";

        leaf severity {
            type cml-data-types:cml_notif_severity_t;
            description "Notification severity level (value: MINOR)";
        }

        leaf eventClass {
            type cml-data-types:cml_notif_class_t;
            description "Notification event class (value: STATE)";
        }

        leaf max-connections-per-client {
            type  uint8;
        description
            "Set the maximum number of connections per client";
        }

        leaf connection-id {
            type  uint32;
        description
            "Connection ID";
        }
    }

    notification twamp-server-maximum-sessions-per-connection-exceeded {
        if-feature feature-list:HAVE_TWAMP;

        description "The TWAMP Client reached the maximum allowed number of sessions per connection with the TWAMP Server.";

        leaf severity {
            type cml-data-types:cml_notif_severity_t;
            description "Notification severity level (value: MINOR)";
        }

        leaf eventClass {
            type cml-data-types:cml_notif_class_t;
            description "Notification event class (value: STATE)";
        }

        leaf maximum-sessions-per-connection {
            type  uint16;
        description
            "Set the maximum number of test sessions per client connection";
        }

        leaf connection-id {
            type  uint32;
        description
            "Connection ID";
        }
    }

    notification twamp-delay-threshold-breached {
        if-feature feature-list:HAVE_TWAMP;

        description "This event is generated when the RTT delay value is greater than the threshold value.";

        leaf severity {
            type cml-data-types:cml_notif_severity_t;
            description "Notification severity level (value: CRITICAL)";
        }

        leaf eventClass {
            type cml-data-types:cml_notif_class_t;
            description "Notification event class (value: STATE)";
        }

        leaf session-name {
            type  string;
        description
            "Test Session name associated with this instance";
        }

        leaf vrf-name {
            type  string;
        description
            "Use this attribute to set the session VRF name";
        }

        leaf average {
            type  uint64;
        description
            "This attribute represents the average value within the statistics";
        }
    }

    notification twamp-overall-rate-crossed {
        if-feature feature-list:HAVE_TWAMP;

        description "Indicates that the overall supported TWAMP rate limit has been crossed.";

        leaf severity {
            type cml-data-types:cml_notif_severity_t;
            description "Notification severity level (value: MAJOR)";
        }

        leaf eventClass {
            type cml-data-types:cml_notif_class_t;
            description "Notification event class (value: STATE)";
        }

        leaf packet-sending-rate {
            type  uint32;
        description
            "TWAMP packet sending rate";
        }

        leaf senders-rate {
            type  uint32;
        description
            "TWAMP senders rate";
        }

        leaf reflectors-rate {
            type  uint32;
        description
            "TWAMP reflectors rate";
        }

        leaf max-sending-rate {
            type  uint32;
        description
            "TWAMP maximum supported sending rate";
        }

        leaf max-sending-rate-crossed {
            type  boolean;
        description
            "TWAMP maximum supported sending rate crossed";
        }
    }

    notification twamp-overall-rate-crossed-cleared {
        if-feature feature-list:HAVE_TWAMP;

        description "Indicates that the overall crossed TWAMP rate limit has been cleared.";

        leaf severity {
            type cml-data-types:cml_notif_severity_t;
            description "Notification severity level (value: WARNING)";
        }

        leaf eventClass {
            type cml-data-types:cml_notif_class_t;
            description "Notification event class (value: STATE)";
        }

        leaf packet-sending-rate {
            type  uint32;
        description
            "TWAMP packet sending rate";
        }

        leaf senders-rate {
            type  uint32;
        description
            "TWAMP senders rate";
        }

        leaf reflectors-rate {
            type  uint32;
        description
            "TWAMP reflectors rate";
        }

        leaf max-sending-rate {
            type  uint32;
        description
            "TWAMP maximum supported sending rate";
        }

        leaf max-sending-rate-crossed {
            type  boolean;
        description
            "TWAMP maximum supported sending rate crossed";
        }
    }

    notification twamp-client-session-accepted {
        if-feature feature-list:HAVE_TWAMP;

        description "The TWAMP Client session has been accepted by the TWAMP Server.";

        leaf severity {
            type cml-data-types:cml_notif_severity_t;
            description "Notification severity level (value: MINOR)";
        }

        leaf eventClass {
            type cml-data-types:cml_notif_class_t;
            description "Notification event class (value: STATE)";
        }

        leaf session-name {
            type  string;
        description
            "Sets client connection Name";
        }

        leaf connection-name {
            type  string;
        description
            "Sets client connection Name";
        }

        leaf vrf-name {
            type  string;
        description
            "Use this attribute to set the Connection VRF name";
        }
    }

    notification twamp-client-sessions-started {
        if-feature feature-list:HAVE_TWAMP;

        description "The TWAMP Client session has been started with the TWAMP Server.";

        leaf severity {
            type cml-data-types:cml_notif_severity_t;
            description "Notification severity level (value: MINOR)";
        }

        leaf eventClass {
            type cml-data-types:cml_notif_class_t;
            description "Notification event class (value: STATE)";
        }

        leaf session-name {
            type  string;
        description
            "Sets client connection Name";
        }

        leaf connection-name {
            type  string;
        description
            "Sets client connection Name";
        }

        leaf vrf-name {
            type  string;
        description
            "Use this attribute to set the Connection VRF name";
        }
    }

    notification twamp-client-sessions-stopped {
        if-feature feature-list:HAVE_TWAMP;

        description "The TWAMP Client session has been stopped with the TWAMP Server.";

        leaf severity {
            type cml-data-types:cml_notif_severity_t;
            description "Notification severity level (value: MINOR)";
        }

        leaf eventClass {
            type cml-data-types:cml_notif_class_t;
            description "Notification event class (value: STATE)";
        }

        leaf session-name {
            type  string;
        description
            "Sets client connection Name";
        }

        leaf connection-name {
            type  string;
        description
            "Sets client connection Name";
        }

        leaf vrf-name {
            type  string;
        description
            "Use this attribute to set the Connection VRF name";
        }
    }

    notification twamp-session-measurement-threshold-crossed {
        if-feature feature-list:HAVE_TWAMP;

        description "Indicates that the TWAMP Session Measurement has crossed the configured threshold.";

        leaf severity {
            type cml-data-types:cml_notif_severity_t;
            description "Notification severity level (value: MINOR)";
        }

        leaf eventClass {
            type cml-data-types:cml_notif_class_t;
            description "Notification event class (value: STATE)";
        }

        leaf session-name {
            type  string;
        description
            "TWAMP End-to-End Session name";
        }

        leaf average-delay {
            type  uint64;
        description
            "This attribute represents the average delay value";
        }
    }

    notification twamp-session-measurement-loss-changed {
        if-feature feature-list:HAVE_TWAMP;

        description "Indicates that the TWAMP Session Measurement loss has changed.";

        leaf severity {
            type cml-data-types:cml_notif_severity_t;
            description "Notification severity level (value: MINOR)";
        }

        leaf eventClass {
            type cml-data-types:cml_notif_class_t;
            description "Notification event class (value: STATE)";
        }

        leaf session-name {
            type  string;
        description
            "TWAMP End-to-End Session name";
        }

        leaf packet-loss {
            type  decimal64 {
                 fraction-digits 4;            }
        description
            "This attribute represents the percentage of lost packets in a
                    measurement interval";
        }
    }

}
