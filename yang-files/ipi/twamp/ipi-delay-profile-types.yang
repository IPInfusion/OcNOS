/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-delay-profile-types.yang
*
*/

module ipi-delay-profile-types {

    yang-version 1.1;

    namespace   "http://www.ipinfusion.com/yang/ocnos/ipi-delay-profile-types";

    prefix "ipi-delay-profile-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Delay Profile types";


    revision "2023-03-02" {
        description "Added one way measurement option";
        reference " 0.3.0.";
    }

    revision "2022-06-01" {
        description "Updated the yang file with feature";
        reference " 0.2.0.";
    }

    revision "2021-11-25" {
        description "Initial Release for Delay Profile types";
        reference " 0.1.0.";
    }



    typedef  delay_profile_measurement_mode_t {
        type enumeration {
            enum one-way {
                value 0;
                if-feature feature-list:HAVE_PTPD;
                description "One way measurement";
            }
            enum two-way {
                value 1;
                description "Two way measurement";
            }
        }
        description "type definition for DELAY_PROFILE_MEASUREMENT_MODE_T";
    }

    typedef  delay_profile_type_t {
        type enumeration {
            enum interfaces {
                value 1;
                description "Enter the delay profile interfaces mode";
            }
        }
        description "type definition for DELAY_PROFILE_TYPE_T";
    }

}
