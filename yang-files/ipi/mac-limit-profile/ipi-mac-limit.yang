/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mac-limit.yang
*
*/

module ipi-mac-limit {

    yang-version 1.1;

    namespace   "http://www.ipinfusion.com/yang/ocnos/ipi-mac-limit";

    prefix "ipi-mac-limit";

    import ipi-mac-limit-types {
        prefix ipi-mac-limit-types;
        revision-date 2025-04-08;
    }

    organization
        "IP Infusion Inc.";

    contact
        "Address: 3965 Freedom Circle, Suite 200, Santa Clara, CA 95054
         Phone: +1 408-400-1900
         E-mail: support@ipinfusion.com
         Web: http://www.ipinfusion.com/";

    description
        "MAC Limiting";


    revision "2025-05-22" {
        description "Remove 'errdisable-timeout' config when action 'log-errdisable' is removed using 'no action'";
        reference " 0.1.3.";
    }

    revision "2025-05-20" {
        description "Fix compilation warnings";
        reference " 0.1.2.";
    }

    revision "2025-05-19" {
        description "Add missing length check for mac-lim-profile-name";
        reference " 0.1.1.";
    }

    revision "2025-04-08" {
        description "Initial Version";
        reference " 0.1.0.";
    }

    grouping mac-limit-profiles-top {
        description
            "Top level grouping for MAC limit profile";
        container mac-limit-profiles {
            description
                "Top level container for MAC move instance";

            list mac-limit-profile-inst {
                key "mac-lim-profile-name";
                description
                    "List for MAC limit profile";
                leaf mac-lim-profile-name  {
                    type  leafref {
                        path  "../config/mac-lim-profile-name";
                    }
                    description "Instance MAC limit config";
                } // END of mac-lim-profile-name definition.

                container config {
                    description
                        "MAC limit profile config";
                    uses mac-limit-profile-config;
                } // END of config-container definition.
                container state {
                    config false;
                    description
                        "Operation state data for MAC limit profile";
                    uses mac-limit-profile-config;
                } // END of state-container definition.
            } // End of mac-limit-profile-inst-list
        } // END of mac-limit-profiles-container definition.
    } // END of mac-limit-profiles-top definition.
    grouping mac-limit-profile-config {
        description
            "Grouping for global MAC limit configuration attributes";
        leaf mac-lim-profile-name  {
            type  string {
                length "1..255";
                pattern "[^?' =,>|]+";
            }
            description "Instance MAC limit config";
        } // END of mac-lim-profile-name definition.

        leaf learning-limit  {
            type  uint32 {
                 range "1..131071"  {
                    description "1..131071: Supported range 1 - 131071";
                 }
            }
            default "131071";
            description "Number of MAC limit supported";
        } // END of learning-limit definition.

        leaf action  {
            type  ipi-mac-limit-types:mac_limit_action_t;
            default "log-only";
            description "MAC limit action";
        } // END of action definition.

        leaf high-watermark  {
            type  uint16 {
                 range "1..100"  {
                    description "1..100: Supported range 1 - 100";
                 }
            }
            default "90";
            description "High watermark for logging";
        } // END of high-watermark definition.

        leaf low-watermark  {
            type  uint16 {
                 range "1..100"  {
                    description "1..100: Supported range 1 - 100";
                 }
            }
            default "70";
            description "Low watermark for logging";
        } // END of low-watermark definition.

        leaf errdisable-timeout-interval  {
            // when " ipi-mac-limit:mac-limit-global/mac-limit-profiles/mac-limit-profile-inst/config/action == '2' ";
            type  uint32 {
                 range "0..86400"  {
                    description "0..86400: Supported range 0 - 86400";
                 }
            }
            units "seconds";
            default "0";
            description "Error disable timeout interval";
        } // END of errdisable-timeout-interval definition.

    } // END of mac-limit-profile-config definition.

    grouping  mac-limit-global-grouping {
    description
        "Global MAC Limit container";
    container mac-limit-global {
        description
            "Global MAC Limit container";
        uses mac-limit-profiles-top;
    } // END of mac-limit-global-container definition.
    } // END of mac-limit-global-grouping definition.

    uses mac-limit-global-grouping;

}
