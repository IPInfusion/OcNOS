/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-port-vlan.yang
*
*/

module ipi-port-vlan {

    yang-version 1.1;

    namespace   "http://www.ipinfusion.com/yang/ocnos/ipi-port-vlan";

    prefix "ipi-port-vlan";

    import cml-data-types {
        prefix cml-data-types;
        revision-date 2026-05-15;
    }

    import ipi-port-vlan-types {
        prefix ipi-port-vlan-types;
        revision-date 2023-01-23;
    }

    import ipi-network-instance {
        prefix ipi-network-instance;
        revision-date 2026-08-12;
    }

    import ipi-interface {
        prefix ipi-interface;
        revision-date 2026-03-10;
    }

    import ipi-vlan {
        prefix ipi-vlan;
        revision-date 2026-02-02;
    }

    import ipi-bridge {
        prefix ipi-bridge;
        revision-date 2026-07-30;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Port VLAN configuration";


    revision "2026-02-12" {
        description "Added dependency for port-security";
        reference " 0.20.2.";
    }

    revision "2025-11-17" {
        description "MAC normalization function for the vlan mac-address attribute.";
        reference " 0.20.1.";
    }

    revision "2025-10-29" {
        description "Removed the when expression on translated SVLAN deletion";
        reference " 0.20.0.";
    }

    revision "2025-06-13" {
        description "Modified the Trigger based on the CVLAN and SVLAN deletion";
        reference " 0.19.0.";
    }

    revision "2025-03-18" {
        description "Added if-feature flag in when tag for global vlan config";
        reference " 0.18.0.";
    }

    revision "2025-02-18" {
        description "Added when tag for association-trunk-vlan-id attribute";
        reference " 0.17.9.";
    }

    revision "2025-02-15" {
        description "Added CML_SKIP_HITLESS_MERGE flag for svlan-id attribute";
        reference " 0.17.8.";
    }

    revision "2025-01-24" {
        description "Added dependencies for customer edge vlan registration";
        reference " 0.17.7.";
    }

    revision "2024-11-21" {
        description "Added CML_SKIP_HITLESS_MERGE flag for allowed-vlan-id attribute";
        reference " 0.17.6.";
    }

    revision "2024-08-21" {
        description "Added dependent object for cvlan registration table to create after switchport mode changed";
        reference " 0.17.5.";
    }

    revision "2024-08-01" {
        description "Add dependencies for port-security";
        reference " 0.17.4.";
    }

    revision "2024-07-31" {
        description "Deprecated the Switchport hybrid allowed vlan except CLI";
        reference " 0.17.4.";
    }

    revision "2024-06-19" {
        description "Removed the when tag which was causing DB sync issue ";
        reference " 0.17.3.";
    }

    revision "2024-06-18" {
        description "Added SWFWDR flag for egress-tagged CLI";
        reference " 0.17.2.";
    }

    revision "2024-02-23" {
        description "Added the when tag for the vlan-id attribute under allowed-vlan-id ";
        reference " 0.17.1.";
    }

    revision "2024-01-30" {
        description "Added a when tag in  port-vlan pointing to intra-domain-link IFNAME";
        reference " 0.17.0.";
    }

    revision "2023-11-08" {
        description "Removed SET_ONLY from allowed-vlan-id";
        reference " 0.16.9.";
    }

    revision "2023-10-01" {
        description "Add SET_ONLY to allowed-vlan-id";
        reference " 0.16.8.";
    }

    revision "2023-07-14" {
        description "Blocking customer-network CLI's for Qumran";
        reference " 0.16.7.";
    }

    revision "2023-07-11" {
        description "Added HAVE_DUNE flag for provider-network vlan translation";
        reference " 0.16.6.";
    }

    revision "2023-06-16" {
        description "Enabling customer-network vlan translation option for DUNE devices";
        reference " 0.16.5.";
    }

    revision "2023-05-10" {
        description "Modified the trigger to remove bridge-group from po interface when mapped to mlag and members";
        reference " 0.16.4.";
    }

    revision "2023-04-17" {
        description "Added a trigger to remove bridge-group from po interface when mapped to mlag and members";
        reference " 0.16.3.";
    }

    revision "2023-04-06" {
        description "Removed the when tag for the vlan-id attribute under default-vlan-config grouping";
        reference " 0.16.2.";
    }

    revision "2023-03-29" {
        description "Added dependency among private-vlan and switchport mode";
        reference " 0.16.1.";
    }

    revision "2023-01-24" {
        description "Added enclosing container for port vlan object list";
        reference " 0.16.0.";
    }

    revision "2023-01-23" {
        description "Enabling customer-network option for qumran devices";
        reference " 0.15.5.";
    }

    revision "2023-01-17" {
        description "Added dependency to allowed-vlan";
        reference " 0.15.4.";
    }

    revision "2023-01-05" {
        description "Leafref correction for config container";
        reference " 0.15.3.";
    }

    revision "2022-12-12" {
        description "Reverting port-vlan enclosing container changes";
        reference " 0.15.2.";
    }

    revision "2022-12-09" {
        description "Added enclosing container for port vlan object list";
        reference " 0.15.1.";
    }

    revision "2022-12-01" {
        description "Updated when expressions";
        reference " 0.15.0.";
    }

    revision "2022-08-29" {
        description "Removed 'when' tags to unblock port security from trunk mode";
        reference " 0.14.5.";
    }

    revision "2022-08-19" {
        description "Added implicit_delete under cvlan-svlan-mapping config container";
        reference " 0.14.4.";
    }

    revision "2022-08-03" {
        description "Added dependency validation flag for vlan and svlan";
        reference " 0.14.3.";
    }

    revision "2022-08-01" {
        description "Making EVC, OEP and OVC CLIs visible for only x86 builds";
        reference " 0.14.1.";
    }

    revision "2022-07-30" {
        description "Updated when expressions in yang";
        reference " 0.14.0.";
    }

    revision "2022-07-28" {
        description "Modified the 'when' tags for translated-svlan-id to remove dependency-validation";
        reference " 0.14.2.";
    }

    revision "2022-07-11" {
        description "Updated dependency module ipi-vlan";
        reference " 0.13.3.";
    }

    revision "2022-07-04" {
        description "Added authentication dependency for bridge configuration in interface";
        reference " 0.13.2.";
    }

    revision "2022-06-27" {
        description "Updated when expressions in yang file";
        reference " 0.13.1.";
    }

    revision "2022-06-01" {
        description "Updated the yang file with feature";
        reference " 0.13.0.";
    }

    revision "2022-04-05" {
        description "changed the cli from  no switchport (provider-network) vlan translation svlan VLAN_ID svlan VLAN_ID to no switchport (provider-network) vlan translation svlan VLAN_ID to fix JIRA-56532";
        reference " 0.12.0.";
    }

    revision "2022-03-30" {
        description "Fixed Hybrid port VLAN Netconf issues and enabled support for Bridge related RPCs";
        reference " 0.11.0.";
    }

    revision "2022-03-09" {
        description "Added implicit_delete under switched-vlan and allowed-vlan container";
        reference " 0.14.6.";
    }

    revision "2022-02-02" {
        description "Changed attribute disable-default-vlan to remove-default-vlan";
        reference " 0.10.1.";
    }

    revision "2022-01-19" {
        description "Added attribute for disable default vlan";
        reference " 0.10.0.";
    }

    revision "2022-01-13" {
        description "Modified sub module";
        reference " 0.9.0.";
    }

    revision "2021-11-16" {
        description "SKU compilation fixes";
        reference " 0.8.2.";
    }

    revision "2021-10-27" {
        description "Added switchport private-vlan association trunk";
        reference " 0.8.1.";
    }

    revision "2021-10-18" {
        description "Removed custom DB triggers and added Netconf support for private VLAN feature";
        reference " 0.8.0.";
    }

    revision "2021-09-21" {
        description "Added when tags and a custom DB trigger to fix JIRA-50460 ";
        reference " 0.7.9.";
    }

    revision "2021-09-18" {
        description "Private VLAN DB clearance issues fixed";
        reference " 0.7.8.";
    }

    revision "2021-09-15" {
        description "Removing implicit-delete tags that were generated as warnings in zebm log";
        reference " 0.7.7.";
    }

    revision "2021-09-14" {
        description "Added a when tag to cvlan-id attribute of cvlan-svlan-mapping objectlist to fix JIRA-49881";
        reference " 0.7.6.";
    }

    revision "2021-09-03" {
        description "Added a whentag to port-security container to fix JIRA-43798";
        reference " 0.7.5.";
    }

    revision "2021-09-01" {
        description "Changed base interface module's switchport attribute name and the datatype from bool to empty";
        reference " 0.7.4.";
    }

    revision "2021-08-26" {
        description "Fix for JIRA-49703 pertaining to PB transactional CLIs";
        reference " 0.7.3.";
    }

    revision "2021-08-09" {
        description "Restructured current Provider Bridging hierarchy to OpenConfig style.";
        reference " 0.7.2.";
    }

    revision "2021-08-04" {
        description "Deprecated egress-tagging-enabled-vlans attribute and allowed-vlan-id attribute will be used with hybrid type interface mode configurations";
        reference " 0.7.1.";
    }

    revision "2021-07-29" {
        description "Netconf support for port security feature enabled";
        reference " 0.7.0.";
    }

    revision "2021-04-27" {
        description "Data model changes done for JIRA-44181";
        reference " 0.6.3.";
    }

    revision "2021-04-08" {
        description "Data model changes done for ocmp-608";
        reference " 0.6.2.";
    }

    revision "2021-03-30" {
        description "Disabled YANG support for port-security feature";
        reference " 0.6.1.";
    }

    revision "2021-03-05" {
        description "Removed dot1q-ether-type attribute and moved to mo_ipi-if-extended.xml file";
        reference " 0.6.0.";
    }

    revision "2021-02-05" {
        description "Change static mac vlan parameters";
        reference " 0.5.0.";
    }

    revision "2021-01-27" {
        description "Change to have descriptions for individual leafs";
        reference " 0.4.0.";
    }

    revision "2020-12-15" {
        description "Change to have data-types in lower case instead of camel case";
        reference " 0.3.0.";
    }

    revision "2018-12-28" {
        description "Provider bridge static MAC support for Qumran platform";
        reference " 0.2.0.";
    }

    revision "2018-06-21" {
        description "Initial Version";
        reference " 0.1.0.";
    }

    grouping oep-mapping-config {
        description
            "Grouping for OEP mapping configuration data";
        leaf type  {
            type  ipi-port-vlan-types:port_vlan_oep_map_type_t;
            description "oep map type";
        } // END of type definition.

        leaf oep-name  {
            type  string {
                length "1..1965";
                pattern "[^?' =,>|]+";
            }
            description "oep mapping table name";
        } // END of oep-name definition.

    } // END of oep-mapping-config definition.
    grouping oep-mapping-top {
        description
            "Top level grouping for OEP mapping";
        container oep-mappings {
            description
                "Enclosing container for list OEP mappings";
            uses oep-mapping-list;
        } // END of oep-mappings-container definition.
    } // END of oep-mapping-top definition.
    grouping oep-mapping-list {
        description
            "Grouping for OEP mapping";
    } // END of oep-mapping-list definition.
    grouping mapping-config {
        description
            "Grouping for private vlan mapping configuration data";
        leaf vlan-id  {
            type  uint16 {
                 range "2..4094"  {
                    description "2..4094: Supported range 2 - 4094";
                 }
            }
            description "Primary vlan identifier";
        } // END of vlan-id definition.

        leaf associate-vlan-id  {
            when " /ipi-interface:interfaces/ipi-interface:interface/ipi-port-vlan:port-vlan/ipi-port-vlan:private-vlan/ipi-port-vlan:config/ipi-port-vlan:mode = 'host' ";
            type  uint16;
            description "Private VLAN Association";
        } // END of associate-vlan-id definition.

        leaf mapping-vlan-id  {
            when " /ipi-interface:interfaces/ipi-interface:interface/ipi-port-vlan:port-vlan/ipi-port-vlan:private-vlan/ipi-port-vlan:config/ipi-port-vlan:mode = 'promiscuous' ";
            type  cml-data-types:cml_range_t;
            description "private-vlan Mapping";
        } // END of mapping-vlan-id definition.

        leaf association-trunk-vlan-id  {
            when " /ipi-interface:interfaces/ipi-interface:interface/ipi-port-vlan:port-vlan/ipi-port-vlan:private-vlan/ipi-port-vlan:config/ipi-port-vlan:mode != 'trunk' ";
            type  uint16 {
                 range "2..4094"  {
                    description "2..4094: Supported range 2 - 4094";
                 }
            }
            description "private-vlan Mapping";
        } // END of association-trunk-vlan-id definition.

    } // END of mapping-config definition.
    grouping association-top {
        description
            "Top level grouping for private vlan data";
        container associations {
            description
                "Enclosing container for list of private vlan mappings";
            uses association-list;
        } // END of associations-container definition.
    } // END of association-top definition.
    grouping association-list {
        description
            "Grouping for private vlan data";

        list association {
        when " /ipi-interface:interfaces/ipi-interface:interface/ipi-port-vlan:port-vlan/ipi-port-vlan:private-vlan/ipi-port-vlan:config/ipi-port-vlan:mode ";
            key "vlan-id";
            description
                "List of private vlan mappings";
            leaf vlan-id  {
                type  leafref {
                    path  "../config/vlan-id";
                }
                description "Primary vlan identifier";
            } // END of vlan-id definition.

            container config {
                description
                    "Configuration data for private vlan mapping";
                uses mapping-config;
            } // END of config-container definition.
            container state {
                config false;
                description
                    "Operational state data";
                uses mapping-config;
            } // END of state-container definition.
        } // End of association-list
    } // END of association-list definition.
    grouping port-private-vlan-config {
        description
            "Grouping for private vlan mode configuration";
        leaf mode  {
            type  ipi-port-vlan-types:port_vlan_pvlan_mode_t;
            mandatory true;
            description "Use this attribute to make a layer2 port as a host port or promiscuous
                        port or pvlan-trunk port";
        } // END of mode definition.

    } // END of port-private-vlan-config definition.
    grouping port-private-vlan-top {
        description
            "Top level grouping for private vlan";
        container private-vlan {
            when " /ipi-interface:interfaces/ipi-interface:interface/ipi-port-vlan:port-vlan/ipi-port-vlan:switched-vlans/ipi-port-vlan:switched-vlan/ipi-port-vlan:config/ipi-port-vlan:interface-mode = 'access' or /ipi-interface:interfaces/ipi-interface:interface/ipi-port-vlan:port-vlan/ipi-port-vlan:switched-vlans/ipi-port-vlan:switched-vlan/ipi-port-vlan:config/ipi-port-vlan:interface-mode = 'trunk' ";
            if-feature feature-list:HAVE_PVLAN;
            description
                "Container for private vlan configuration and state data";
            container config {
                presence "Configure private vlan mode";
                description
                    "Configuration data for port private vlan";
                uses port-private-vlan-config;
            } // END of config-container definition.
            container state {
                config false;
                description
                    "Operational state data";
                uses port-private-vlan-config;
            } // END of state-container definition.
            uses association-top;
        } // END of private-vlan-container definition.
    } // END of port-private-vlan-top definition.
    grouping port-security-mac-default-vlan-config {
        description
            "Port security configuration with MAC default vlan";
        leaf mac-address  {
            type  cml-data-types:cml_mac_addr_t {
                length "1..1965";
            }
            description "Use this attribute to configure the static forwarding entry for
                        port-security";
        } // END of mac-address definition.

    } // END of port-security-mac-default-vlan-config definition.
    grouping port-security-mac-vlan-config {
        description
            "Port security configuration with MAC CVLAN or MAC SVLAN";
        leaf mac-address  {
            type  cml-data-types:cml_mac_addr_t {
                length "1..1965";
            }
            description "Use this attribute to configure the static forwarding entry for
                        port-security";
        } // END of mac-address definition.

        leaf-list cvlan-id  {
            when " /ipi-network-instance:network-instances/ipi-network-instance:network-instance/ipi-bridge:bridge/ipi-vlan:vlans/ipi-vlan:vlan/ipi-vlan:config/ipi-vlan:vlan-id and /ipi-network-instance:network-instances/ipi-network-instance:network-instance/ipi-bridge:bridge/ipi-vlan:vlans/ipi-vlan:vlan/ipi-vlan:customer-vlan/ipi-vlan:config/ipi-vlan:type ";
            type  uint16;
            description "Use this attribute to configure the port-security with static
                        forwarding entry and CVLAN ID";
        } // END of cvlan-id definition.

        leaf-list svlan-id  {
            when " /ipi-network-instance:network-instances/ipi-network-instance:network-instance/ipi-bridge:bridge/ipi-vlan:vlans/ipi-vlan:vlan/ipi-vlan:config/ipi-vlan:vlan-id and /ipi-network-instance:network-instances/ipi-network-instance:network-instance/ipi-bridge:bridge/ipi-vlan:vlans/ipi-vlan:vlan/ipi-vlan:service-vlan/ipi-vlan:config/ipi-vlan:type ";
            type  uint16;
            description "Use this attribute to configure the port-security with static
                        forwarding entry and SVLAN ID";
        } // END of svlan-id definition.

    } // END of port-security-mac-vlan-config definition.
    grouping port-security-mac-cvlan-svlan-config {
        description
            "Port security configuration with MAC CVLAN SVLAN";
        leaf mac-address  {
            type  cml-data-types:cml_mac_addr_t {
                length "1..1965";
            }
            description "Use this attribute to configure the static forwarding entry for
                        port-security";
        } // END of mac-address definition.

        leaf cvlan-id  {
            when " /ipi-network-instance:network-instances/ipi-network-instance:network-instance/ipi-bridge:bridge/ipi-vlan:vlans/ipi-vlan:vlan/ipi-vlan:config/ipi-vlan:vlan-id and /ipi-network-instance:network-instances/ipi-network-instance:network-instance/ipi-bridge:bridge/ipi-vlan:vlans/ipi-vlan:vlan/ipi-vlan:customer-vlan/ipi-vlan:config/ipi-vlan:type ";
            type  uint16;
            description "Use this attribute to configure the port-security with static
                        forwarding entry and CVLAN ID";
        } // END of cvlan-id definition.

        leaf svlan-id  {
            when " /ipi-network-instance:network-instances/ipi-network-instance:network-instance/ipi-bridge:bridge/ipi-vlan:vlans/ipi-vlan:vlan/ipi-vlan:config/ipi-vlan:vlan-id and /ipi-network-instance:network-instances/ipi-network-instance:network-instance/ipi-bridge:bridge/ipi-vlan:vlans/ipi-vlan:vlan/ipi-vlan:service-vlan/ipi-vlan:config/ipi-vlan:type ";
            type  uint16;
            description "Use this attribute to configure the port-security with static
                        forwarding entry and SVLAN ID";
        } // END of svlan-id definition.

    } // END of port-security-mac-cvlan-svlan-config definition.
    grouping port-security-mac-list-top {
        description
            "Top level grouping for port security objectlist for configuration of
                        static MAC with default vlan";
        container default-vlan-mappings {
            description
                "Enclosing container for list of Static MAC with default vlan";
            uses port-security-mac-list;
        } // END of default-vlan-mappings-container definition.
    } // END of port-security-mac-list-top definition.
    grouping port-security-mac-list {
        description
            "Port security objectlist for configuration of static MAC with default
                        vlan";

        list default-vlan-mapping {
            key "mac-address";
            description
                "List for Static MAC with default vlan";
            leaf mac-address  {
                type  leafref {
                    path  "../config/mac-address";
                }
                description "Use this attribute to configure the static forwarding entry for
                            port-security";
            } // END of mac-address definition.

            container config {
                description
                    "Configuration data for port-security with MAC and default vlan entries";
                uses port-security-mac-default-vlan-config;
            } // END of config-container definition.
            container state {
                config false;
                description
                    "Operational state data for port-security with MAC and default vlan
                            entries";
                uses port-security-mac-default-vlan-config;
            } // END of state-container definition.
        } // End of default-vlan-mapping-list
    } // END of port-security-mac-list definition.
    grouping port-security-mac-vlan-list-top {
        description
            "Top level grouping for port security objectlist for configuration of
                        static MAC with MAC-CVLAN or MAC-SVLAN entries";
        container vlan-mappings {
            description
                "Enclosing container for list of Static MAC with CVLAN or MAC with
                        SVLAN";
            uses port-security-mac-vlan-list;
        } // END of vlan-mappings-container definition.
    } // END of port-security-mac-vlan-list-top definition.
    grouping port-security-mac-vlan-list {
        description
            "Port security objectlist for configuration of static MAC with
                        MAC-CVLAN or MAC-SVLAN entries";

        list vlan-mapping {
            key "mac-address";
            description
                "List for Static MAC with CVLAN or MAC with SVLAN";
            leaf mac-address  {
                type  leafref {
                    path  "../config/mac-address";
                }
                description "Use this attribute to configure the static forwarding entry for
                            port-security";
            } // END of mac-address definition.

            container config {
                description
                    "Configuration data for port-security with MAC CVLAN or MAC SVLAN
                            entries";
                uses port-security-mac-vlan-config;
            } // END of config-container definition.
            container state {
                config false;
                description
                    "Operational state data for port-security with MAC or CVLAN or SVLAN
                            entries";
                uses port-security-mac-vlan-config;
            } // END of state-container definition.
        } // End of vlan-mapping-list
    } // END of port-security-mac-vlan-list definition.
    grouping port-security-mac-cvlan-svlan-list-top {
        description
            "Top level grouping for port security objectlist for configuration of
                        static MAC with MAC-CVLAN-SVLAN entries";
        container cvlan-svlan-mappings {
            description
                "Enclosing container for list of Static MAC with MAC-CVLAN-SVLAN
                        entries";
            uses port-security-mac-cvlan-svlan-list;
        } // END of cvlan-svlan-mappings-container definition.
    } // END of port-security-mac-cvlan-svlan-list-top definition.
    grouping port-security-mac-cvlan-svlan-list {
        description
            "Port security objectlist for configuration of static MAC with
                        MAC-CVLAN-SVLAN entries";

        list cvlan-svlan-mapping {
            key "mac-address cvlan-id svlan-id";
            description
                "List for Static MAC with MAC-CVLAN-SVLAN entries";
            leaf mac-address  {
                type  leafref {
                    path  "../config/mac-address";
                }
                description "Use this attribute to configure the static forwarding entry for
                            port-security";
            } // END of mac-address definition.

            leaf cvlan-id  {
                type  leafref {
                    path  "../config/cvlan-id";
                }
                description "Use this attribute to configure the port-security with static
                            forwarding entry and CVLAN ID";
            } // END of cvlan-id definition.

            leaf svlan-id  {
                type  leafref {
                    path  "../config/svlan-id";
                }
                description "Use this attribute to configure the port-security with static
                            forwarding entry and SVLAN ID";
            } // END of svlan-id definition.

            container config {
                description
                    "Configuration data for port-security with MAC CVLAN SVLAN entries";
                uses port-security-mac-cvlan-svlan-config;
            } // END of config-container definition.
            container state {
                config false;
                description
                    "Operational state data for port-security with MAC CVLAN SVLAN entries";
                uses port-security-mac-cvlan-svlan-config;
            } // END of state-container definition.
        } // End of cvlan-svlan-mapping-list
    } // END of port-security-mac-cvlan-svlan-list definition.
    grouping port-security-mac-top {
        description
            "Top level grouping for port MAC security data";
        container secure-mac {
            when " /ipi-interface:interfaces/ipi-interface:interface/ipi-port-vlan:port-vlan/ipi-port-vlan:port-security/ipi-port-vlan:config/ipi-port-vlan:mode ";
            if-feature feature-list:HAVE_PROVIDER_BRIDGE;
            description
                "Configure data for static MAC entries";
            uses port-security-mac-list-top;
            uses port-security-mac-vlan-list-top;
            uses port-security-mac-cvlan-svlan-list-top;
        } // END of secure-mac-container definition.
    } // END of port-security-mac-top definition.
    grouping port-security-config {
        description
            "Port security common configuration data";
        leaf mode  {
            type  ipi-port-vlan-types:port_vlan_port_sec_mode_t;
            mandatory true;
            description "port security mode type";
        } // END of mode definition.

        leaf maximum-limit  {
            type  uint16 {
                 range "1..1000"  {
                    description "1..1000: Supported range 1 - 1000";
                 }
            }
            default "1";
            description "Maximum limit for port security";
        } // END of maximum-limit definition.

        leaf logging  {
            type  empty;
            description "port security logging";
        } // END of logging definition.

    } // END of port-security-config definition.
    grouping port-security-top {
        description
            "Top level grouping for port security";
        container port-security {
            when " /ipi-interface:interfaces/ipi-interface:interface/ipi-interface:config/ipi-interface:enable-switchport ";
            // when " ipi-port-vlan:port-vlan/port-security/config/mode + not(/ipi-vlan:layer2-global/ipi-vlan:config/ipi-vlan:disable-port-security) ";
            description
                "Configuration and state data for port security";
            container config {
                presence "Configure port security mode";
                description
                    "Configuration data for port security";
                uses port-security-config;
            } // END of config-container definition.
            container state {
                config false;
                description
                    "Operational state data for port-security";
                uses port-security-config;
            } // END of state-container definition.
            uses port-security-mac-top;
        } // END of port-security-container definition.
    } // END of port-security-top definition.
    grouping allowed-vlan-config {
        description
            "Configuration data for port allowed VLAN";
        leaf allowed-vlan-id  {
            type  cml-data-types:cml_range_t;
            description "Use this attribute to create a single/range of VLANs on the VLAN aware
                        bridges";
        } // END of allowed-vlan-id definition.

        leaf egress-tagging-disabled-vlans  {
            when " /ipi-interface:interfaces/ipi-interface:interface/ipi-port-vlan:port-vlan/ipi-port-vlan:switched-vlans/ipi-port-vlan:switched-vlan/ipi-port-vlan:config/ipi-port-vlan:interface-mode = 'hybrid' or /ipi-interface:interfaces/ipi-interface:interface/ipi-port-vlan:port-vlan/ipi-port-vlan:switched-vlans/ipi-port-vlan:switched-vlan/ipi-port-vlan:config/ipi-port-vlan:interface-mode = 'customer-edge-hybrid' ";
            type  cml-data-types:cml_range_t;
            description "Egress tagging per VLAN";
        } // END of egress-tagging-disabled-vlans definition.

    } // END of allowed-vlan-config definition.
    grouping allowed-vlan-top {
        description
            "Top level grouping for port allowed VLANs";
        container allowed-vlan {
            when " /ipi-interface:interfaces/ipi-interface:interface/ipi-interface:config/ipi-interface:enable-switchport ";
            description
                "Configuration and state data for allowed VLANs";
            container config {
                description
                    "Configuration data for port allowed VLANs";
                uses allowed-vlan-config;
            } // END of config-container definition.
            container state {
                config false;
                description
                    "Operational state data";
                uses allowed-vlan-config;
            } // END of state-container definition.
        } // END of allowed-vlan-container definition.
    } // END of allowed-vlan-top definition.
    grouping translation-qos-config {
        description
            "Grouping for CVLAN translation QoSconfiguration";
        leaf svlan-cos  {
            if-feature feature-list:NOT_HAVE_DUNE;
            if-feature feature-list:NOT_HAVE_POND;
            type  uint8 {
                 range "0..7"  {
                    description "0..7: Supported range 0 - 7";
                 }
            }
            description "Service VLAN class of service value";
        } // END of svlan-cos definition.

        leaf svlan-cfi  {
            if-feature feature-list:NOT_HAVE_DUNE;
            if-feature feature-list:NOT_HAVE_POND;
            type  uint8 {
                 range "0..1"  {
                    description "0..1: Supported range 0 - 1";
                 }
            }
            description "Service VLAN Canonical Format Indicator value";
        } // END of svlan-cfi definition.

        leaf cvlan-cos  {
            if-feature feature-list:NOT_HAVE_DUNE;
            if-feature feature-list:NOT_HAVE_POND;
            type  uint8 {
                 range "0..7"  {
                    description "0..7: Supported range 0 - 7";
                 }
            }
            description "Customer VLAN class of service value";
        } // END of cvlan-cos definition.

        leaf cvlan-cfi  {
            if-feature feature-list:NOT_HAVE_DUNE;
            if-feature feature-list:NOT_HAVE_POND;
            type  uint8 {
                 range "0..1"  {
                    description "0..1: Supported range 0 - 1";
                 }
            }
            description "Customer VLAN Canonical Format Indicator value";
        } // END of cvlan-cfi definition.

    } // END of translation-qos-config definition.
    grouping cvlan-svlan-translation-config {
        description
            "Grouping for CVLAN translation configuration";
        leaf cvlan-id  {
            type  uint16 {
                 range "1..4095"  {
                    description "1..4095:Feature : HAVE_4K_VLAN Supported range 1 - 4095Not Feature :
                            HAVE_4K_VLAN  Supported range 1 - 4094";
                 }
            }
            description "Specifies customer VLAN identifier";
        } // END of cvlan-id definition.

        leaf svlan-id  {
            type  uint16 {
                 range "1..4095"  {
                    description "1..4095:Feature : HAVE_4K_VLAN Supported range 1 - 4095Not Feature :
                            HAVE_4K_VLAN  Supported range 1 - 4094";
                 }
            }
            description "Specifies service VLAN identifier";
        } // END of svlan-id definition.

        leaf translated-cvlan-id  {
            type  uint16 {
                 range "1..4095"  {
                    description "1..4095:Feature : HAVE_4K_VLAN Supported range 1 - 4095Not Feature :
                            HAVE_4K_VLAN  Supported range 1 - 4094";
                 }
            }
            description "Specifies translated customer VLAN identifier";
        } // END of translated-cvlan-id definition.

        leaf translated-svlan-id  {
            type  uint16 {
                 range "1..4095"  {
                    description "1..4095:Feature : HAVE_4K_VLAN Supported range 1 - 4095Not Feature :
                            HAVE_4K_VLAN  Supported range 1 - 4094";
                 }
            }
            mandatory true;
            description "Specifies translated service VLAN identifier";
        } // END of translated-svlan-id definition.

    } // END of cvlan-svlan-translation-config definition.
    grouping cvlan-svlan-translation-top {
        description
            "Top level grouping for CVLAN-SVLAN translation";
        container cvlan-svlan-translations {
            description
                "Enclosing container for the list of data for CVLAN-SVLAN translation";

            list cvlan-svlan-translation {
                if-feature feature-list:HAVE_PROVIDER_BRIDGE;
                key "cvlan-id svlan-id";
                description
                    "List for CVLAN-SVLAN translation entries";
                leaf cvlan-id  {
                    type  leafref {
                        path  "../config/cvlan-id";
                    }
                    description "Specifies to be translated customer vlan identifier";
                } // END of cvlan-id definition.

                leaf svlan-id  {
                    type  leafref {
                        path  "../config/svlan-id";
                    }
                    description "Specifies to be translated service VLAN identifier";
                } // END of svlan-id definition.

                container config {
                    description
                        "Configuration data for CVLAN-SVLAN translation";
                    uses cvlan-svlan-translation-config;
                    uses translation-qos-config;
                } // END of config-container definition.
                container state {
                    config false;
                    description
                        "Operational state data for CVLAN-SVLAN translation";
                    uses cvlan-svlan-translation-config;
                    uses translation-qos-config;
                } // END of state-container definition.
            } // End of cvlan-svlan-translation-list
        } // END of cvlan-svlan-translations-container definition.
    } // END of cvlan-svlan-translation-top definition.
    grouping svlan-translation-config {
        description
            "Grouping for SVLAN translation configuration data";
        leaf translated-svlan-id  {
            type  uint16;
            description "Specifies translated service VLAN identifier";
        } // END of translated-svlan-id definition.

        leaf original-svlan-id  {
            type  uint16;
            description "Original SVLAN ID";
        } // END of original-svlan-id definition.

        leaf translated-cvlan-id  {
            type  uint16 {
                 range "1..4095"  {
                    description "1..4095:Feature : HAVE_4K_VLAN Supported range 1 - 4095Not Feature :
                            HAVE_4K_VLAN  Supported range 1 - 4094";
                 }
            }
            description "Specifies translated customer VLAN identifier";
        } // END of translated-cvlan-id definition.

    } // END of svlan-translation-config definition.
    grouping svlan-translation-top {
        description
            "Top level grouping for SVLAN translation data";
        container svlan-translations {
            description
                "Enclosing container for the list of data for SVLAN translation";

            list svlan-translation {
                if-feature feature-list:HAVE_PROVIDER_BRIDGE;
                key "original-svlan-id";
                description
                    "List for SVLAN translation entries";
                leaf original-svlan-id  {
                    type  leafref {
                        path  "../config/original-svlan-id";
                    }
                    description "Original SVLAN ID";
                } // END of original-svlan-id definition.

                container config {
                    description
                        "Configuration data for SVLAN translation";
                    uses svlan-translation-config;
                    uses translation-qos-config;
                } // END of config-container definition.
                container state {
                    config false;
                    description
                        "Operational state data for SVLAN translation";
                    uses svlan-translation-config;
                    uses translation-qos-config;
                } // END of state-container definition.
            } // End of svlan-translation-list
        } // END of svlan-translations-container definition.
    } // END of svlan-translation-top definition.
    grouping ce-vlan-translation-config {
        description
            "Grouping for customer edge VLAN translation configuration";
        leaf original-vlan-id  {
            when " /ipi-network-instance:network-instances/ipi-network-instance:network-instance/ipi-bridge:bridge/ipi-vlan:vlans/ipi-vlan:vlan/ipi-vlan:config/ipi-vlan:vlan-id and /ipi-network-instance:network-instances/ipi-network-instance:network-instance/ipi-bridge:bridge/ipi-vlan:vlans/ipi-vlan:vlan/ipi-vlan:customer-vlan/ipi-vlan:config/ipi-vlan:type ";
            type  uint16;
            description "Specifies the customer VLAN to be translated";
        } // END of original-vlan-id definition.

        leaf translated-vlan-id  {
            when " /ipi-network-instance:network-instances/ipi-network-instance:network-instance/ipi-bridge:bridge/ipi-vlan:vlans/ipi-vlan:vlan/ipi-vlan:config/ipi-vlan:vlan-id and /ipi-network-instance:network-instances/ipi-network-instance:network-instance/ipi-bridge:bridge/ipi-vlan:vlans/ipi-vlan:vlan/ipi-vlan:customer-vlan/ipi-vlan:config/ipi-vlan:type ";
            type  uint16;
            mandatory true;
            description "Specifies the new customer VLAN for translate";
        } // END of translated-vlan-id definition.

    } // END of ce-vlan-translation-config definition.
    grouping ce-vlan-translation-top {
        description
            "Top level grouping for customer edge VLAN translation data";
        container ce-vlan-translations {
            description
                "Enclosing container for the list of data for customer edge VLAN
                        translation";
        } // END of ce-vlan-translations-container definition.
    } // END of ce-vlan-translation-top definition.
    grouping default-vlan-config {
        description
            "Grouping for port switched VLAN configuration data";
        leaf vlan-id  {
            when " /ipi-interface:interfaces/ipi-interface:interface/ipi-port-vlan:port-vlan/ipi-port-vlan:switched-vlans/ipi-port-vlan:switched-vlan/ipi-port-vlan:interface-mode = 'access' or /ipi-interface:interfaces/ipi-interface:interface/ipi-port-vlan:port-vlan/ipi-port-vlan:switched-vlans/ipi-port-vlan:switched-vlan/ipi-port-vlan:interface-mode = 'hybrid' or /ipi-interface:interfaces/ipi-interface:interface/ipi-port-vlan:port-vlan/ipi-port-vlan:switched-vlans/ipi-port-vlan:switched-vlan/ipi-port-vlan:interface-mode = 'customer-network' or /ipi-interface:interfaces/ipi-interface:interface/ipi-port-vlan:port-vlan/ipi-port-vlan:switched-vlans/ipi-port-vlan:switched-vlan/ipi-port-vlan:interface-mode = 'customer-edge-access' or /ipi-interface:interfaces/ipi-interface:interface/ipi-port-vlan:port-vlan/ipi-port-vlan:switched-vlans/ipi-port-vlan:switched-vlan/ipi-port-vlan:interface-mode = 'customer-edge-hybrid' ";
            type  uint16 {
                 range "2..4094"  {
                    description "2..4094: Supported range 2 - 4094";
                 }
            }
            description "Default VLAN identifier";
        } // END of vlan-id definition.

        leaf native-vlan-id  {
            when " /ipi-interface:interfaces/ipi-interface:interface/ipi-port-vlan:port-vlan/ipi-port-vlan:switched-vlans/ipi-port-vlan:switched-vlan/ipi-port-vlan:interface-mode = 'trunk' ";
            // when " !ipi-port-vlan:port-vlan/switched-vlans/switched-vlan/config/disable-native-vlan ";
            type  uint16 {
                 range "2..4094"  {
                    description "2..4094: Supported range 2 - 4094";
                 }
            }
            description "Native VLAN ID";
        } // END of native-vlan-id definition.

        leaf svlan-id  {
            // when " ipi-vlan:vlans/vlan/config/vlan-id + ipi-vlan:vlans/vlan/service-vlan/config/type ";
            if-feature feature-list:HAVE_PROVIDER_BRIDGE;
            if-feature feature-list:HAVE_SWFWDR;
            type  uint16;
            description "Default service VLAN ID";
        } // END of svlan-id definition.

    } // END of default-vlan-config definition.
    grouping vlans-top {
        description
            "Top level grouping for port VLANs";
        container vlans {
            description
                "Configuration and state data for port VLANs";
            container config {
                description
                    "Configuration data for port VLANs";
                uses default-vlan-config;
            } // END of config-container definition.
            container state {
                config false;
                description
                    "Operational state data for port VLANs";
                uses default-vlan-config;
            } // END of state-container definition.
        } // END of vlans-container definition.
    } // END of vlans-top definition.
    grouping switched-vlan-config {
        description
            "Grouping for port switched VLAN configuration data";
        leaf interface-mode  {
            type  ipi-port-vlan-types:port_vlan_switch_port_mode_t;
            description "Set the interface to access or trunk or hybrid mode for VLANs";
        } // END of interface-mode definition.

        leaf ingress-filter  {
            if-feature feature-list:NOT_HAVE_DUNE;
            type  cml-data-types:cml_enable_disable_t;
            description "Use this attribute to set the switching characteristics of the
                        interface as hybrid, and classify both tagged and untagged frames.
                        Received frames are classified based on the VLAN characteristics, then
                        accepted or discarded based on the specified filtering criteria.";
        } // END of ingress-filter definition.

        leaf acceptable-frame-type  {
            type  ipi-port-vlan-types:port_vlan_frame_type_t;
            description "Use this attribute to set the interface acceptable frame types. This
                        processing occurs after VLAN classification";
        } // END of acceptable-frame-type definition.

        leaf disable-native-vlan  {
            // when " not(../remove-default-vlan) ";
            type  empty;
            description "Use this attribute to disable native VLAN for the port. Untagged
                        frames will be dropped.";
        } // END of disable-native-vlan definition.

        leaf remove-default-vlan  {
            // when " not(../disable-native-vlan) ";
            type  empty;
            description "Use this attribute to remove default VLAN for the port. Untagged
                        frames will be dropped.";
        } // END of remove-default-vlan definition.

    } // END of switched-vlan-config definition.
    grouping switched-vlan-top {
        description
            "Top-level grouping for VLAN data associated with an interface";
        container switched-vlans {
            description
                "Enclosing container for VLAN related configuration that is part of
                        interface";
            uses switched-vlan-list;
        } // END of switched-vlans-container definition.
    } // END of switched-vlan-top definition.
    grouping switched-vlan-list {
        description
            "Grouping for VLAN data associated with an interface";

        list switched-vlan {
        when " /ipi-interface:interfaces/ipi-interface:interface/ipi-interface:config/ipi-interface:enable-switchport ";
            key "interface-mode";
            description
                "VLAN related configuration that is part of interface";
            leaf interface-mode  {
                type  leafref {
                    path  "../config/interface-mode";
                }
                description "Set the interface to access or trunk or hybrid mode for VLANs";
            } // END of interface-mode definition.

            container config {
                description
                    "Configuration data for port switched VLAN";
                uses switched-vlan-config;
            } // END of config-container definition.
            container state {
                config false;
                description
                    "Operational state data for port switched VLANs";
                uses switched-vlan-config;
            } // END of state-container definition.
            uses vlans-top;
            uses allowed-vlan-top;
            uses ce-vlan-translation-top;
            uses svlan-translation-top;
            uses cvlan-svlan-translation-top;
        } // End of switched-vlan-list
    } // END of switched-vlan-list definition.
    grouping uni-id-config {
        description
            "Grouping for uni ID configuration";
        leaf uni-id  {
            type  string {
                length "1..1965";
                pattern "[^?' =,>|]+";
            }
            description "Use this attribute to set UNI Name";
        } // END of uni-id definition.

    } // END of uni-id-config definition.
    grouping enni-id-config {
        description
            "Grouping for ENNI ID configuration";
        leaf enni-id  {
            type  string {
                length "1..1965";
                pattern "[^?' =,>|]+";
            }
            description "Use this attribute to set ENNI Name";
        } // END of enni-id definition.

    } // END of enni-id-config definition.
    grouping uni-enni-type-config {
        description
            "Grouping for UNI/ENNI type configuration";
        leaf type  {
            type  ipi-port-vlan-types:port_vlan_uni_enni_type_t;
            mandatory true;
            description "Use this attribute to set UNI/ENNI type";
        } // END of type definition.

    } // END of uni-enni-type-config definition.
    grouping uni-enni-evc-config {
        description
            "Grouping for EVC configuration";
        leaf evc-id  {
            type  string {
                length "1..1965";
                pattern "[^?' =,>|]+";
            }
            description "Use this attribute to set Ethernet Virtual Connection identifier";
        } // END of evc-id definition.

    } // END of uni-enni-evc-config definition.
    grouping uni-enni-evc-top {
        description
            "Top level grouping for port UNI/ENNI configuration";
        container evcs {
            description
                "Enclosing container for list of EVC entries";
            uses uni-enni-evc-list;
        } // END of evcs-container definition.
    } // END of uni-enni-evc-top definition.
    grouping uni-enni-evc-list {
        description
            "Grouping for port UNI/ENNI configuration";
    } // END of uni-enni-evc-list definition.
    grouping uni-enni-svlan-config {
        description
            "Grouping for UNI/ENNI svlan configuration data";
        leaf svlan-id  {
            type  uint16;
            description "Use this attribute to set service VLAN identifier";
        } // END of svlan-id definition.

    } // END of uni-enni-svlan-config definition.
    grouping uni-enni-svlan-top {
        description
            "Top level grouping for UNI/ENNI svlan data";
        container svlans {
            description
                "Enclosing container for list of svlan entries";
            uses uni-enni-svlan-list;
        } // END of svlans-container definition.
    } // END of uni-enni-svlan-top definition.
    grouping uni-enni-svlan-list {
        description
            "Grouping for UNI/ENNI svlan data";
    } // END of uni-enni-svlan-list definition.
    grouping port-vlan-enni-top {
        description
            "Top level grouping for port ENNI data";
        container ennis {
            description
                "Enclosing container for list of port ENNI entries";
            uses port-vlan-enni-list;
        } // END of ennis-container definition.
    } // END of port-vlan-enni-top definition.
    grouping port-vlan-enni-list {
        description
            "Grouping for port ENNI data";
    } // END of port-vlan-enni-list definition.
    grouping uni-config {
        description
            "Grouping for UNI service data";
        leaf service  {
            when " /ipi-interface:interfaces/ipi-interface:interface/ipi-interface:config/ipi-interface:enable-switchport ";
            type  ipi-port-vlan-types:port_vlan_uni_service_t;
            description "Use this attribute to set UNI service";
        } // END of service definition.

        leaf evc-maximum-number  {
            when " /ipi-interface:interfaces/ipi-interface:interface/ipi-interface:config/ipi-interface:enable-switchport ";
            type  uint32 {
                 range "1..4094"  {
                    description "1..4094: Supported range 1 - 4094";
                 }
            }
            description "Use this attribute to set maximum number of EVCs for the UNI";
        } // END of evc-maximum-number definition.

    } // END of uni-config definition.
    grouping uni-bridge-config {
        description
            "Grouping for bridge UNI data";
        leaf instance-name  {
            type  leafref {
                path  "/ipi-network-instance:network-instances/ipi-network-instance:network-instance/ipi-network-instance:instance-name";
            }
            description "Bridge group number";
        } // END of instance-name definition.

        leaf type-mode  {
            when " /ipi-interface:interfaces/ipi-interface:interface/ipi-interface:config/ipi-interface:enable-switchport ";
            if-feature feature-list:HAVE_SWFWDR;
            type  ipi-port-vlan-types:port_vlan_uni_enable_disable_t;
            mandatory true;
            description "Use this attribute to enable or disable UNI type";
        } // END of type-mode definition.

    } // END of uni-bridge-config definition.
    grouping uni-bridge-top {
        description
            "Top level grouping for bridge UNI data";
        container bridges {
            description
                "Enclosing container for list of UNI bridge entries";
            uses uni-bridge-list;
        } // END of bridges-container definition.
    } // END of uni-bridge-top definition.
    grouping uni-bridge-list {
        description
            "Grouping for bridge UNI data";

        list bridge {
            if-feature feature-list:HAVE_PROVIDER_BRIDGE;
            if-feature feature-list:HAVE_SWFWDR;
            key "instance-name";
            max-elements 1;
            description
                "List for UNI bridge entries";
            leaf instance-name  {
                type  leafref {
                    path  "../config/instance-name";
                }
                description "Bridge group number";
            } // END of instance-name definition.

            container config {
                description
                    "Configuration data for UNI bridge";
                uses uni-bridge-config;
            } // END of config-container definition.
            container state {
                config false;
                description
                    "Operational state data";
                uses uni-bridge-config;
            } // END of state-container definition.
        } // End of bridge-list
    } // END of uni-bridge-list definition.
    grouping uni-enni-parameters-top {
        description
            "Top level grouping for UNI/ENNI common parameters";
        container parameters {
            description
                "Enclosing container for list of UNI/ENNI common parameters";
            uses uni-enni-parameters-list;
        } // END of parameters-container definition.
    } // END of uni-enni-parameters-top definition.
    grouping uni-enni-parameters-list {
        description
            "Grouping for UNI/ENNI common parameters";
    } // END of uni-enni-parameters-list definition.
    grouping port-vlan-uni-top {
        description
            "Top level grouping for port UNI data";
    } // END of port-vlan-uni-top definition.
    grouping vlan-stacking-config {
        description
            "Grouping for vlan stacking data";
        leaf type  {
            type  ipi-port-vlan-types:port_vlan_stack_t;
            mandatory true;
            description "Attribute to select vlan stacking port type";
        } // END of type definition.

        leaf ether-type  {
            type  string {
                length "0..1965";
                pattern "[^?' =,>|]*";
            }
            default "";
            description "Attribute to select ether type for vlan tagging";
        } // END of ether-type definition.

    } // END of vlan-stacking-config definition.
    grouping port-vlan-stacking-top {
        description
            "Top level grouping for port vlan stacking";
    } // END of port-vlan-stacking-top definition.
    grouping port-vlan-global-config {
        description
            "Grouping for port vlan global configuration";
        leaf isolated-vlan-id  {
            when " /ipi-interface:interfaces/ipi-interface:interface/ipi-port-vlan:port-vlan/ipi-port-vlan:switched-vlans/ipi-port-vlan:switched-vlan/ipi-port-vlan:config/ipi-port-vlan:interface-mode = 'provider-network' ";
            if-feature feature-list:NOT_HAVE_SWFWDR;
            type  cml-data-types:cml_range_t;
            description "Isolated VLAN identifier";
        } // END of isolated-vlan-id definition.

        leaf cvlan-registration-table  {
            if-feature feature-list:HAVE_PROVIDER_BRIDGE;
            type  leafref {
                path  "/ipi-network-instance:network-instances/ipi-network-instance:network-instance/ipi-bridge:bridge/ipi-vlan:cvlan-registration-tables/ipi-vlan:cvlan-registration-table/ipi-vlan:config/ipi-vlan:table-name";
            }
            description "cvlan registration table";
        } // END of cvlan-registration-table definition.

    } // END of port-vlan-global-config definition.
    grouping port-vlan-global-top {
        description
            "Top level grouping for port VLAN global level information";
        container global {
            description
                "Port VLAN global level configuration and state data";
            container config {
                description
                    "Global level configuration data for port VLAN";
                uses port-vlan-global-config;
            } // END of config-container definition.
            container state {
                config false;
                description
                    "Operational state data";
                uses port-vlan-global-config;
            } // END of state-container definition.
            uses port-vlan-stacking-top;
        } // END of global-container definition.
    } // END of port-vlan-global-top definition.
    grouping mac-table-config {
        description
            "Grouping for VLAN static FDB data";
        leaf interface-name  {
            // when " !ipi-port-vlan:port-vlan/port-security/config/mode ";
            type  leafref {
                path  "/ipi-interface:interfaces/ipi-interface:interface/ipi-interface:name";
            }
            mandatory true;
            description "The textual name of the interface";
        } // END of interface-name definition.

        leaf mac-address  {
            type  cml-data-types:cml_mac_addr_t {
                length "1..1965";
            }
            description "Use this attribute to configure the static forwarding table entry for
                        the bridge";
        } // END of mac-address definition.

        leaf action  {
            type  ipi-port-vlan-types:port_vlan_l2_fdb_action_t;
            mandatory true;
            description "Specifies to forward or discard packets for particular static MAC
                        entry";
        } // END of action definition.

        leaf vlan-id  {
            type  uint16 {
                 range "2..4094"  {
                    description "2..4094: Supported range 2 - 4094";
                 }
            }
            description "Specifies VLAN identifier for static MAC entry in case of
                        provider-network VLAN will be considered as service VLAN";
        } // END of vlan-id definition.

        leaf svlan-id  {
            when " /ipi-network-instance:network-instances/ipi-network-instance:network-instance/ipi-bridge:bridge/ipi-vlan:vlans/ipi-vlan:vlan/ipi-vlan:service-vlan/ipi-vlan:config/ipi-vlan:type ";
            if-feature feature-list:HAVE_PB_STATIC_FDB_CUSTOM_CONFIG;
            type  uint16 {
                 range "2..4094"  {
                    description "2..4094: Supported range 2 - 4094";
                 }
            }
            description "Specifies service VLAN identifier for static MAC entry";
        } // END of svlan-id definition.

    } // END of mac-table-config definition.
    grouping mac-table-top {
        description
            "Top level grouping for VLAN static MAC table information";
        container entries {
            description
                "Enclosing container for list of VLAN static FDB MAC table
                        configuration and state data";
            uses mac-table-list;
        } // END of entries-container definition.
    } // END of mac-table-top definition.
    grouping mac-table-list {
        description
            "Grouping for VLAN static MAC table information";

        list entry {
            key "mac-address vlan-id";
            description
                "List of VLAN static FDB MAC table configuration and state data";
            leaf mac-address  {
                type  leafref {
                    path  "../config/mac-address";
                }
                description "Use this attribute to configure the static forwarding table entry for
                            the bridge";
            } // END of mac-address definition.

            leaf vlan-id  {
                type  leafref {
                    path  "../config/vlan-id";
                }
                description "Specifies VLAN identifier for static MAC entry in case of
                            provider-network VLAN will be considered as service VLAN";
            } // END of vlan-id definition.

            container config {
                description
                    "Configuration data for VLAN FDB";
                uses mac-table-config;
            } // END of config-container definition.
            container state {
                config false;
                description
                    "Operational state data";
                uses mac-table-config;
            } // END of state-container definition.
        } // End of entry-list
    } // END of mac-table-list definition.

    grouping  port-vlan-grouping {
    description
        "Top level container for port level VLAN configuration and state data";
    container port-vlan {
        if-feature feature-list:HAVE_L2;
        description
            "Top level container for port level VLAN configuration and state data";
        uses port-vlan-global-top;
        uses port-vlan-uni-top;
        uses port-vlan-enni-top;
        uses switched-vlan-top;
        uses port-security-top;
        uses port-private-vlan-top;
        uses oep-mapping-top;
    } // END of port-vlan-container definition.
    } // END of port-vlan-grouping definition.

    grouping  vlan-static-fdb-grouping {
    description
        "Top level container for VLAN static FDB configuration and state data";
    container vlan-static-fdb {
        if-feature feature-list:HAVE_L2;
        description
            "Top level container for VLAN static FDB configuration and state data";
        uses mac-table-top;
    } // END of vlan-static-fdb-container definition.
    } // END of vlan-static-fdb-grouping definition.

    augment /ipi-interface:interfaces/ipi-interface:interface {
    when " /ipi-interface:interfaces/ipi-interface:interface/ipi-interface:config/ipi-interface:enable-switchport ";
    // when " not(/ipi-interface:interfaces/ipi-interface:interface/ipi-if-aggregate:member-aggregation/ipi-if-aggregate:config) ";
        description
            "Top level container for port level VLAN configuration and state data";
        uses port-vlan-grouping;
    }

    augment /ipi-network-instance:network-instances/ipi-network-instance:network-instance/ipi-bridge:bridge {
        if-feature feature-list:HAVE_L2;
        description
            "Top level container for VLAN static FDB configuration and state data";
        uses vlan-static-fdb-grouping;
    }


}
