/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-service-map-types.yang
*
*/

module ipi-service-map-types {

    yang-version 1.1;

    namespace   "http://www.ipinfusion.com/yang/ocnos/ipi-service-map-types";

    prefix "ipi-service-map-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Service Map data types";


    revision "2022-06-01" {
        description "Updated the yang file with feature";
        reference " 0.2.0.";
    }

    revision "2022-03-21" {
        description "Initial Version";
        reference " 0.1.0.";
    }



    typedef  tunnel_selection_mode_t {
        type enumeration {
            enum dedicated {
                value 1;
                description "Dedicated tunnel selection mode(Default)";
            }
            enum best-effort {
                value 2;
                description "Best effort tunnel selection mode";
            }
        }
        description "type definition for TUNNEL_SELECTION_MODE_T";
    }

    typedef  tunnel_selection_type_t {
        type enumeration {
            enum rsvp {
                value 1;
                if-feature feature-list:HAVE_MPLS;
                description "Tunnel type RSVP";
            }
            enum sr-mpls {
                value 2;
                if-feature feature-list:HAVE_SR_MPLS;
                description "Tunnel type SR-MPLS";
            }
            enum srv6 {
                value 3;
                if-feature feature-list:HAVE_SRV6;
                description "Tunnel type SRv6";
            }
        }
        description "type definition for TUNNEL_SELECTION_TYPE_T";
    }

}
