/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-seamless-bfd.yang
*
*/

module ipi-seamless-bfd {

    yang-version 1.1;

    namespace   "http://www.ipinfusion.com/yang/ocnos/ipi-seamless-bfd";

    prefix "ipi-seamless-bfd";

    import ipi-sbfd-types {
        prefix ipi-sbfd-types;
        revision-date 2022-06-01;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Seamless BFD";


    revision "2024-04-05" {
        description "Added CML_RESET_INSTANCE for minimun-tx and detection-multiplier";
        reference " 0.5.0.";
    }

    revision "2023-02-27" {
        description "Added implicit-delete for attribute container";
        reference " 0.4.0.";
    }

    revision "2022-11-28" {
        description "Added enclosing container for all objectlists";
        reference " 0.3.0.";
    }

    revision "2022-07-04" {
        description "Changed default value for detection-multiplier";
        reference " 0.2.2.";
    }

    revision "2022-06-24" {
        description "Changed local discriminator to objectlist";
        reference " 0.2.1.";
    }

    revision "2022-06-01" {
        description "Updated the yang file with feature";
        reference " 0.2.0.";
    }

    revision "2022-03-23" {
        description "Initial Version";
        reference " 0.1.0.";
    }

    grouping sbfd-attributes-config {
        description
            "SBFD Attribute";
        leaf admin-down  {
            type  empty;
            description "This attribute is used to shutdown selected S-BFD session";
        } // END of admin-down definition.

    } // END of sbfd-attributes-config definition.
    grouping sbfd-local-discriminator-top {
        description
            "SBFD discriminator Attributes";
        container local-discriminators {
            description
                "local discriminators values for the S-BFD session";

            list local-discriminator {
                key "discriminator";
                max-elements 1;
                description
                    "local discriminator values for the S-BFD session";
                leaf discriminator  {
                    type  leafref {
                        path  "../config/discriminator";
                    }
                    description "This attribute is used to configure local discriminator value for
                                reflector";
                } // END of discriminator definition.

                container config {
                    description
                        "Configuration container for S-BFD discriminator";
                    uses sbfd-local-discriminator-config;
                } // END of config-container definition.
                container state {
                    config false;
                    description
                        "Operational container for S-BFD discriminator";
                    uses sbfd-local-discriminator-config;
                } // END of state-container definition.
            } // End of local-discriminator-list
        } // END of local-discriminators-container definition.
    } // END of sbfd-local-discriminator-top definition.
    grouping sbfd-interval-attributes-top {
        description
            "SBFD interval Attributes";
        container intervals {
            description
                "Intervals values for the S-BFD sessions";

            list interval {
                key "minimum-tx detection-multiplier";
                max-elements 1;
                description
                    "Intervals values for the S-BFD sessions";
                leaf minimum-tx  {
                    type  leafref {
                        path  "../config/minimum-tx";
                    }
                    description "This attribute holds minimum transmission interval value";
                } // END of minimum-tx definition.

                leaf detection-multiplier  {
                    type  leafref {
                        path  "../config/detection-multiplier";
                    }
                    description "This attribute is multiplied with minimum tx value to get detection
                                time";
                } // END of detection-multiplier definition.

                container config {
                    description
                        "Configuration container for S-BFD intervals";
                    uses sbfd-interval-attributes-config;
                } // END of config-container definition.
                container state {
                    config false;
                    description
                        "Operational container for S-BFD intervals";
                    uses sbfd-interval-attributes-config;
                } // END of state-container definition.
            } // End of interval-list
        } // END of intervals-container definition.
    } // END of sbfd-interval-attributes-top definition.
    grouping sbfd-interval-attributes-config {
        description
            "S-BFD interval Attributes";
        leaf minimum-tx  {
            type  uint32 {
                 range "3..4294967"  {
                    description "3..4294967: Supported range 3 - 4294967";
                 }
            }
            description "This attribute holds minimum transmission interval value";
        } // END of minimum-tx definition.

        leaf detection-multiplier  {
            type  uint8 {
                 range "1..255"  {
                    description "1..255: Supported range 1 - 255";
                 }
            }
            description "This attribute is multiplied with minimum tx value to get detection
                        time";
        } // END of detection-multiplier definition.

    } // END of sbfd-interval-attributes-config definition.
    grouping sbfd-sr-policy-config {
        description
            "SR S-BFD Configs";
        leaf lsp-type  {
            type  ipi-sbfd-types:sbfd_sr_type_t;
            description "This attribute is used to configure lsp type of the SR SBFD session";
        } // END of lsp-type definition.

        leaf sr-policy-name  {
            type  string {
                length "1..32";
                pattern "[^?' =,>|]+";
            }
            description "This attribute is used to configure policy name of the SR S-BFD
                        session";
        } // END of sr-policy-name definition.

    } // END of sbfd-sr-policy-config definition.
    grouping sbfd-local-discriminator-config {
        description
            "Local discriminator Configs";
        leaf discriminator  {
            type  string {
                length "1..1965";
                pattern "[^?' =,>|]+";
            }
            description "This attribute is used to configure local discriminator value for
                        reflector";
        } // END of discriminator definition.

        leaf required-min-rx-interval  {
            type  uint32 {
                 range "3..999"  {
                    description "3..999: Supported range 3 - 999";
                 }
            }
            description "This attribute is used to configure required minimum rx interval value
                        for reflector";
        } // END of required-min-rx-interval definition.

    } // END of sbfd-local-discriminator-config definition.
    grouping sbfd-discriminators-state {
        description
            "sbfd learnt discriminators";
        leaf-list remote-discriminator  {
            type  string {
                length "1..1965";
                pattern "[^?' =,>|]+";
            }
            config false;
            description "";
        } // END of remote-discriminator definition.

    } // END of sbfd-discriminators-state definition.
    grouping sbfd-sr-policies-top {
        description
            "SR policies Configs";
        container sr-policies {
            description
                "SR S-BFD policy configurations";

            list sr-policy {
                key "lsp-type sr-policy-name";
                description
                    "SR S-BFD policy configurations";
                leaf lsp-type  {
                    type  leafref {
                        path  "../config/lsp-type";
                    }
                    description "This attribute is used to configure lsp type of the SR S-BFD session";
                } // END of lsp-type definition.

                leaf sr-policy-name  {
                    type  leafref {
                        path  "../config/sr-policy-name";
                    }
                    description "This attribute is used to configure policy-name of the SR S-BFD
                                session";
                } // END of sr-policy-name definition.

                container config {
                    description
                        "Configuration container for SR S-BFD";
                    uses sbfd-sr-policy-config;
                } // END of config-container definition.
                container state {
                    config false;
                    description
                        "Operational container for SR S-BFD";
                    uses sbfd-sr-policy-config;
                } // END of state-container definition.
                container session-attributes {
                    description
                        "S-BFD session attributes";
                    container config {
                        description
                            "Configuration container for SBFD session attributes";
                        uses sbfd-attributes-config;
                    } // END of config-container definition.
                    container state {
                        config false;
                        description
                            "Operational container for SBFD session attributes";
                        uses sbfd-attributes-config;
                    } // END of state-container definition.
                    uses sbfd-interval-attributes-top;
                } // END of session-attributes-container definition.
            } // End of sr-policy-list
        } // END of sr-policies-container definition.
    } // END of sbfd-sr-policies-top definition.

    grouping  seamless-bfd-grouping {
    description
        "Top container for sbfd related configuration";
    container seamless-bfd {
        if-feature feature-list:HAVE_SBFD;
        description
            "Top container for sbfd related configuration";
        container state {
            config false;
            description
                "Operational container for S-BFD Reflector Dicriminator";
            uses sbfd-discriminators-state;
        } // END of state-container definition.
        uses sbfd-sr-policies-top;
        uses sbfd-local-discriminator-top;
    } // END of seamless-bfd-container definition.
    } // END of seamless-bfd-grouping definition.

    uses seamless-bfd-grouping;

}
