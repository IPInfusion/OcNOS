/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-vxlan.yang
*
*/

module ipi-vxlan {

    yang-version 1.1;

    namespace   "http://www.ipinfusion.com/yang/ocnos/ipi-vxlan";

    prefix "ipi-vxlan";

    import cml-data-types {
        prefix cml-data-types;
        revision-date 2026-05-15;
    }

    import ietf-inet-types {
        prefix inet;
        revision-date 2013-07-15;
    }

    import ipi-vxlan-types {
        prefix ipi-vxlan-types;
        revision-date 2025-11-04;
    }

    import ipi-interface {
        prefix ipi-interface;
        revision-date 2026-03-10;
    }

    import ipi-bridge {
        prefix ipi-bridge;
        revision-date 2026-07-30;
    }

    import ipi-vlan {
        prefix ipi-vlan;
        revision-date 2026-02-02;
    }

    import ipi-vrf {
        prefix ipi-vrf;
        revision-date 2026-08-12;
    }

    import ipi-qos {
        prefix ipi-qos;
        revision-date 2026-09-09;
    }

    import ipi-network-instance {
        prefix ipi-network-instance;
        revision-date 2026-08-12;
    }

    import ipi-mac-limit {
        prefix ipi-mac-limit;
        revision-date 2025-05-22;
    }

    import ietf-yang-types {
        prefix yang;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for VxLAN protocol";


    revision "2025-12-11" {
        description "Changed Type of access-port-description attribute";
        reference " 0.15.0.";
    }

    revision "2025-11-04" {
        description "Updated element name Dynamic to Dynamic-Local";
        reference " 0.14.12.";
    }

    revision "2025-11-03" {
        description "Added when tag for tenant-type and tenant-type-bridge attributes, removed optional-attribute for bridge-vlan-id configuration.";
        reference " 0.14.11.";
    }

    revision "2025-10-20" {
        description "Moved VxLAN VNI counter to ipi-platform-profile-hardware-l2vpn-instances-limits module";
        reference " 0.14.10.";
    }

    revision "2025-09-11" {
        description "Removed attribute mh-mac-relocate-scan";
        reference " 0.14.9.";
    }

    revision "2025-09-09" {
        description "Added a counter for the VxLAN VNIs in use";
        reference " 0.14.8.";
    }

    revision "2025-09-08" {
        description "Added dependentObject with global vxlan disable cli and multi-homed system-mac";
        reference " 0.14.7.";
    }

    revision "2025-09-05" {
        description "Removing if-feature HAVE_BGNOS_CUSTOM from vtep-entries-top grouping";
        reference " 0.14.6.";
    }

    revision "2025-08-22" {
        description "One flag modified to HAVE_ALL_PHOTONICS_CUSTOM";
        reference " 0.14.5.";
    }

    revision "2025-08-11" {
        description "Changed nvo vxlan mac-move-count to evpn mac-move-count";
        reference " 0.14.4.";
    }

    revision "2025-08-05" {
        description "CLI implementation nvo vxlan mac-move-count";
        reference " 0.14.3.";
    }

    revision "2025-08-01" {
        description "Added dependentObject in /vxlan/global/config for delete";
        reference " 0.14.2.";
    }

    revision "2025-07-10" {
        description "Removed evpn-mac-holdtime attribute";
        reference " 0.14.1.";
    }

    revision "2025-05-23" {
        description "Import ipi-if-extended is not required as it is used only in dependency";
        reference " 0.14.0.";
    }

    revision "2025-05-22" {
        description "Added dependent Object in vxlan-tenants container for tunnel/config";
        reference " 0.13.5.";
    }

    revision "2025-05-09" {
        description "Fix compilation warnings";
        reference " 0.13.4.";
    }

    revision "2025-05-05" {
        description "Added input displayString and helpString for learning-limit EVI and AC";
        reference " 0.13.3.";
    }

    revision "2025-04-28" {
        description "Added CML_SKIP_HITLESS_MERGE for tenant-xconnect-type attribute";
        reference " 0.13.2.";
    }

    revision "2025-04-08" {
        description "Added learning-limit for 'nvo vxlan access-if' modes and also for 'nvo vxlan' EVI instance.";
        reference " 0.13.1.";
    }

    revision "2025-03-24" {
        description "Added 'CML_UNIQUE' for attributes 'xconnect-identifier','tenant-description'and 'irb-name'";
        reference " 0.13.0.";
    }

    revision "2025-02-20" {
        description "CLI implementation disable-l3-termination check removed for Trident 4";
        reference " 0.12.14.";
    }

    revision "2025-02-06" {
        description "CLI implementation to Disable arp/nd cache on interface";
        reference " 0.12.13.";
    }

    revision "2025-01-21" {
        description "CLI implementation disable-l3-termination";
        reference " 0.12.7.";
    }

    revision "2024-11-15" {
        description "Updated Vxlan MAC ageing and Arp-Nd refresh time";
        reference " 0.12.11.";
    }

    revision "2024-11-13" {
        description "Added dependent object for arp-cache disable in /vxlan/global/config";
        reference " 0.12.10.";
    }

    revision "2024-10-30" {
        description "CLI implementation for MH MAC relocate scan";
        reference " 0.12.9.";
    }

    revision "2024-10-18" {
        description "CLI implementation evp-mac-holdtime";
        reference " 0.12.9.";
    }

    revision "2024-10-08" {
        description "Added 'is-bitmap-check-enable' in vxlan-tenants container with config tenant-type";
        reference " 0.12.8.";
    }

    revision "2024-10-03" {
        description "CLI implementation disable-arp-storm-control-for-cpu";
        reference " 0.12.8.";
    }

    revision "2024-09-30" {
        description "Fix the when directive for empty flags enable-vxlan and enable-switchport";
        reference " 0.12.7.";
    }

    revision "2024-09-18" {
        description "Added pattern for destiantion-vtep-ip";
        reference " 0.12.6.";
    }

    revision "2024-07-25" {
        description "Added length for description";
        reference " 0.12.5.";
    }

    revision "2024-07-24" {
        description "Enabled the access-if-vxlan and vxlan bridge-vlan CLI only for TR3 boards";
        reference " 0.12.4.";
    }

    revision "2024-07-08" {
        description "Added the dependency of bridge-vlan-id with global vlan";
        reference " 0.12.3.";
    }

    revision "2024-06-28" {
        description "Added the XGS flag for new cli vxlan-access-if";
        reference " 0.12.2.";
    }

    revision "2024-06-21" {
        description "Added the new cli vxlan-access-if inside interface mode";
        reference " 0.12.1.";
    }

    revision "2024-06-19" {
        description "Added length for vxlan access-port 'description' attribute";
        reference " 0.11.2.";
    }

    revision "2024-06-13" {
        description "Changed vxlan-qos-global-top when condition";
        reference " 0.12.0.";
    }

    revision "2024-05-30" {
        description "Added utils_func 'cml_ipv6_format' for ipv6-address attribute";
        reference " 0.11.1.";
    }

    revision "2024-04-24" {
        description "Added mode for clear commands";
        reference " 0.11.0.";
    }

    revision "2024-03-11" {
        description "Add force-unset to vtep-ipv4 attribute";
        reference " 0.10.0.";
    }

    revision "2024-02-13" {
        description "Unset first vxlan-name before setting the new value";
        reference " 0.9.15.";
    }

    revision "2024-02-09" {
        description "add skip-yang for when tag";
        reference " 0.9.14.";
    }

    revision "2024-02-05" {
        description "Changed the helpString for port-vlan of single and double tagged access interface";
        reference " 0.9.13.";
    }

    revision "2024-02-01" {
        description "Changed the helpstring for interface-name of vxlan access-if";
        reference " 0.9.12.";
    }

    revision "2024-01-15" {
        description "Added CML_SKIP_HITLESS_MERGE for xconnect-identifier attribute";
        reference " 0.12.12.";
    }

    revision "2024-01-06" {
        description "Added support for EVPN ETREE";
        reference " 0.9.11.";
    }

    revision "2024-01-02" {
        description "Attribute bridge-vlan-id added under vxlan-tenant-global-config grouping to create tenant with ingress-replication bridge-vlan tunnel and changes for CLI support";
        reference " 0.9.10.";
    }

    revision "2023-12-15" {
        description "Added flag BGP_EVPN in mac address attr for arp-nd refresh timer cli";
        reference " 0.9.9.";
    }

    revision "2023-12-12" {
        description "Added mac address into arp-nd refresh timer cli";
        reference " 0.9.8.";
    }

    revision "2023-10-16" {
        description "Added streaming telemetry yaml file";
        reference " 0.9.7.";
    }

    revision "2023-08-28" {
        description "modified the helpstring for tag-protocol-identifier attribute";
        reference " 0.9.6.";
    }

    revision "2023-08-24" {
        description "RPC Implementation for clear nvo vxlan mac address-table with vnid and mac+vnid combination";
        reference " 0.9.5.";
    }

    revision "2023-08-23" {
        description "Added new enum values to VXLAN_VTEP_REDUND_TYPE_T to map vteps having multiple redund types in remote-vtep-entries grouping";
        reference " 0.9.4.";
    }

    revision "2023-07-10" {
        description "Enable QoS by default related changes";
        reference " 0.9.3.";
    }

    revision "2023-06-28" {
        description "Added new grouping for remote-vtep-entries with attributes remote-vtep-ip-addr, description, redund-type";
        reference " 0.9.2.";
    }

    revision "2023-06-26" {
        description "Added module-init-condition to disable vxlan cli's for TH3 platform";
        reference " 0.9.1.";
    }

    revision "2023-04-18" {
        description "added dependentObject vxlan-tenant in vxlan/global/config";
        reference " 0.9.0.";
    }

    revision "2023-04-14" {
        description "disabled clear vxlan counters for port-vlan for DNX";
        reference " 0.8.4.";
    }

    revision "2023-02-21" {
        description "updated API for disabling VxLAN enable";
        reference " 0.8.3.";
    }

    revision "2023-02-17" {
        description "Fixed prependstr warning";
        reference " 0.8.2.";
    }

    revision "2023-02-15" {
        description "Add enclosing container for below mentioned lists: tagged-access-interface, untagged-access-interface, double-tagged-access-interface, access-interface-qos-type-mapping, host-mac-ipv4, host-mac-ipv6, qos-tunnel-mapping, vxlan-tenant, static-tenant";
        reference " 0.8.1.";
    }

    revision "2023-01-27" {
        description "updated dependentObject in /vxlan/global/config";
        reference " 0.8.0.";
    }

    revision "2023-01-12" {
        description "Updated input for RDN attrs";
        reference " 0.7.6.";
    }

    revision "2023-01-11" {
        description "Delete when constraint for attr irb-advertise-host-route";
        reference " 0.7.5.";
    }

    revision "2023-01-04" {
        description "Changed the name of the RDN of objectlist untagged-access-interface";
        reference " 0.7.4.";
    }

    revision "2022-12-21" {
        description "Added implicit_delete in ipi-vxlan/vxlan/tagged-access-interface/map/config";
        reference " 0.7.3.";
    }

    revision "2022-11-21" {
        description "Added tag include-input-for-unset for advertise-host-to-route attribute";
        reference " 0.7.2.";
    }

    revision "2022-11-16" {
        description "Added advertise-host-to-route option for evpn-IRB";
        reference " 0.7.1.";
    }

    revision "2022-11-11" {
        description "Added implicit-delete tags to remove empty config container";
        reference " 0.7.0.";
    }

    revision "2022-10-29" {
        description "Added max-cache-disable to 2500 evpn data model";
        reference " 0.5.4.";
    }

    revision "2022-10-20" {
        description "Created a separated container for arp/nd cache config and vxlan identifier for tagged/double-tagged access port to guarantee the applying order";
        reference " 0.6.4.";
    }

    revision "2022-10-13" {
        description "Created a separated container for arp/nd cache config and vxlan identifier for untagged access port to guarantee the applying order";
        reference " 0.6.3.";
    }

    revision "2022-09-15" {
        description "Updated MAC_ADDR macro with it's value";
        reference " 0.6.2.";
    }

    revision "2022-09-13" {
        description "Added if-feature HAVE_BGP_EVPN for accessing evpn data model";
        reference " 0.6.1.";
    }

    revision "2022-07-13" {
        description "Added dependent object in tagged access interface";
        reference " 0.6.0.";
    }

    revision "2022-06-09" {
        description "Blocking nvo vxlan access-if cli for Jericho2";
        reference " 0.5.3.";
    }

    revision "2022-06-01" {
        description "Updated the yang file with feature";
        reference " 0.5.2.";
    }

    revision "2022-05-04" {
        description "Remove VTEP-IP dependency with secondary ip ";
        reference " 0.5.1.";
    }

    revision "2022-04-22" {
        description "Added dependent object for global vrf configs";
        reference " 0.5.0.";
    }

    revision "2022-02-16" {
        description "Added new attributes in grouping vxlan-access-port-counters-state";
        reference " 0.4.3.";
    }

    revision "2021-12-28" {
        description "VxLAN Xconnect (ELINE) get-api update";
        reference " 0.4.2.";
    }

    revision "2021-12-27" {
        description "VxLAN Xconnect inner-vid-disabled option add";
        reference " 0.4.1.";
    }

    revision "2021-11-29" {
        description "VxLAN Xconnect (ELINE) New feature";
        reference " 0.4.0.";
    }

    revision "2021-10-14" {
        description "Modified the access interface grouping as separted for arp/nd cache inorder to max-cache-disable-count dependency needed only for tagged/stacked incase of Non-Dune";
        reference " 0.3.6.";
    }

    revision "2021-09-29" {
        description "changed ordering of mac-ageing timer and arp-nd refresh timer";
        reference " 0.3.5.";
    }

    revision "2021-09-15" {
        description "Added dependency for secondary ip address config and implicit_delete for parent container";
        reference " 0.3.4.";
    }

    revision "2021-09-07" {
        description "Added dependency for API exection order for esi/system-mac";
        reference " 0.3.3.";
    }

    revision "2021-09-01" {
        description "Changed base interface module's switchport attribute name and the datatype from bool to empty";
        reference " 0.3.2.";
    }

    revision "2021-08-16" {
        description "Added default option with port only access-interface creation and deletion; Changed to allow vlan range also in case of tagged access-interface";
        reference " 0.3.1.";
    }

    revision "2021-08-01" {
        description "Updated trigger for default mode addition for missing bridges";
        reference " 0.3.0.";
    }

    revision "2021-03-31" {
        description "Added helpstrings, Modified RPC implementation on clear network/access port";
        reference " 0.2.1.";
    }

    revision "2021-03-04" {
        description "On Access Interface configuration modified when tags on switchport status check";
        reference " 0.2.0.";
    }

    revision "2020-12-15" {
        description "Change to have data-types in lower case instead of camel case";
        reference " 0.1.1.";
    }

    revision "2020-06-02" {
        description "Restructured as per Openconfig style";
        reference " 0.1.0.";
    }

    grouping vxlan-global-config {
        description
            "Grouping for global vxlan configuration";
        leaf enable-vxlan  {
            type  empty;
            mandatory true;
            description "Use this attribute to enable VxLAN module. Without this attribute
                        vxlan functionality can not be achieved";
        } // END of enable-vxlan definition.

        leaf vtep-ipv4  {
            type  inet:ipv4-address;
            description "Use this attribute to set source vtep global ip address. This will be
                        treated at vxlan tunnel source address";
        } // END of vtep-ipv4 definition.

        leaf mac-ageing-timer  {
            type  uint32 {
                 range "10..1000000"  {
                    description "10..1000000:Feature : HAVE_DUNE Supported range 10 - 572Not Feature :
                            HAVE_DUNE  Supported range 10 - 1000000";
                 }
            }
            units "seconds";
            default "300";
            description "Use this attribute to set the time till a learned mac address will
                        persist after last update";
        } // END of mac-ageing-timer definition.

        leaf arp-nd-refresh-timer  {
            if-feature feature-list:HAVE_BGP_EVPN;
            type  uint32 {
                 range "3..21600"  {
                    description "3..21600:Feature : HAVE_DUNE Supported range 3 - 190Not Feature :
                            HAVE_DUNE  Supported range 3 - 21600";
                 }
            }
            units "seconds";
            description "Use this attribute to configure aging out the arp-cache and nd-cache
                        entries for given time multiplied by 3 in secs.";
        } // END of arp-nd-refresh-timer definition.

        leaf mac-address  {
            // when " ipi-vxlan:vxlan/global/config/arp-nd-refresh-timer ";
            if-feature feature-list:HAVE_BGP_EVPN;
            type  cml-data-types:cml_mac_addr_t {
                length "1..1965";
            }
            description "Use this attribute to set the mac address with arp-nd refresh-timer";
        } // END of mac-address definition.

        leaf maximum-cache-disable-count  {
            if-feature feature-list:HAVE_BGP_EVPN;
            if-feature feature-list:NOT_HAVE_DUNE;
            type  uint16 {
                 range "1..2500"  {
                    description "1..2500: Supported range 1 - 2500";
                 }
            }
            description "Use this command to configure the maximum number of ARP and ND cache
                        disables on access ports configured with
                        the port+VLAN options. This command does not limit the ARP and ND
                        cache disables on access ports created with
                        only the port option.";
        } // END of maximum-cache-disable-count definition.

        leaf disable-arp-storm-control-for-cpu  {
            if-feature feature-list:NOT_HAVE_DUNE;
            type  empty;
            description "Use this attribute to set the vxlan disable arp storm control for cpu";
        } // END of disable-arp-storm-control-for-cpu definition.

    } // END of vxlan-global-config definition.
    grouping vxlan-qos-global-config {
        description
            "Grouping for global vxlan-qos configuration";
        leaf traffic-direction  {
            type  ipi-vxlan-types:vxlan_qos_dir_t;
            description "Use this attribute to set global direction(ingress/egress) for VxLAN.
                        Ingreess means traffic coming to network side and egress means traffic
                        going out from network side";
        } // END of traffic-direction definition.

        leaf qos-map-mode  {
            type  ipi-vxlan-types:vxlan_qos_global_mode_t;
            description "Use this attribute to set VxLAN-QoS Map Mode for overlay dscp";
        } // END of qos-map-mode definition.

        leaf profile-name  {
            type  string {
                length "1..1965";
                pattern "[^?' =,>|]+";
            }
            mandatory true;
            description "Use this attribute to map QOS profile name. This profile name should
                        be already configured before mapping it to vxlan tunnel";
        } // END of profile-name definition.

    } // END of vxlan-qos-global-config definition.
    grouping vxlan-tenant-global-config {
        description
            "Grouping for global vxlan-qos configuration";
        leaf vxlan-identifier  {
            type  uint32 {
                 range "1..16777215"  {
                    description "1..16777215: Supported range 1 - 16777215";
                 }
            }
            description "Use this attribute to add a tenant and the type of VPN";
        } // END of vxlan-identifier definition.

        leaf tenant-type  {
            type  ipi-vxlan-types:vxlan_tenant_type_t;
            description "Use this attribute to create tenant with multicast tunnel";
        } // END of tenant-type definition.

        leaf tenant-type-bridge  {
            type  ipi-vxlan-types:vxlan_tenant_type_bridge_t;
            description "Use this attribute to create tenant with multicast tunnel and Bridge
                        id";
        } // END of tenant-type-bridge definition.

        leaf bridge-vlan-id  {
            if-feature feature-list:NOT_HAVE_DUNE;
            type  leafref {
                path  "/ipi-network-instance:network-instances/ipi-network-instance:network-instance/ipi-bridge:bridge/ipi-vlan:vlans/ipi-vlan:vlan/ipi-vlan:vlan-id";
            }
            description "Use this attribute to create tenant with ingress-replication
                        bridge-vlan tunnel";
        } // END of bridge-vlan-id definition.

        leaf etree-leaf  {
            type  empty;
            description "Use this attribute to select the particular vpn-id as leaf";
        } // END of etree-leaf definition.

        leaf xconnect-identifier  {
            if-feature feature-list:HAVE_EVPN_VPWS;
            type  uint32 {
                 range "1..16777215"  {
                    description "1..16777215: Supported range 1 - 16777215";
                 }
            }
            description "Use this attribute to create Xconnect tenant";
        } // END of xconnect-identifier definition.

        leaf tenant-xconnect-type  {
            type  ipi-vxlan-types:vxlan_tenant_xconnect_type_t;
            description "Use this attribute to create tenant with different type of tunnel";
        } // END of tenant-xconnect-type definition.

    } // END of vxlan-tenant-global-config definition.
    grouping vxlan-tenant-config {
        description
            "Grouping for vxlan-tenant configuration";
        leaf vrf-name  {
            if-feature feature-list:HAVE_BGP_EVPN;
            type  leafref {
                path  "/ipi-network-instance:network-instances/ipi-network-instance:network-instance/ipi-vrf:vrf/ipi-vrf:config/ipi-vrf:vrf-name";
            }
            description "Use this attribute to map VRF to carry EVPN routes. This defines BGP
                        as the mechanism for host reachability advertisement.";
        } // END of vrf-name definition.

        leaf-list map-network  {
            type  string {
                length "1..1965";
                pattern "[^?' =,>|]+";
            }
            description "Use this attribute to map a tunnel to the tenant";
        } // END of map-network definition.

        leaf mac-hold-timer  {
            if-feature feature-list:HAVE_BGP_EVPN;
            type  int32 {
                 range "-1..300"  {
                    description "-1..300: Supported range -1 - 300";
                 }
            }
            units "seconds";
            default "0";
            description "Use this attribute to set the time a host mac entry
                        will persist after unconfiguring. Hold time range -1 to 300 in
                        seconds.
                        -1(never expire)";
        } // END of mac-hold-timer definition.

        leaf tenant-description  {
            type  string {
                length "1..10";
                pattern "[^?' =,>|]+";
            }
            description "Use this attribute to set VxLAN identifier name";
        } // END of tenant-description definition.

        leaf irb-name  {
            if-feature feature-list:HAVE_BGP_EVPN;
            type  leafref {
                path  "/ipi-interface:interfaces/ipi-interface:interface/ipi-interface:name";
            }
            description "Use this attribute to to configure default gateway behavior on a VTEP
                        for particular VNID.";
        } // END of irb-name definition.

        leaf disable-l3-termination  {
            if-feature feature-list:NOT_HAVE_DUNE;
            type  cml-data-types:cml_mac_addr_t {
                length "1..1965";
            }
            description "Use this attribute to set the disable l3 terminaation";
        } // END of disable-l3-termination definition.

        leaf evi-learning-limit  {
            type  leafref {
                path  "/ipi-mac-limit:mac-limit-global/ipi-mac-limit:mac-limit-profiles/ipi-mac-limit:mac-limit-profile-inst/ipi-mac-limit:config/ipi-mac-limit:mac-lim-profile-name";
            }
            description "Attach (EVPN-VxLAN) EVI MAC learning limit profile";
        } // END of evi-learning-limit definition.

    } // END of vxlan-tenant-config definition.
    grouping vxlan-tenant-route-count-state {
        description
            "Grouping for vxlan-tenant configuration";
        leaf total  {
            type  uint32;
            description "Use this attribute to show count of Total Route Entries";
        } // END of total definition.

        leaf mac-only  {
            type  uint32;
            description "Use this attribute to show count of MAC Only Entries";
        } // END of mac-only definition.

        leaf mac-ipv4  {
            type  uint32;
            description "Use this attribute to show count of MAC Ipv4 Entries";
        } // END of mac-ipv4 definition.

        leaf mac-ipv6  {
            if-feature feature-list:HAVE_IPV6;
            type  uint32;
            description "Use this attribute to show count of MAC Ipv6 Entries";
        } // END of mac-ipv6 definition.

    } // END of vxlan-tenant-route-count-state definition.
    grouping vxlan-tenant-xconnect-mapping-state {
        description
            "Grouping for vxlan xconnect mapping";
        leaf source-tenant-description  {
            type  string {
                length "1..1965";
                pattern "[^?' =,>|]+";
            }
            description "Use this attribute to show name of source tenant";
        } // END of source-tenant-description definition.

        leaf destination-vpws-identifier  {
            type  uint32;
            description "Use this attribute to show the remote vpws id";
        } // END of destination-vpws-identifier definition.

        leaf vlan-id  {
            type  string {
                length "1..1965";
                pattern "[^?' =,>|]+";
            }
            description "vlan id";
        } // END of vlan-id definition.

        leaf inner-vlan-id  {
            type  uint32;
            description "Inner vlan Id";
        } // END of inner-vlan-id definition.

        leaf source-interface  {
            type  string {
                length "1..1965";
                pattern "[^?' =,>|]+";
            }
            description "Use this attribute to show source connection of tunnel";
        } // END of source-interface definition.

        leaf destination-interface  {
            type  string {
                length "1..1965";
                pattern "[^?' =,>|]+";
            }
            description "Use this attribute to show destination connection of tunnel";
        } // END of destination-interface definition.

        leaf vtep-ip-address  {
            type  inet:ipv4-address;
            description "Use this attribute to show tunnel ip address";
        } // END of vtep-ip-address definition.

        leaf connection-type  {
            type  ipi-vxlan-types:vxlan_tenant_xconnect_connection_type_t;
            description "Use this attribute to show the type of network connection";
        } // END of connection-type definition.

        leaf connection-status  {
            type  ipi-vxlan-types:vxlan_tenant_xconnect_connection_status_t;
            description "Use this attribute to show status of network connection";
        } // END of connection-status definition.

    } // END of vxlan-tenant-xconnect-mapping-state definition.
    grouping vxlan-static-tenant-config {
        description
            "Grouping for vxlan-static tenant configuration";
        leaf mac-address  {
            type  cml-data-types:cml_mac_addr_t {
                length "1..1965";
            }
            description "Use this attribute to know MAC address of the
                        host.create a static route to reach a destination MAC in the VXLAN
                        forwarding table. This command helps to supports different tenants so
                        that they can have the same MAC/IP, but different VNIDs.This command
                        is required for unicast tunnels to map the remote VTEP";
        } // END of mac-address definition.

        leaf remote-vtep-ipv4  {
            type  inet:ipv4-address;
            mandatory true;
            description "Use this attribute to set unicast IP address of the destination VTEP";
        } // END of remote-vtep-ipv4 definition.

    } // END of vxlan-static-tenant-config definition.
    grouping vxlan-tenant-arp-cache-state {
        description
            "Grouping for display arp-cache information";
        leaf host-ip  {
            type  inet:ipv4-address;
            description "Use this attribute to show Host IP address";
        } // END of host-ip definition.

        leaf host-mac  {
            type  cml-data-types:cml_mac_addr_t {
                length "1..1965";
            }
            description "Use this attribute to show Host MAC address";
        } // END of host-mac definition.

        leaf host-type  {
            type  ipi-vxlan-types:vxlan_host_t;
            description "Use this attribute to show Host Type";
        } // END of host-type definition.

        leaf interface-index  {
            type  uint32;
            description "Use this attribute to show Interface Index";
        } // END of interface-index definition.

    } // END of vxlan-tenant-arp-cache-state definition.
    grouping vxlan-tenant-nd-cache-state {
        description
            "Grouping for display nd-cache information";
        leaf host-ip  {
            type  inet:ipv6-address;
            description "Use this attribute to show Host IP address";
        } // END of host-ip definition.

        leaf host-mac  {
            type  cml-data-types:cml_mac_addr_t {
                length "1..1965";
            }
            description "Use this attribute to show Host MAC Address";
        } // END of host-mac definition.

        leaf host-type  {
            type  ipi-vxlan-types:vxlan_host_t;
            description "Use this attribute to show Host Type";
        } // END of host-type definition.

        leaf interface-index  {
            type  uint32;
            description "Use this attribute to show Interface Index";
        } // END of interface-index definition.

    } // END of vxlan-tenant-nd-cache-state definition.
    grouping vxlan-tenant-mac-table-state {
        description
            "Grouping for display mac table information";
        leaf mac-address  {
            type  cml-data-types:cml_mac_addr_t {
                length "1..1965";
            }
            description "MAC Adress of the host";
        } // END of mac-address definition.

        leaf interface-name  {
            type  leafref {
                path  "/ipi-interface:interfaces/ipi-interface:interface/ipi-interface:name";
            }
            description "interface name";
        } // END of interface-name definition.

        leaf vlan-id  {
            type  string {
                length "1..1965";
                pattern "[^?' =,>|]+";
            }
            description "vlan id";
        } // END of vlan-id definition.

        leaf inner-vlan-id  {
            type  uint32;
            description "Inner vlan Id";
        } // END of inner-vlan-id definition.

        leaf vtep-ip-esi  {
            type  string {
                length "1..1965";
                pattern "[^?' =,>|]+";
            }
            description "VTEP global ip address or ESI";
        } // END of vtep-ip-esi definition.

        leaf host-type  {
            type  ipi-vxlan-types:vxlan_host_t;
            description "Host Type";
        } // END of host-type definition.

        leaf host-status  {
            type  ipi-vxlan-types:vxlan_host_status_t;
            description "Host Status";
        } // END of host-status definition.

        leaf access-port-description  {
            type  cml-data-types:cml_line_t {
                length "1..1965";
            }
            description "Description for the port";
        } // END of access-port-description definition.

    } // END of vxlan-tenant-mac-table-state definition.
    grouping vxlan-tenant-static-host-state {
        description
            "Grouping for displaying static host state";
        leaf mac-address  {
            type  cml-data-types:cml_mac_addr_t {
                length "1..1965";
            }
            description "MAC Adress of the host";
        } // END of mac-address definition.

        leaf static-host-state  {
            type  ipi-vxlan-types:vxlan_static_host_state_t;
            description "static host state";
        } // END of static-host-state definition.

        leaf host-ipv4  {
            type  inet:ipv4-address;
            description "Host IP Adress ipv4";
        } // END of host-ipv4 definition.

    } // END of vxlan-tenant-static-host-state definition.
    grouping vxlan-tenant-static-host-ipv6-state {
        description
            "Grouping for displaying static host-ipv6 state";
        leaf mac-address  {
            type  cml-data-types:cml_mac_addr_t {
                length "1..1965";
            }
            description "MAC Adress of the host";
        } // END of mac-address definition.

        leaf static-host-state  {
            type  ipi-vxlan-types:vxlan_static_host_state_t;
            description "static host state";
        } // END of static-host-state definition.

        leaf host-ipv6  {
            if-feature feature-list:HAVE_IPV6;
            type  inet:ipv6-address;
            description "Host IP Adress ipv6";
        } // END of host-ipv6 definition.

    } // END of vxlan-tenant-static-host-ipv6-state definition.
    grouping vxlan-tunnel-state {
        description
            "Grouping for displaying tunnel information";
        leaf destination-vtep-ip  {
            type  inet:ipv4-address {
                pattern "(([0-9]|[1-9][0-9]|1[0-9][0-9]|2[0-4][0-9]|25[0-5])\\.){3}([0-9]|[1-9][0-9]|1[0-9][0-9]|2[0-4][0-9]|25[0-5])";
                }
                description "Use this attribute to set Tunnel destination IP";
            } // END of destination-vtep-ip definition.

            leaf source-vtep-ip  {
                type  inet:ipv4-address;
                description "Use this attribute to set Tunnel source IP";
            } // END of source-vtep-ip definition.

            leaf up-down-time  {
                type  yang:timeticks;
                description "Use this attribute to indicate tunnel up/down time";
            } // END of up-down-time definition.

            leaf tunnel-status  {
                type  ipi-vxlan-types:vxlan_tunnel_status_t;
                description "Use this attribute to see the Status of tunnel";
            } // END of tunnel-status definition.

    } // END of vxlan-tunnel-state definition.
    grouping vxlan-tunnel-counters-state {
        description
            "Grouping for displaying tunnel counters and statistics.";
        container counters {
            config false;
            description
                "A collection of vxlan network-related statistics";
            leaf out-bytes  {
                type  yang:counter64;
                description "This indicates total number of bytes sent out from tunnel interface";
            } // END of out-bytes definition.

            leaf out-packets  {
                type  yang:counter64;
                description "This indicates total number of packets sent out from tunnel interface";
            } // END of out-packets definition.

            leaf in-bytes  {
                type  yang:counter64;
                description "This indicates total number of bytes received on tunnel interface";
            } // END of in-bytes definition.

            leaf in-packets  {
                type  yang:counter64;
                description "This indicates total number of packets received on tunnel interface";
            } // END of in-packets definition.

            leaf tx-arp-discard-packets  {
                type  yang:counter64;
                description "This Object describes Arp Discarded Packets";
            } // END of tx-arp-discard-packets definition.

            leaf tx-nd-discard-packets  {
                type  yang:counter64;
                description "This Object describes Nd Discarded Packets";
            } // END of tx-nd-discard-packets definition.

            leaf tx-arp-request-packets  {
                type  yang:counter64;
                description "This Object describes Arp request Transmitted Packets";
            } // END of tx-arp-request-packets definition.

            leaf tx-arp-reply-packets  {
                type  yang:counter64;
                description "This Object describes Arp reply Transmitted Packets";
            } // END of tx-arp-reply-packets definition.

            leaf tx-neighbor-solicitation-packets  {
                type  yang:counter64;
                description "This Object describes Neighbour Solicitation Transmitted Packets";
            } // END of tx-neighbor-solicitation-packets definition.

            leaf tx-neighbor-advertisement-packets  {
                type  yang:counter64;
                description "This Object describes Neighbour Advertisement Transmitted Packets";
            } // END of tx-neighbor-advertisement-packets definition.

            leaf tx-garp-packets  {
                type  yang:counter64;
                description "This Object describes Garp Transmitted Packets";
            } // END of tx-garp-packets definition.

            leaf tx-gna-packets  {
                type  yang:counter64;
                description "This Object describes Gna Transmitted Packets";
            } // END of tx-gna-packets definition.

        } // END of counters-container definition.
    } // END of vxlan-tunnel-counters-state definition.
    grouping vxlan-access-port-vlan-config {
        description
            "Grouping for single tagged vxlan access interface";
        leaf vlan-identifier  {
            type  string {
                length "1..1965";
                pattern "[^?' =,>|]+";
            }
            description "Use this attriute to map a VLAN on physical interface to identify the
                        tenant traffic and to enter NVO access interface mode";
        } // END of vlan-identifier definition.

    } // END of vxlan-access-port-vlan-config definition.
    grouping vxlan-access-port-stacked-vlan-config {
        description
            "Grouping for double tagged vxlan access interface";
        leaf vlan-identifier  {
            type  string {
                length "1..1965";
                pattern "[^?' =,>|]+";
            }
            description "S-VLAN on which interface is mapped";
        } // END of vlan-identifier definition.

        leaf inner-vlan-identifier  {
            type  uint32 {
                 range "2..4094"  {
                    description "2..4094: Supported range 2 - 4094";
                 }
            }
            description "Use this attriute to map VLAN'S on an interface to identify the tenant
                        traffic and to enter NVO access interface mode";
        } // END of inner-vlan-identifier definition.

    } // END of vxlan-access-port-stacked-vlan-config definition.
    grouping vxlan-access-encapsulation-config {
        description
            "Grouping for single tagged vxlan access interface";
        leaf tag-protocol-identifier  {
            type  string {
                length "1..1965";
                pattern "[^?' =,>|]+";
            }
            description "Use this attribute to set the Tpid for the outer vlan. Ox88A8: IEEE
                        802.1ad Provider Bridging and Ox9100: IEEE 802.1Q VLAN-tagged frame
                        with double tagging";
        } // END of tag-protocol-identifier definition.

    } // END of vxlan-access-encapsulation-config definition.
    grouping vxlan-untagged-access-interface-config {
        description
            "Grouping for vxlan untagged access interface configuration";
        leaf untagged-interface-name  {
            type  leafref {
                path  "/ipi-interface:interfaces/ipi-interface:interface/ipi-interface:name";
            }
            description "Use this attribute to map a physical interface to identify the tenant
                        traffic and to enter NVO access interface mode for untagged access-if";
        } // END of untagged-interface-name definition.

    } // END of vxlan-untagged-access-interface-config definition.
    grouping vxlan-access-interface-config {
        description
            "Grouping for vxlan access interface configuration";
        leaf interface-name  {
            type  leafref {
                path  "/ipi-interface:interfaces/ipi-interface:interface/ipi-interface:name";
            }
            description "Use this attribute to map a physical interface to identify the tenant
                        traffic and to enter NVO access interface mode";
        } // END of interface-name definition.

        leaf admin-shutdown  {
            type  empty;
            description "Use this attribute to shutdown vxlan access interface";
        } // END of admin-shutdown definition.

        leaf description  {
            type  cml-data-types:cml_line_t {
                length "1..32";
            }
            description "Use this attribute to set description of access interface";
        } // END of description definition.

        leaf dynamic-learning-disable  {
            type  empty;
            description "Use this attribute to disable dynamic learning of MACs at the access
                        port. This command also disables dynamic learning of MAC/IP from
                        ARP/ND messages received on this access port.";
        } // END of dynamic-learning-disable definition.

        leaf access-mac-hold-time  {
            type  int32 {
                 range "-1..300"  {
                    description "-1..300: Supported range -1 - 300";
                 }
            }
            description "Use this attribute to set the time a host mac entry will persist after
                        unconfiguring. The feature holds the MAC in hardware until BGP has
                        withdrawn from the neighbors. This helps to reduce flooding to other
                        access ports. This setting applies when the access port is shut down,
                        the physical port on which the access port is down, or the access port
                        is removed from the VNID using the no form of the map vnid command.
                        When the MAC hold time is configured as -1, then the MAC is not
                        removed from the hardware and is also not withdrawn from EVPN BGP";
        } // END of access-mac-hold-time definition.

        leaf arp-nd-flood-suppress  {
            if-feature feature-list:HAVE_BGP_EVPN;
            type  empty;
            description "Use this attribute to restrict the flood of ARP/ND packets towards
                        remote VTEPs or other access ports.This command applies only when the
                        ARP cache and ND cache are enabled. When the ARP cache is disabled,
                        ARP flooding is not suppressed even if this command is given. When the
                        ND cache is disabled, ND flooding is not disabled, even if this
                        command is given";
        } // END of arp-nd-flood-suppress definition.

        leaf garp-gna-enable  {
            if-feature feature-list:HAVE_BGP_EVPN;
            type  empty;
            description "Use this attribute to allow garp-gna packets advertisement";
        } // END of garp-gna-enable definition.

        leaf-list mac-address  {
            type  cml-data-types:cml_mac_addr_t {
                length "1..1965";
            }
            description "Use this attribute to set the static mac address of host";
        } // END of mac-address definition.

        leaf ac-learning-limit  {
            type  leafref {
                path  "/ipi-mac-limit:mac-limit-global/ipi-mac-limit:mac-limit-profiles/ipi-mac-limit:mac-limit-profile-inst/ipi-mac-limit:config/ipi-mac-limit:mac-lim-profile-name";
            }
            description "Attach MAC learning limit profile to VxLAN AC port";
        } // END of ac-learning-limit definition.

    } // END of vxlan-access-interface-config definition.
    grouping vxlan-untagged-access-interface-cache-config {
        description
            "Grouping for vxlan untagged access interface arp/nd cache
                        configuration";
        leaf arp-cache-disable  {
            if-feature feature-list:HAVE_BGP_EVPN;
            type  empty;
            description "Use this attribute to disable the ARP cache for MAC/IP. When the ARP
                        cache is disabled on a VxLAN access port, ZebOS-XP does not reply to
                        any ARP arriving on this port from the cache. ZebOS-XP withdraws all
                        MAC/IPs configured/learned on this access port and removes the MAC/IP
                        entry for this access port from the local ARP cache. ZebOS-XP also
                        makes sure that on withdrawing the MAC/IP route, the MAC does not
                        become unknown. If all routes for this MAC are being withdrawn because
                        of this command, then ZebOS-XP advertises a MAC-only route. This is
                        done so that the MAC does not become unknown and only the cache
                        functionality becomes disabled.See also nvo vxlan max-cache-disable.
                        Use the no form of this command to enable ARP cache for MAC/IP. Note:
                        On enabling the cache, an IP will be in conflict, then the cache
                        enable will fail. The conflict has to be manually removed and then the
                        cache enabled.";
        } // END of arp-cache-disable definition.

        leaf nd-cache-disable  {
            if-feature feature-list:HAVE_BGP_EVPN;
            type  empty;
            description "Use this attribute to disable ND cache for MAC/IPv6. When the ARP
                        cache is disabled on a VxLAN access port, ZebOS-XP does not reply to
                        any ARP arriving on this port from the cache. ZebOS-XP withdraws all
                        MAC/IPs configured/learned on this access port and removes the MAC/IP
                        entry for this access port from the local ARP cache. ZebOS-XP also
                        makes sure that on withdrawing the MAC/IP route, the MAC does not
                        become unknown. If all routes for this MAC are being withdrawn because
                        of this command, then ZebOS-XP advertises a MAC-only route. This is
                        done so that the MAC does not become unknown and only the cache
                        functionality becomes disabled. Use the no form of this command to
                        enable ND cache for MAC/IPv6. Note: On enabling the cache, an IP will
                        be in conflict, then the cache enable will fail. The conflict has to
                        be manually removed and then the cache enabled.";
        } // END of nd-cache-disable definition.

    } // END of vxlan-untagged-access-interface-cache-config definition.
    grouping vxlan-untagged-access-interface-cache {
        description
            "Grouping for ARP/ND cache configuration for untagged access interfaces";
        container cache {
            description
                "ARP/ND cache container";
            container config {
                description
                    "Configuration data for ARP/ND cache";
                uses vxlan-untagged-access-interface-cache-config;
            } // END of config-container definition.
            container state {
                config false;
                description
                    "Operational state data for ARP/ND cache";
                uses vxlan-untagged-access-interface-cache-config;
            } // END of state-container definition.
        } // END of cache-container definition.
    } // END of vxlan-untagged-access-interface-cache definition.
    grouping vxlan-tagged-access-interface-cache {
        description
            "Grouping for ARP/ND cache configuration for tagged access interfaces";
        container cache {
            description
                "ARP/ND cache container";
            container config {
                description
                    "Configuration data for ARP/ND cache";
                uses vxlan-access-interface-cache-config;
            } // END of config-container definition.
            container state {
                config false;
                description
                    "Operational state data for ARP/ND cache";
                uses vxlan-access-interface-cache-config;
            } // END of state-container definition.
        } // END of cache-container definition.
    } // END of vxlan-tagged-access-interface-cache definition.
    grouping vxlan-double-tagged-access-interface-cache {
        description
            "Grouping for ARP/ND cache configuration for double tagged access
                        interfaces";
        container cache {
            description
                "ARP/ND cache container";
            container config {
                description
                    "Configuration data for ARP/ND cache";
                uses vxlan-access-interface-cache-config;
            } // END of config-container definition.
            container state {
                config false;
                description
                    "Operational state data for ARP/ND cache";
                uses vxlan-access-interface-cache-config;
            } // END of state-container definition.
        } // END of cache-container definition.
    } // END of vxlan-double-tagged-access-interface-cache definition.
    grouping vxlan-access-interface-cache-config {
        description
            "Grouping for vxlan tagged and stacked access interface arp/nd cache
                        configuration";
        leaf arp-cache-disable  {
            if-feature feature-list:HAVE_BGP_EVPN;
            type  empty;
            description "Use this attribute to disable the ARP cache for MAC/IP. When the ARP
                        cache is disabled on a VxLAN access port, ZebOS-XP does not reply to
                        any ARP arriving on this port from the cache. ZebOS-XP withdraws all
                        MAC/IPs configured/learned on this access port and removes the MAC/IP
                        entry for this access port from the local ARP cache. ZebOS-XP also
                        makes sure that on withdrawing the MAC/IP route, the MAC does not
                        become unknown. If all routes for this MAC are being withdrawn because
                        of this command, then ZebOS-XP advertises a MAC-only route. This is
                        done so that the MAC does not become unknown and only the cache
                        functionality becomes disabled.See also nvo vxlan max-cache-disable.
                        Use the no form of this command to enable ARP cache for MAC/IP. Note:
                        On enabling the cache, an IP will be in conflict, then the cache
                        enable will fail. The conflict has to be manually removed and then the
                        cache enabled.";
        } // END of arp-cache-disable definition.

        leaf nd-cache-disable  {
            if-feature feature-list:HAVE_BGP_EVPN;
            type  empty;
            description "Use this attribute to disable ND cache for MAC/IPv6. When the ARP
                        cache is disabled on a VxLAN access port, ZebOS-XP does not reply to
                        any ARP arriving on this port from the cache. ZebOS-XP withdraws all
                        MAC/IPs configured/learned on this access port and removes the MAC/IP
                        entry for this access port from the local ARP cache. ZebOS-XP also
                        makes sure that on withdrawing the MAC/IP route, the MAC does not
                        become unknown. If all routes for this MAC are being withdrawn because
                        of this command, then ZebOS-XP advertises a MAC-only route. This is
                        done so that the MAC does not become unknown and only the cache
                        functionality becomes disabled. Use the no form of this command to
                        enable ND cache for MAC/IPv6. Note: On enabling the cache, an IP will
                        be in conflict, then the cache enable will fail. The conflict has to
                        be manually removed and then the cache enabled.";
        } // END of nd-cache-disable definition.

    } // END of vxlan-access-interface-cache-config definition.
    grouping vxlan-access-mac-ipv4-config {
        description
            "Grouping for vxlan access interface configuration";
        leaf mac-address  {
            type  cml-data-types:cml_mac_addr_t {
                length "1..1965";
            }
            description "MAC Address of host connected to vxlan access port";
        } // END of mac-address definition.

        leaf ipv4-address  {
            type  inet:ipv4-address;
            description "USe this attribute to associate a static MAC address and a static IPv4
                        or IPv6 address on an access interface.";
        } // END of ipv4-address definition.

    } // END of vxlan-access-mac-ipv4-config definition.
    grouping vxlan-access-mac-ipv6-config {
        description
            "Grouping for vxlan access host configuration";
        leaf mac-address  {
            type  cml-data-types:cml_mac_addr_t {
                length "1..1965";
            }
            description "MAC Address of host connected to vxlan access port";
        } // END of mac-address definition.

        leaf ipv6-address  {
            type  inet:ipv6-address;
            description "USe this attribute to associate a static MAC address and a static IPv4
                        or IPv6 address on an access interface.";
        } // END of ipv6-address definition.

    } // END of vxlan-access-mac-ipv6-config definition.
    grouping vxlan-access-interface-qos-type-mapping-config {
        description
            "Grouping for vxlan access interface qos configuration";
        leaf profile-map-type  {
            type  ipi-vxlan-types:vxlan_qos_map_profile_type_t;
            description "Use this attribute to map the profile type for which qos profile is
                        already created globally to access port";
        } // END of profile-map-type definition.

        leaf profile-name  {
            type  string {
                length "1..1965";
                pattern "[^?' =,>|]+";
            }
            mandatory true;
            description "Use this attribute to map QOS profile name to port for which QOS
                        profile is already created globally";
        } // END of profile-name definition.

    } // END of vxlan-access-interface-qos-type-mapping-config definition.
    grouping vxlan-irb-config {
        description
            "Grouping for vxlan Integrated Routing and Bridging attributes";
        leaf irb-advertise-host-route  {
            when " /ipi-vxlan:vxlan/ipi-vxlan:vxlan-tenants/ipi-vxlan:vxlan-tenant/ipi-vxlan:config/ipi-vxlan:irb-name ";
            if-feature feature-list:HAVE_BGP_EVPN;
            type  empty;
            description "Use this attribute to set advertise host to route";
        } // END of irb-advertise-host-route definition.

    } // END of vxlan-irb-config definition.
    grouping vxlan-access-port-counters-state {
        description
            "Grouping for displaying tunnel counters and statistics.";
        leaf interface-index  {
            type  uint32;
            config false;
            description "Use this attribute to fetch nvo access port counters";
        } // END of interface-index definition.

        leaf if-name  {
            type  cml-data-types:cml_line_t {
                length "1..1965";
            }
            description "Use this attribute to fetch nvo access port name";
        } // END of if-name definition.

        container access-counters {
            config false;
            description
                "A collection of vxlan access-port-related statistics";
            leaf rx-arp-discard-packets  {
                type  yang:counter64;
                description "This Object describes Arp Discard Packets(Applicable only for logical
                            VxLAN-access ports)";
            } // END of rx-arp-discard-packets definition.

            leaf tx-arp-discard-packet  {
                type  yang:counter64;
                description "This Object describes Arp Out Discard Packets(Applicable only for
                            logical VxLAN-access ports)";
            } // END of tx-arp-discard-packet definition.

            leaf rx-arp-request-packets  {
                type  yang:counter64;
                description "This Object describes Arp request Received Packets(Applicable only for
                            logical VxLAN-access ports)";
            } // END of rx-arp-request-packets definition.

            leaf rx-arp-reply-packets  {
                type  yang:counter64;
                description "This Object describes Arp reply Received Packets(Applicable only for
                            logical VxLAN-access ports)";
            } // END of rx-arp-reply-packets definition.

            leaf tx-arp-request-packet  {
                type  yang:counter64;
                description "This Object describes Arp request Transmitted Packets(Applicable only
                            for logical VxLAN-access ports)";
            } // END of tx-arp-request-packet definition.

            leaf tx-arp-reply-packet  {
                type  yang:counter64;
                description "This Object describes Arp reply Transmitted Packets(Applicable only
                            for logical VxLAN-access ports)";
            } // END of tx-arp-reply-packet definition.

            leaf rx-nd-discard-packets  {
                type  yang:counter64;
                description "This Object describes ND Discard Packets(Applicable only for logical
                            VxLAN-access ports)";
            } // END of rx-nd-discard-packets definition.

            leaf tx-nd-discard-packet  {
                type  yang:counter64;
                description "This Object describes ND Out Discard Packets(Applicable only for
                            logical VxLAN-access ports)";
            } // END of tx-nd-discard-packet definition.

            leaf rx-neighbor-solicitation-packets  {
                type  yang:counter64;
                description "This Object describes ND Solicitaion Received Packets(Applicable only
                            for logical VxLAN-access ports)";
            } // END of rx-neighbor-solicitation-packets definition.

            leaf rx-neighbor-advertisement-packets  {
                type  yang:counter64;
                description "This Object describes ND Advertisement Received Packets(Applicable
                            only for logical VxLAN-access ports)";
            } // END of rx-neighbor-advertisement-packets definition.

            leaf tx-neighbor-solicitation-packet  {
                type  yang:counter64;
                description "This Object describes ND Solicitaion Transmitted Packets(Applicable
                            only for logical VxLAN-access ports)";
            } // END of tx-neighbor-solicitation-packet definition.

            leaf tx-neighbor-advertisement-packet  {
                type  yang:counter64;
                description "This Object describes ND Advertisement Transmitted Packets(Applicable
                            only for logical VxLAN-access ports)";
            } // END of tx-neighbor-advertisement-packet definition.

            leaf rx-gratuitous-arp-packets  {
                type  yang:counter64;
                description "This Object describes Gratuitous ARP  (Garp) Received
                            Packets(Applicable only for logical VxLAN-access ports)";
            } // END of rx-gratuitous-arp-packets definition.

            leaf tx-gratuitous-arp-packets  {
                type  yang:counter64;
                description "This Object describes Gratuitous ARP (Garp) Transmitted
                            Packets(Applicable only for logical VxLAN-access ports)";
            } // END of tx-gratuitous-arp-packets definition.

            leaf rx-gratuitous-na-packets  {
                type  yang:counter64;
                description "This Object describes Gratuitous NA (Gna) Received Packets(Applicable
                            only for logical VxLAN-access ports)";
            } // END of rx-gratuitous-na-packets definition.

            leaf tx-gratuitous-na-packets  {
                type  yang:counter64;
                description "This Object describes Gratuitous NA (Gna) Transmitted
                            Packets(Applicable only for logical VxLAN-access ports)";
            } // END of tx-gratuitous-na-packets definition.

            leaf rx-data-packets  {
                type  yang:counter64;
                description "This Object describes Received Data Packets(Applicable only for
                            logical VxLAN-access ports)";
            } // END of rx-data-packets definition.

            leaf rx-data-bytes  {
                type  yang:counter64;
                description "This Object describes Received bytes(Applicable only for logical
                            VxLAN-access ports)";
            } // END of rx-data-bytes definition.

            leaf tx-data-packets  {
                type  yang:counter64;
                description "This Object describes Transmitted Packets(Applicable only for logical
                            VxLAN-access ports)";
            } // END of tx-data-packets definition.

            leaf tx-data-bytes  {
                type  yang:counter64;
                description "This Object describes Transmitted Bytes(Applicable only for logical
                            VxLAN-access ports)";
            } // END of tx-data-bytes definition.

        } // END of access-counters-container definition.
    } // END of vxlan-access-port-counters-state definition.
    grouping vxlan-irb-top {
        description
            "Top level Grouping for Integrated Routing and Bridgin";
        container irb {
            description
                "Integrated Routing and Bridging container";
            container config {
                description
                    "Configuration data";
                uses vxlan-irb-config;
            } // END of config-container definition.
            container state {
                config false;
                description
                    "Operational state data";
                uses vxlan-irb-config;
            } // END of state-container definition.
        } // END of irb-container definition.
    } // END of vxlan-irb-top definition.
    grouping vxlan-qos-global-top {
        description
            "Top level Grouping for global vxlan qos";
        container qos-tunnel-mappings {
            description
                "QoS tunnel mapping list enclosing container";

            list qos-tunnel-mapping {
            when " /ipi-vxlan:vxlan/ipi-vxlan:global/ipi-vxlan:config/ipi-vxlan:enable-vxlan ";
                if-feature feature-list:HAVE_QOS;
                key "qos-map-mode traffic-direction";
                description
                    "VxLAN QoS configuration for mapping direction and profile";
                leaf qos-map-mode  {
                    type  leafref {
                        path  "../config/qos-map-mode";
                    }
                    description "Use this attribute to set VxLAN-QoS Map Mode for overlay dscp";
                } // END of qos-map-mode definition.

                leaf traffic-direction  {
                    type  leafref {
                        path  "../config/traffic-direction";
                    }
                    description "Use this attribute to set global direction(ingress/egress) for VxLAN.
                                Ingreess means traffic coming to network side and egress means traffic
                                going out from network side";
                } // END of traffic-direction definition.

                container config {
                    description
                        "Configuration data";
                    uses vxlan-qos-global-config;
                } // END of config-container definition.
                container state {
                    config false;
                    description
                        "Operational state data";
                    uses vxlan-qos-global-config;
                } // END of state-container definition.
            } // End of qos-tunnel-mapping-list
        } // END of qos-tunnel-mappings-container definition.
    } // END of vxlan-qos-global-top definition.
    grouping vxlan-tenant-top {
        description
            "Top-Level Grouping for VxLAN Tenant";
        container vxlan-tenants {
            description
                "VxLAN tenant list enclosing container";

            list vxlan-tenant {
            when " /ipi-vxlan:vxlan/ipi-vxlan:global/ipi-vxlan:config ";
                key "vxlan-identifier";
                unique "config/xconnect-identifier config/tenant-description config/irb-name";
                description
                    "Tenant related configurations";
                leaf vxlan-identifier  {
                    type  leafref {
                        path  "../config/vxlan-identifier";
                    }
                    description "Use this attribute to add a tenant and the type of VPN";
                } // END of vxlan-identifier definition.

                container config {
                    description
                        "Configuration data";
                    uses vxlan-tenant-global-config;
                    uses vxlan-tenant-config;
                } // END of config-container definition.
                container state {
                    config false;
                    description
                        "Operational state data";
                    uses vxlan-tenant-global-config;
                    uses vxlan-tenant-config;
                } // END of state-container definition.
                container route-count-info {
                    config false;
                    description
                        "Configuration data for VxLAN global capability configuration";
                    container state {
                        config false;
                        description
                            "Operational state data";
                        uses vxlan-tenant-route-count-state;
                    } // END of state-container definition.
                } // END of route-count-info-container definition.
                container xconnect-mapping-info {
                    if-feature feature-list:HAVE_EVPN_VPWS;
                    config false;
                    description
                        "This holds data for VXLAN xconnect mapping summary";
                    container state {
                        config false;
                        description
                            "Operational state data";
                        uses vxlan-tenant-xconnect-mapping-state;
                    } // END of state-container definition.
                } // END of xconnect-mapping-info-container definition.
                uses vxlan-irb-top;
                uses vxlan-static-tenant-list;
                uses vxlan-tenant-arp-cache-list;
                uses vxlan-tenant-nd-cache-list;
                uses vxlan-tenant-mac-table-list;
                uses vxlan-tenant-static-host-list;
                uses vxlan-tenant-static-host-ipv6-list;
            } // End of vxlan-tenant-list
        } // END of vxlan-tenants-container definition.
    } // END of vxlan-tenant-top definition.
    grouping vxlan-static-tenant-list {
        description
            "List grouping for static-vxlan-tenant configuration";
        container static-tenants {
            description
                "VxLAN static-tenant list enclosing container";

            list static-tenant {
            // when " ipi-vxlan:vxlan/vxlan-tenants/vxlan-tenant/static-tenants/static-tenant/config/remote-vtep-ipv4 ";
                key "mac-address";
                description
                    "static tenant related configurations";
                leaf mac-address  {
                    type  leafref {
                        path  "../config/mac-address";
                    }
                    description "Use this attribute to know MAC address of the host.create
                                a static route to reach a destination MAC in the VXLAN forwarding
                                table. This command helps to supports different tenants so that they
                                can have the same MAC/IP, but different VNIDs.This command is
                                required for unicast tunnels to map the remote VTEP";
                } // END of mac-address definition.

                container config {
                    description
                        "Configuration data";
                    uses vxlan-static-tenant-config;
                } // END of config-container definition.
                container state {
                    config false;
                    description
                        "Operational state data";
                    uses vxlan-static-tenant-config;
                } // END of state-container definition.
            } // End of static-tenant-list
        } // END of static-tenants-container definition.
    } // END of vxlan-static-tenant-list definition.
    grouping vxlan-tenant-arp-cache-list {
        description
            "Grouping for arp-cache information configuration";

        list arp-cache-info {
            key "host-ip";
            config false;
            description
                "arp-cache information list";
            leaf host-ip  {
                type  leafref {
                    path  "../state/host-ip";
                }
                description "Use this attribute to show Host IP address";
            } // END of host-ip definition.

            container state {
                config false;
                description
                    "Operational state data";
                uses vxlan-tenant-arp-cache-state;
            } // END of state-container definition.
        } // End of arp-cache-info-list
    } // END of vxlan-tenant-arp-cache-list definition.
    grouping vxlan-tenant-nd-cache-list {
        description
            "Grouping for nd-cache information display";

        list nd-cache-info {
            key "host-ip";
            config false;
            description
                "nd-cache information list";
            leaf host-ip  {
                type  leafref {
                    path  "../state/host-ip";
                }
                description "Use this attribute to show Host IP address";
            } // END of host-ip definition.

            container state {
                config false;
                description
                    "Operational state data";
                uses vxlan-tenant-nd-cache-state;
            } // END of state-container definition.
        } // End of nd-cache-info-list
    } // END of vxlan-tenant-nd-cache-list definition.
    grouping vxlan-tenant-mac-table-list {
        description
            "Grouping for mac table information display";

        list mac-table-info {
            key "mac-address";
            config false;
            description
                "mac table display information";
            leaf mac-address  {
                type  leafref {
                    path  "../state/mac-address";
                }
                description "MAC Adress of the host";
            } // END of mac-address definition.

            container state {
                config false;
                description
                    "Operational state data";
                uses vxlan-tenant-mac-table-state;
            } // END of state-container definition.
        } // End of mac-table-info-list
    } // END of vxlan-tenant-mac-table-list definition.
    grouping vxlan-tenant-static-host-list {
        description
            "Grouping for static host state display";

        list static-host-info {
            key "mac-address host-ipv4";
            config false;
            description
                "static host state display information";
            leaf mac-address  {
                type  leafref {
                    path  "../state/mac-address";
                }
                description "MAC Adress of the host";
            } // END of mac-address definition.

            leaf host-ipv4  {
                type  leafref {
                    path  "../state/host-ipv4";
                }
                description "Host IP Adress ipv4";
            } // END of host-ipv4 definition.

            container state {
                config false;
                description
                    "Operational state data";
                uses vxlan-tenant-static-host-state;
            } // END of state-container definition.
        } // End of static-host-info-list
    } // END of vxlan-tenant-static-host-list definition.
    grouping vxlan-tenant-static-host-ipv6-list {
        description
            "Grouping for static host-ipv6 state display";

        list static-host-ipv6-info {
            key "mac-address host-ipv6";
            config false;
            description
                "static host-ipv6 state display information";
            leaf mac-address  {
                type  leafref {
                    path  "../state/mac-address";
                }
                description "MAC Adress of the host";
            } // END of mac-address definition.

            leaf host-ipv6  {
                type  leafref {
                    path  "../state/host-ipv6";
                }
                description "Host IP Adress ipv6";
            } // END of host-ipv6 definition.

            container state {
                config false;
                description
                    "Operational state data";
                uses vxlan-tenant-static-host-ipv6-state;
            } // END of state-container definition.
        } // End of static-host-ipv6-info-list
    } // END of vxlan-tenant-static-host-ipv6-list definition.
    grouping vxlan-tunnel-top {
        description
            "Top-Level Grouping for VxLAN Tunnel";

        list tunnel {
            key "destination-vtep-ip";
            config false;
            description
                "tunnel related display information";
            leaf destination-vtep-ip  {
                type  leafref {
                    path  "../state/destination-vtep-ip";
                }
                description "Use this attribute to set Tunnel destination IP";
            } // END of destination-vtep-ip definition.

            container state {
                config false;
                description
                    "Operational state data";
                uses vxlan-tunnel-state;
                uses vxlan-tunnel-counters-state;
            } // END of state-container definition.
        } // End of tunnel-list
    } // END of vxlan-tunnel-top definition.
    grouping vxlan-access-port-default-config {
        description
            "Grouping for port only default config";
        leaf default-access-interface  {
            type  empty;
            description "Use this attribute to create default access interface";
        } // END of default-access-interface definition.

    } // END of vxlan-access-port-default-config definition.
    grouping vxlan-access-interface-top {
        description
            "Top-Level Grouping for VxLAN access interfaces";
        container untagged-access-interfaces {
            description
                "Enclosing container for untagged-access-interface list";

            list untagged-access-interface {
            when " /ipi-vxlan:vxlan/ipi-vxlan:global/ipi-vxlan:config and /ipi-interface:interfaces/ipi-interface:interface/ipi-interface:config/ipi-interface:enable-switchport ";
                if-feature feature-list:NOT_HAVE_DNX;
                key "untagged-interface-name";
                description
                    "untagged access port related configurations";
                leaf untagged-interface-name  {
                    type  leafref {
                        path  "../config/untagged-interface-name";
                    }
                    description "Use this attribute to map a physical interface to identify the tenant
                                traffic and to enter NVO access interface mode";
                } // END of untagged-interface-name definition.

                container config {
                    description
                        "Configuration data";
                    uses vxlan-access-port-default-config;
                    uses vxlan-access-interface-config;
                    uses vxlan-untagged-access-interface-config;
                } // END of config-container definition.
                container state {
                    config false;
                    description
                        "Operational state data";
                    uses vxlan-access-port-default-config;
                    uses vxlan-access-interface-config;
                    uses vxlan-untagged-access-interface-config;
                } // END of state-container definition.
                uses vxlan-untagged-access-interface-cache;
                uses vxlan-untagged-access-interface-map;
                uses vxlan-access-interface-port-only-mac-ipv4-list;
                uses vxlan-access-interface-port-only-mac-ipv6-list;
                uses vxlan-access-interface-qos-map-list;
            } // End of untagged-access-interface-list
        } // END of untagged-access-interfaces-container definition.
        container tagged-access-interfaces {
            description
                "Enclosing container for single tagged VxLAN access-port list";

            list tagged-access-interface {
            when " /ipi-vxlan:vxlan/ipi-vxlan:global/ipi-vxlan:config and /ipi-interface:interfaces/ipi-interface:interface/ipi-interface:config/ipi-interface:enable-switchport ";
                if-feature feature-list:NOT_HAVE_DNX;
                key "interface-name vlan-identifier";
                description
                    "single tagged VxLAN access-port related configurations";
                leaf interface-name  {
                    type  leafref {
                        path  "../config/interface-name";
                    }
                    description "Physical Port on which access-port is created";
                } // END of interface-name definition.

                leaf vlan-identifier  {
                    type  leafref {
                        path  "../config/vlan-identifier";
                    }
                    description "Use this attriute to map a VLAN on physical interface to identify the
                                tenant traffic and to enter NVO access interface mode";
                } // END of vlan-identifier definition.

                container config {
                    description
                        "Configuration data";
                    uses vxlan-access-port-vlan-config;
                    uses vxlan-access-encapsulation-config;
                    uses vxlan-access-interface-config;
                } // END of config-container definition.
                container state {
                    config false;
                    description
                        "Operational state data";
                    uses vxlan-access-port-vlan-config;
                    uses vxlan-access-encapsulation-config;
                    uses vxlan-access-interface-config;
                } // END of state-container definition.
                uses vxlan-tagged-access-interface-cache;
                uses vxlan-tagged-access-interface-map;
                uses vxlan-access-interface-port-vlan-mac-ipv4-list;
                uses vxlan-access-interface-port-vlan-mac-ipv6-list;
                uses vxlan-access-interface-qos-map-list;
            } // End of tagged-access-interface-list
        } // END of tagged-access-interfaces-container definition.
        container double-tagged-access-interfaces {
            description
                "Enclosing container for double tagged access port list";

            list double-tagged-access-interface {
            when " /ipi-vxlan:vxlan/ipi-vxlan:global/ipi-vxlan:config and /ipi-interface:interfaces/ipi-interface:interface/ipi-interface:config/ipi-interface:enable-switchport ";
                if-feature feature-list:NOT_HAVE_DNX;
                key "interface-name vlan-identifier inner-vlan-identifier";
                description
                    "double tagged access port related configurations";
                leaf interface-name  {
                    type  leafref {
                        path  "../config/interface-name";
                    }
                    description "Physical Port on which access-port is created";
                } // END of interface-name definition.

                leaf vlan-identifier  {
                    type  leafref {
                        path  "../config/vlan-identifier";
                    }
                    description "S-VLAN on which interface is mapped";
                } // END of vlan-identifier definition.

                leaf inner-vlan-identifier  {
                    type  leafref {
                        path  "../config/inner-vlan-identifier";
                    }
                    description "Use this attriute to map VLAN'S on an interface to identify the tenant
                                traffic and to enter NVO access interface mode";
                } // END of inner-vlan-identifier definition.

                container config {
                    description
                        "Configuration data";
                    uses vxlan-access-port-stacked-vlan-config;
                    uses vxlan-access-encapsulation-config;
                    uses vxlan-access-interface-config;
                } // END of config-container definition.
                container state {
                    config false;
                    description
                        "Operational state data";
                    uses vxlan-access-port-stacked-vlan-config;
                    uses vxlan-access-encapsulation-config;
                    uses vxlan-access-interface-config;
                } // END of state-container definition.
                uses vxlan-double-tagged-access-interface-map;
                uses vxlan-double-tagged-access-interface-cache;
                uses vxlan-access-interface-port-stacked-vlan-mac-ipv4-list;
                uses vxlan-access-interface-port-stacked-vlan-mac-ipv6-list;
                uses vxlan-access-interface-qos-map-list;
            } // End of double-tagged-access-interface-list
        } // END of double-tagged-access-interfaces-container definition.
    } // END of vxlan-access-interface-top definition.
    grouping vxlan-access-interface-map-config {
        description
            "Grouping for VxLAN map identifier attributes";
        leaf vxlan-identifier  {
            type  leafref {
                path  "/vxlan/vxlan-tenants/vxlan-tenant/config/vxlan-identifier";
            }
            description "Use this attribute to map a tenant to an access-port";
        } // END of vxlan-identifier definition.

        leaf tenant-description  {
            type  leafref {
                path  "/vxlan/vxlan-tenants/vxlan-tenant/config/tenant-description";
            }
            description "Use this attribute to map VXLAN Identifier Name";
        } // END of tenant-description definition.

    } // END of vxlan-access-interface-map-config definition.
    grouping vxlan-untagged-access-interface-map {
        description
            "Grouping for map of VxLAN identifier configuration for untagged access
                        interfaces";
        container map {
            description
                "VxLAN map identifier container";
            container config {
                description
                    "Configuration data for VxLAN identifier";
                uses vxlan-access-interface-map-config;
            } // END of config-container definition.
            container state {
                config false;
                description
                    "Operational state data for VxLAN identifier";
                uses vxlan-access-interface-map-config;
            } // END of state-container definition.
        } // END of map-container definition.
    } // END of vxlan-untagged-access-interface-map definition.
    grouping vxlan-tagged-access-interface-map {
        description
            "Grouping for map of VxLAN identifier configuration for tagged access
                        interfaces";
        container map {
            description
                "VxLAN map identifier container";
            container config {
                description
                    "Configuration data for VxLAN identifier";
                uses vxlan-access-interface-map-config;
            } // END of config-container definition.
            container state {
                config false;
                description
                    "Operational state data for VxLAN identifier";
                uses vxlan-access-interface-map-config;
            } // END of state-container definition.
        } // END of map-container definition.
    } // END of vxlan-tagged-access-interface-map definition.
    grouping vxlan-double-tagged-access-interface-map {
        description
            "Grouping for map of VxLAN identifier configuration for double tagged
                        access interfaces";
        container map {
            description
                "VxLAN map identifier container";
            container config {
                description
                    "Configuration data for VxLAN identifier";
                uses vxlan-access-interface-map-config;
            } // END of config-container definition.
            container state {
                config false;
                description
                    "Operational state data for VxLAN identifier";
                uses vxlan-access-interface-map-config;
            } // END of state-container definition.
        } // END of map-container definition.
    } // END of vxlan-double-tagged-access-interface-map definition.
    grouping vxlan-access-interface-port-only-mac-ipv4-list {
        description
            "Grouping for mac-ipv4 configuration for untagged access port";
        container host-macs-ipv4 {
            description
                "Enclosing container for untagged access side host MAC IPv4 list";

            list host-mac-ipv4 {
                if-feature feature-list:NOT_HAVE_DNX;
                key "mac-address ipv4-address";
                description
                    "untagged access side host related configurations";
                leaf mac-address  {
                    type  leafref {
                        path  "../config/mac-address";
                    }
                    description "Use this attribute to know MAC address of the host";
                } // END of mac-address definition.

                leaf ipv4-address  {
                    type  leafref {
                        path  "../config/ipv4-address";
                    }
                    description "USe this attribute to associate a static MAC address and a static IPv4
                                or IPv6 address on an access interface.";
                } // END of ipv4-address definition.

                container config {
                    description
                        "Configuration data";
                    uses vxlan-access-mac-ipv4-config;
                } // END of config-container definition.
                container state {
                    config false;
                    description
                        "Operational state data";
                    uses vxlan-access-mac-ipv4-config;
                } // END of state-container definition.
            } // End of host-mac-ipv4-list
        } // END of host-macs-ipv4-container definition.
    } // END of vxlan-access-interface-port-only-mac-ipv4-list definition.
    grouping vxlan-access-interface-qos-map-list {
        description
            "Grouping for mapping qos profile  configuration for untagged access
                        port";
        container access-interface-qos-type-mappings {
            description
                "Enclosing container for untagged access side QoS map list";

            list access-interface-qos-type-mapping {
            when " /ipi-qos:qos/ipi-qos:global/ipi-qos:config/ipi-qos:enable-qos = 'enable' ";
                if-feature feature-list:HAVE_QOS;
                key "profile-map-type";
                description
                    "untagged access side QoS map related configurations";
                leaf profile-map-type  {
                    type  leafref {
                        path  "../config/profile-map-type";
                    }
                    description "Use this attribute to map the profile type for which qos profile is
                                already created globally to access port";
                } // END of profile-map-type definition.

                container config {
                    description
                        "Configuration data";
                    uses vxlan-access-interface-qos-type-mapping-config;
                } // END of config-container definition.
                container state {
                    config false;
                    description
                        "Operational state data";
                    uses vxlan-access-interface-qos-type-mapping-config;
                } // END of state-container definition.
            } // End of access-interface-qos-type-mapping-list
        } // END of access-interface-qos-type-mappings-container definition.
    } // END of vxlan-access-interface-qos-map-list definition.
    grouping vxlan-access-interface-port-vlan-mac-ipv4-list {
        description
            "Grouping for mac-ipv4 configuration for single tagged access port";
        container host-macs-ipv4 {
            description
                "Enclosing container for single tagged access side host MAC IPv4 list";

            list host-mac-ipv4 {
                key "mac-address ipv4-address";
                description
                    "single tagged access side host related configurations";
                leaf mac-address  {
                    type  leafref {
                        path  "../config/mac-address";
                    }
                    description "Use this attribute to know MAC address of the host";
                } // END of mac-address definition.

                leaf ipv4-address  {
                    type  leafref {
                        path  "../config/ipv4-address";
                    }
                    description "IPv4 Address of host connected to vxlan access port";
                } // END of ipv4-address definition.

                container config {
                    description
                        "Configuration data";
                    uses vxlan-access-mac-ipv4-config;
                } // END of config-container definition.
                container state {
                    config false;
                    description
                        "Operational state data";
                    uses vxlan-access-mac-ipv4-config;
                } // END of state-container definition.
            } // End of host-mac-ipv4-list
        } // END of host-macs-ipv4-container definition.
    } // END of vxlan-access-interface-port-vlan-mac-ipv4-list definition.
    grouping vxlan-access-interface-port-stacked-vlan-mac-ipv4-list {
        description
            "Grouping for mac-ipv4 configuration for double tagged access port";
        container host-macs-ipv4 {
            description
                "Enclosing container for double tagged access side host MAC IPv4 list";

            list host-mac-ipv4 {
                if-feature feature-list:NOT_HAVE_DNX;
                key "mac-address ipv4-address";
                description
                    "double tagged access side host related configurations";
                leaf mac-address  {
                    type  leafref {
                        path  "../config/mac-address";
                    }
                    description "Use this attribute to know MAC address of the host";
                } // END of mac-address definition.

                leaf ipv4-address  {
                    type  leafref {
                        path  "../config/ipv4-address";
                    }
                    description "USe this attribute to associate a static MAC address and a static IPv4
                                or IPv6 address on an access interface.";
                } // END of ipv4-address definition.

                container config {
                    description
                        "Configuration data";
                    uses vxlan-access-mac-ipv4-config;
                } // END of config-container definition.
                container state {
                    config false;
                    description
                        "Operational state data";
                    uses vxlan-access-mac-ipv4-config;
                } // END of state-container definition.
            } // End of host-mac-ipv4-list
        } // END of host-macs-ipv4-container definition.
    } // END of vxlan-access-interface-port-stacked-vlan-mac-ipv4-list definition.
    grouping vxlan-access-interface-port-only-mac-ipv6-list {
        description
            "Grouping for mac-ipv6 configuration for untagged access port";
        container host-macs-ipv6 {
            description
                "Enclosing container for untagged access side host MAC IPv6 list";

            list host-mac-ipv6 {
                if-feature feature-list:HAVE_IPV6;
                if-feature feature-list:NOT_HAVE_DNX;
                key "mac-address ipv6-address";
                description
                    "untagged access side host related configurations";
                leaf mac-address  {
                    type  leafref {
                        path  "../config/mac-address";
                    }
                    description "Use this attribute to know MAC address of the host";
                } // END of mac-address definition.

                leaf ipv6-address  {
                    type  leafref {
                        path  "../config/ipv6-address";
                    }
                    description "USe this attribute to associate a static MAC address and a static IPv4
                                or IPv6 address on an access interface.";
                } // END of ipv6-address definition.

                container config {
                    description
                        "Configuration data";
                    uses vxlan-access-mac-ipv6-config;
                } // END of config-container definition.
                container state {
                    config false;
                    description
                        "Operational state data";
                    uses vxlan-access-mac-ipv6-config;
                } // END of state-container definition.
            } // End of host-mac-ipv6-list
        } // END of host-macs-ipv6-container definition.
    } // END of vxlan-access-interface-port-only-mac-ipv6-list definition.
    grouping vxlan-access-interface-port-vlan-mac-ipv6-list {
        description
            "Grouping for mac-ipv6 configuration for single tagged access port";
        container host-macs-ipv6 {
            description
                "Enclosing container for single tagged access side host MAC IPv6 list";

            list host-mac-ipv6 {
                if-feature feature-list:HAVE_IPV6;
                key "mac-address ipv6-address";
                description
                    "single tagged access side host related configurations";
                leaf mac-address  {
                    type  leafref {
                        path  "../config/mac-address";
                    }
                    description "Use this attribute to know MAC address of the host";
                } // END of mac-address definition.

                leaf ipv6-address  {
                    type  leafref {
                        path  "../config/ipv6-address";
                    }
                    description "USe this attribute to associate a static MAC address and a static IPv4
                                or IPv6 address on an access interface.";
                } // END of ipv6-address definition.

                container config {
                    description
                        "Configuration data";
                    uses vxlan-access-mac-ipv6-config;
                } // END of config-container definition.
                container state {
                    config false;
                    description
                        "Operational state data";
                    uses vxlan-access-mac-ipv6-config;
                } // END of state-container definition.
            } // End of host-mac-ipv6-list
        } // END of host-macs-ipv6-container definition.
    } // END of vxlan-access-interface-port-vlan-mac-ipv6-list definition.
    grouping vxlan-access-interface-port-stacked-vlan-mac-ipv6-list {
        description
            "Grouping for mac-ipv6 configuration for double tagged access port";
        container host-macs-ipv6 {
            description
                "Enclosing container for double tagged access side host MAC IPv6 list";

            list host-mac-ipv6 {
                if-feature feature-list:HAVE_IPV6;
                key "mac-address ipv6-address";
                description
                    "double tagged access side host related configurations";
                leaf mac-address  {
                    type  leafref {
                        path  "../config/mac-address";
                    }
                    description "Use this attribute to know MAC address of the host";
                } // END of mac-address definition.

                leaf ipv6-address  {
                    type  leafref {
                        path  "../config/ipv6-address";
                    }
                    description "USe this attribute to associate a static MAC address and a static IPv4
                                or IPv6 address on an access interface.";
                } // END of ipv6-address definition.

                container config {
                    description
                        "Configuration data";
                    uses vxlan-access-mac-ipv6-config;
                } // END of config-container definition.
                container state {
                    config false;
                    description
                        "Operational state data";
                    uses vxlan-access-mac-ipv6-config;
                } // END of state-container definition.
            } // End of host-mac-ipv6-list
        } // END of host-macs-ipv6-container definition.
    } // END of vxlan-access-interface-port-stacked-vlan-mac-ipv6-list definition.
    grouping vxlan-access-interface-counters-top {
        description
            "Top-Level Grouping for VxLAN access interfaces counters";
        container access-interfaces {
            config false;
            description
                "access-interfaces container";

            list access-interface {
                key "interface-index";
                config false;
                description
                    "access port counters list";
                leaf interface-index  {
                    type  leafref {
                        path  "../state/interface-index";
                    }
                    description "Use this attribute to fetch nvo access port counters";
                } // END of interface-index definition.

                container state {
                    config false;
                    description
                        "Operational state data";
                    uses vxlan-access-port-counters-state;
                } // END of state-container definition.
            } // End of access-interface-list
        } // END of access-interfaces-container definition.
    } // END of vxlan-access-interface-counters-top definition.
    grouping vtep-entries-config {
        description
            "VTEP locally configured details";
        leaf address  {
            type  inet:ipv4-address;
            description "VTEP ip address";
        } // END of address definition.

        leaf description  {
            type  cml-data-types:cml_line_t {
                length "1..128";
            }
            description "VTEP description";
        } // END of description definition.

        leaf redund-type  {
            type  ipi-vxlan-types:vxlan_vtep_redund_type_t;
            description "VTEP redundancy type";
        } // END of redund-type definition.

    } // END of vtep-entries-config definition.
    grouping vtep-entries-top {
        description
            "Top level grouping for vtep info";
        container vtep-entries {
            description
                "Top level container for vtep-entries";

            list vtep-entry {
            when " /ipi-vxlan:vxlan/ipi-vxlan:global/ipi-vxlan:config ";
                key "address";
                description
                    "VTEP locally configured details";
                leaf address  {
                    type  leafref {
                        path  "../config/address";
                    }
                    description "VTEP ip address";
                } // END of address definition.

                container config {
                    description
                        "Config container";
                    uses vtep-entries-config;
                } // END of config-container definition.
                container state {
                    config false;
                    description
                        "Operational state data";
                    uses vtep-entries-config;
                } // END of state-container definition.
            } // End of vtep-entry-list
        } // END of vtep-entries-container definition.
    } // END of vtep-entries-top definition.
    grouping vxlan-access-if-config {
        description
            "VXLAN access-if details";
        leaf name  {
            type  leafref {
                path  "/ipi-interface:interfaces/ipi-interface:interface/ipi-interface:name";
            }
            description "Use this attribute to map a physical interface to create VXLAN logical
                        access port";
        } // END of name definition.

        leaf access-if  {
            if-feature feature-list:HAVE_XGS5;
            if-feature feature-list:NOT_HAVE_DUNE;
            type  empty;
            description "VXLAN logical access port per physical interface";
        } // END of access-if definition.

        leaf arp-cache  {
            if-feature feature-list:NOT_HAVE_DUNE;
            type  empty;
            description "Use this attribute to set the ARP cache in interface";
        } // END of arp-cache definition.

        leaf nd-cache  {
            if-feature feature-list:NOT_HAVE_DUNE;
            type  empty;
            description "Use this attribute to set the ND cache in interface";
        } // END of nd-cache definition.

    } // END of vxlan-access-if-config definition.
    grouping vxlan-access-if-top {
        description
            "Top level grouping for VXLAN access-if";
        container interfaces {
            description
                "Top level container for VXLAN access-if";

            list interface {
            when " /ipi-vxlan:vxlan/ipi-vxlan:global/ipi-vxlan:config/ipi-vxlan:enable-vxlan and /ipi-interface:interfaces/ipi-interface:interface/ipi-interface:config/ipi-interface:enable-switchport ";
                key "name";
                description
                    "VXLAN access port related configurations";
                leaf name  {
                    type  leafref {
                        path  "../config/name";
                    }
                    description "Use this attribute to map a physical interface to create VXLAN logical
                                access port";
                } // END of name definition.

                container config {
                    description
                        "Configuration data for VXLAN access-if";
                    uses vxlan-access-if-config;
                } // END of config-container definition.
                container state {
                    config false;
                    description
                        "Operational state data for VXLAN access-if";
                    uses vxlan-access-if-config;
                } // END of state-container definition.
            } // End of interface-list
        } // END of interfaces-container definition.
    } // END of vxlan-access-if-top definition.

    grouping  vxlan-grouping {
    description
        "VxLAN global level container";
    container vxlan {
        if-feature feature-list:HAVE_VXLAN;
        description
            "VxLAN global level container";
        container global {
            // when " ipi-vxlan:vxlan/global/config/enable-vxlan == '1' ";
            description
                "Configuration data for VxLAN global capability configuration";
            container config {
                presence "Enable EVPN-VxLAN";
                description
                    "Configuration data";
                uses vxlan-global-config;
            } // END of config-container definition.
            container state {
                config false;
                description
                    "Operational state data";
                uses vxlan-global-config;
            } // END of state-container definition.
        } // END of global-container definition.
        uses vxlan-qos-global-top;
        uses vxlan-tenant-top;
        uses vxlan-tunnel-top;
        uses vxlan-access-interface-top;
        uses vxlan-access-interface-counters-top;
        uses vtep-entries-top;
        uses vxlan-access-if-top;
    } // END of vxlan-container definition.
    } // END of vxlan-grouping definition.

    uses vxlan-grouping;

    rpc clear-nvo-vxlan-dynamic-mac-address-table {
        if-feature feature-list:HAVE_VXLAN;
        description "Use this RPC to clear the dynamic entries from mac address table";
    }

    rpc clear-nvo-vxlan-dynamic-mac-address-table-vnid {
        if-feature feature-list:HAVE_VXLAN;
        description "Use this RPC to clear the dynamic entries from mac address table with
                    vnid or vnid+mac";
        input  {
            leaf vxlan-identifier  {
                type uint32 {
                    range "1..16777215";
                }
                mandatory true;
                description "Use this attribute to include vxlan identifier";
            }
            leaf mac-address  {
                type cml-data-types:cml_mac_addr_t;
                description "Interface MAC address";
            }
        }
    }

    rpc clear-nvo-vxlan-tunnels {
        if-feature feature-list:HAVE_VXLAN;
        description "Use this RPC to clear all the nvo vxlan tunnels";
    }

    rpc clear-nvo-id-vxlan-tunnels-destip {
        if-feature feature-list:HAVE_VXLAN;
        description "Use this RPC to clear the nvo vxlan tunnels dest ip";
        input  {
            leaf destination-vtep-ip  {
                type inet:ipv4-address;
                mandatory true;
                description "Use this attribute to include Tunnel destination IP";
            }
        }
    }

    rpc clear-nvo-vxlan-mac-stale-entries {
        if-feature feature-list:HAVE_VXLAN;
        description "Use this RPC to clear the vxlan mac stale entries";
        input  {
            leaf vxlan-identifier  {
                type uint32 {
                    range "1..16777215";
                }
                description "Use this attribute to include a tenant and the type of VPN";
            }
        }
    }

    rpc clear-vxlan-untagged-access-port-counters {
        if-feature feature-list:HAVE_VXLAN;
        description "Use this RP to clear the counters of untagged access port";
        input  {
            leaf interface-name  {
                type string;
                mandatory true;
                description "interface name";
            }
        }
    }

    rpc clear-vxlan-single-tagged-access-port-counters {
        if-feature feature-list:NOT_HAVE_DNX;
        if-feature feature-list:HAVE_VXLAN;
        description "Use this RPC to clear the counters of single tagged port counters";
        input  {
            leaf interface-name  {
                type string;
                mandatory true;
                description "interface name";
            }
            leaf vlan-identifier  {
                type string;
                mandatory true;
                description "S-VLAN on which interface is mapped";
            }
        }
    }

    rpc clear-vxlan-double-tagged-access-port-counters {
        if-feature feature-list:NOT_HAVE_DNX;
        if-feature feature-list:HAVE_VXLAN;
        description "Use this RPC to clear the counters of double tagged port";
        input  {
            leaf interface-name  {
                type string;
                mandatory true;
                description "interface name";
            }
            leaf outer-vlan-identifier  {
                type uint32 {
                    range "2..4094";
                }
                mandatory true;
                description "Outer vlan on which interface mapped";
            }
            leaf inner-vlan-identifier  {
                type uint32 {
                    range "2..4094";
                }
                mandatory true;
                description "Inner vlan on which interface mapped";
            }
        }
    }

    rpc clear-vxlan-access-port-counters-all {
        if-feature feature-list:HAVE_VXLAN;
        description "Use this RPC to clear the all the access port counters";
    }

    rpc clear-vxlan-network-port-counters {
        if-feature feature-list:HAVE_VXLAN;
        description "Use this RPC to clear the network port counters";
        input  {
            leaf destination-vtep-ip  {
                type inet:ipv4-address;
                mandatory true;
                description "Use this attribute to include Tunnel destination IP";
            }
        }
    }

    rpc clear-vxlan-network-port-counters-all {
        if-feature feature-list:HAVE_VXLAN;
        description "Use this RPC to clear all the network port counters";
    }

    notification vxlan-tunnel-status-change-notification {
        if-feature feature-list:HAVE_VXLAN;

        description "The nvoTunnelStatus trap is generated when there is any status change in Tunnel Severity level is INFO for tunnel status going to Unresolved/Deleted status and MINOR for Resolved status..";

        leaf severity {
            type cml-data-types:cml_notif_severity_t;
            description "Notification severity level";
        }

        leaf eventClass {
            type cml-data-types:cml_notif_class_t;
            description "Notification event class (value: STATE)";
        }

        leaf destination-vtep-ip {
            type  inet:ipv4-address;
        description
            "Use this attribute to set Tunnel destination IP";
        }

        leaf tunnel-status {
            type ipi-vxlan-types:vxlan_tunnel_status_t;
        description
            "Use this attribute to see the Status of tunnel";
        }
    }

}
