/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-prefix-group-types.yang
*
*/

module ipi-prefix-group-types {

    yang-version 1.1;

    namespace   "http://www.ipinfusion.com/yang/ocnos/ipi-prefix-group-types";

    prefix "ipi-prefix-group-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-prefix-group-types";


    revision "2025-03-20" {
        description "Removed the data-type which are not used";
        reference " 0.1.1.";
    }

    revision "2025-03-05" {
        description "Initial Version";
        reference " 0.1.0.";
    }



    typedef  prefix_group_type_t {
        type enumeration {
            enum ip {
                value 1;
                description "Prefix-group type IPv4";
            }
            enum ipv6 {
                value 2;
                description "Prefix-group type IPv6";
            }
        }
        description "type definition for PREFIX_GROUP_TYPE_T";
    }

}
