/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-prefix-group.yang
*
*/

module ipi-prefix-group {

    yang-version 1.1;

    namespace   "http://www.ipinfusion.com/yang/ocnos/ipi-prefix-group";

    prefix "ipi-prefix-group";

    import cml-data-types {
        prefix cml-data-types;
        revision-date 2026-05-15;
    }

    import ipi-prefix-group-types {
        prefix ipi-prefix-group-types;
        revision-date 2025-03-20;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-prefix-group";


    revision "2025-04-18" {
        description "Added missing api header";
        reference " 0.1.7.";
    }

    revision "2025-04-15" {
        description "Add the same pattern to store the prefixes for IPv4 and IPv6 entries";
        reference " 0.1.6.";
    }

    revision "2025-04-08" {
        description "Included additional smi modules and dependencies to CoPP access-list";
        reference " 0.1.5.";
    }

    revision "2025-04-07" {
        description "Support for dynamic entry match-xpath to static entry in same transaction";
        reference " 0.1.4.";
    }

    revision "2025-03-26" {
        description "Added a maximum limit to the entries in the prefix-group list";
        reference " 0.1.3.";
    }

    revision "2025-03-25" {
        description "Added state leaf-list to the prefix entries";
        reference " 0.1.2.";
    }

    revision "2025-03-20" {
        description "Added the support for match-xpath Entry";
        reference " 0.1.1.";
    }

    revision "2025-03-05" {
        description "Initial Version";
        reference " 0.1.0.";
    }

    grouping prefix-group-ipv6-entries-state {
        description
            "Grouping for IPv6 prefix-group entries state attributes";
        leaf-list ipv6-prefixes  {
            type  cml-data-types:cml_ipv6_prefix_t;
            description "This attribute displays all (dynamic or static) IPv6 prefixes added to
                        the prefix-group.";
        } // END of ipv6-prefixes definition.

    } // END of prefix-group-ipv6-entries-state definition.
    grouping prefix-group-ipv6-entries-config {
        description
            "Grouping for IPv6 prefix-group entries configuration attributes";
        leaf-list ipv6-entry  {
            // when " not(../ipv6-match-xpath-entry) ";
            type  cml-data-types:cml_ipv6_prefix_t;
            description "Use this attribute to set the IPv6 prefix value.";
        } // END of ipv6-entry definition.

        leaf ipv6-match-xpath-entry  {
            // when " not(../ipv6-entry) ";
            type  string {
                length "1..1965";
                pattern "[^?]+";
            }
            description "Use this attribute to dynamically set an IPv6 prefix value using XPath";
        } // END of ipv6-match-xpath-entry definition.

    } // END of prefix-group-ipv6-entries-config definition.
    grouping prefix-group-ipv6-entries-top {
        description
            "Top Level grouping for IPv6 prefix-group entries";
        container ipv6-entries {
            if-feature feature-list:HAVE_IPV6;
            description
                "Prefix groups entries";
            container config {
                // when " ../../type='ipv6' ";
                description
                    "Configuration data for IPv6 prefix-group entries";
                uses prefix-group-ipv6-entries-config;
            } // END of config-container definition.
            container state {
                config false;
                description
                    "Operational state data for IPv6 prefix-group entries";
                uses prefix-group-ipv6-entries-config;
                uses prefix-group-ipv6-entries-state;
            } // END of state-container definition.
        } // END of ipv6-entries-container definition.
    } // END of prefix-group-ipv6-entries-top definition.
    grouping prefix-group-ipv4-entries-state {
        description
            "Grouping for IPv4 prefix-group entries state attributes";
        leaf-list ipv4-prefixes  {
            type  cml-data-types:cml_ipv4_addr_prefix_t;
            description "This attribute displays all (dynamic or static) IPv4 prefixes added to
                        the prefix-group.";
        } // END of ipv4-prefixes definition.

    } // END of prefix-group-ipv4-entries-state definition.
    grouping prefix-group-ipv4-entries-config {
        description
            "Grouping for IPv4 prefix-group entries configuration attributes";
        leaf-list ipv4-entry  {
            // when " not(../ipv4-match-xpath-entry) ";
            type  cml-data-types:cml_ipv4_addr_prefix_t;
            description "Use this attribute to set the IPv4 prefix value.";
        } // END of ipv4-entry definition.

        leaf ipv4-match-xpath-entry  {
            // when " not(../ipv4-entry) ";
            type  string {
                length "1..1965";
                pattern "[^?]+";
            }
            description "Use this attribute to dynamically set an IPv4 prefix value using XPath";
        } // END of ipv4-match-xpath-entry definition.

    } // END of prefix-group-ipv4-entries-config definition.
    grouping prefix-group-ipv4-entries-top {
        description
            "Top Level grouping for IPv4 prefix-group entries";
        container ipv4-entries {
            description
                "Prefix groups entries";
            container config {
                // when " ../../type='ip' ";
                description
                    "Configuration data for IPv4 prefix-group entries";
                uses prefix-group-ipv4-entries-config;
            } // END of config-container definition.
            container state {
                config false;
                description
                    "Operational state data for IPv4 prefix-group entries";
                uses prefix-group-ipv4-entries-config;
                uses prefix-group-ipv4-entries-state;
            } // END of state-container definition.
        } // END of ipv4-entries-container definition.
    } // END of prefix-group-ipv4-entries-top definition.
    grouping prefix-group-config {
        description
            "Grouping for prefix-group configuration attributes";
        leaf type  {
            type  ipi-prefix-group-types:prefix_group_type_t;
            description "Use this attribute to set the prefix-group type: IPv4 or IPv6.";
        } // END of type definition.

        leaf name  {
            type  string {
                length "1..64";
                pattern "[a-zA-Z0-9][^?' =,>|]*";
            }
            description "Use this attribute to set the prefix-group name.";
        } // END of name definition.

        leaf description  {
            type  cml-data-types:cml_line_t {
                length "1..80";
            }
            description "Use this attribute to set a description to the prefix-group.";
        } // END of description definition.

    } // END of prefix-group-config definition.
    grouping prefix-group-top {
        description
            "Top level grouping for prefix-group configuration";

        list prefix-group {
            key "type name";
            max-elements 1024;
            description
                "Prefix Groups list";
            leaf type  {
                type  leafref {
                    path  "../config/type";
                }
                description "Use this attribute to set the prefix-group type: IPv4 or IPv6.";
            } // END of type definition.

            leaf name  {
                type  leafref {
                    path  "../config/name";
                }
                description "Use this attribute to set the prefix-group name.";
            } // END of name definition.

            container config {
                description
                    "Configuration data for prefix-group";
                uses prefix-group-config;
            } // END of config-container definition.
            container state {
                config false;
                description
                    "Operational state data for prefix-group";
                uses prefix-group-config;
            } // END of state-container definition.
            uses prefix-group-ipv4-entries-top;
            uses prefix-group-ipv6-entries-top;
        } // End of prefix-group-list
    } // END of prefix-group-top definition.

    grouping  prefix-groups-grouping {
    description
        "Top level container for prefix-group config and operational state data";
    container prefix-groups {
        description
            "Top level container for prefix-group config and operational state data";
        uses prefix-group-top;
    } // END of prefix-groups-container definition.
    } // END of prefix-groups-grouping definition.

    uses prefix-groups-grouping;

}
