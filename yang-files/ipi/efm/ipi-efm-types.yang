/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-efm-types.yang
*
*/

module ipi-efm-types {

    yang-version 1.1;

    namespace   "http://www.ipinfusion.com/yang/ocnos/ipi-efm-types";

    prefix "ipi-efm-types";

    organization
        "IP Infusion Inc.";

    contact
        "Address: 3965 Freedom Circle, Suite 200, Santa Clara, CA 95054
         Phone: +1 408-400-1900
         E-mail: support@ipinfusion.com
         Web: http://www.ipinfusion.com/";

    description
        "Ethernet OAM(EFM) data types";


    revision "2023-03-20" {
        description "Added datatype for ETHERNET_OAM_REMOTE_FAILURE_EVENTS_T";
        reference " 0.4.0.";
    }

    revision "2022-08-10" {
        description "Debug hierarchy change";
        reference " 0.3.0.";
    }

    revision "2022-06-01" {
        description "Updated the yang file with feature";
        reference " 0.2.0.";
    }

    revision "2020-07-27" {
        description "Initial version";
        reference " 0.1.0.";
    }



    typedef  ethernet_oam_mode_t {
        type enumeration {
            enum active {
                value 1;
                description "Active Mode";
            }
            enum passive {
                value 2;
                description "Passive Mode";
            }
        }
        description "type definition for ETHERNET_OAM_MODE_T";
    }

    typedef  ethernet_oam_debug_t {
        type bits {
            bit event {
                position 0;
                description "Event debugs";
            }
            bit rx {
                position 1;
                description "OAMPDU receive debugs";
            }
            bit tx {
                position 2;
                description "OAMPDU transmit debugs";
            }
        }
        description "This is the Ethernet OAM DEBUG type";
    }

    typedef  ethernet_oam_remote_failure_events_t {
        type bits {
            bit dying-gasp {
                position 0;
                description "EFM dying gasp events";
            }
            bit link-fault {
                position 1;
                description "EFM link fault events";
            }
            bit critical-event {
                position 2;
                description "EFM Critical events";
            }
        }
        description "type definition for ETHERNET_OAM_REMOTE_FAILURE_EVENTS_T";
    }

    typedef  ethernet_oam_oper_status_t {
        type enumeration {
            enum disabled {
                value 1;
                description "Ethernet OAM disabled";
            }
            enum link-fault {
                value 2;
                description "Ethernet OAM faulty Link";
            }
            enum passive-wait {
                value 3;
                description "Ethernet OAM passive wait";
            }
            enum active-send-local {
                value 4;
                description "Ethernet OAM local active send";
            }
            enum send-local-remote {
                value 5;
                description "Ethernet OAM local send to remote";
            }
            enum send-local-remote-ok {
                value 6;
                description "Ethernet OAM local send to remote ok";
            }
            enum peering-locally-rejected {
                value 7;
                description "Ethernet OAM peering locally rejected";
            }
            enum peering-remotely-rejected {
                value 8;
                description "Ethernet OAM peering remotely rejected";
            }
            enum operational {
                value 9;
                description "Ethernet OAM is operational";
            }
            enum non-operational-half-duplex {
                value 10;
                description "Ethernet OAM non operational half duplex";
            }
        }
        description "type definition for ETHERNET_OAM_OPER_STATUS_T";
    }

}
