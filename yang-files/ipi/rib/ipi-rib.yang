/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-rib.yang
*
*/

module ipi-rib {

    yang-version 1.1;

    namespace   "http://www.ipinfusion.com/yang/ocnos/ipi-rib";

    prefix "ipi-rib";

    import cml-data-types {
        prefix cml-data-types;
        revision-date 2026-05-15;
    }

    import ipi-rib-types {
        prefix ipi-rib-types;
        revision-date 2025-02-07;
    }

    import ipi-interface {
        prefix ipi-interface;
        revision-date 2026-03-10;
    }

    import ipi-network-instance {
        prefix ipi-network-instance;
        revision-date 2026-08-12;
    }

    import ipi-rib-common {
        prefix ipi-rib-common;
        revision-date 2025-12-01;
    }

    import ietf-inet-types {
        prefix inet;
        revision-date 2013-07-15;
    }

    import ietf-yang-types {
        prefix yang;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for RIB object";


    revision "2025-12-01" {
        description "Add CML_SKIP_HITLESS_MERGE flag to enable-global-table-lookup attribute.";
        reference " 1.3.1.";
    }

    revision "2025-10-30" {
        description "Changed flag for enable-global-table-lookup attribute to delete-on-no-child";
        reference " 1.2.6.";
    }

    revision "2025-09-22" {
        description "Added xPath for distance attribute in next-hop-gateway objectlist for IPv4/IPv6 static routes";
        reference " 1.2.5.";
    }

    revision "2025-09-18" {
        description "Reverted the changes for XPath in next-hop-gateway objectlist for IPv4/IPv6 static routes";
        reference " 1.2.4.";
    }

    revision "2025-09-12" {
        description "Modified the when XPath in next-hop-gateway objectlist for IPv4/IPv6 static routes";
        reference " 1.2.3.";
    }

    revision "2025-07-08" {
        description "Added streaming telemetry support";
        reference " 1.2.2.";
    }

    revision "2025-06-19" {
        description "Add a counters container with attributes to display the number of routes from all VRFs";
        reference " 1.2.1.";
    }

    revision "2025-06-17" {
        description "Added when tag distance to prefix attribute in ipv4/ipv6 static-route objectlist";
        reference " 1.2.0.";
    }

    revision "2025-02-07" {
        description "Added an option to configure maximum-fib-routes";
        reference " 1.1.0.";
    }

    revision "2024-12-12" {
        description "Added When tag constraints for object-list 'interfaces/interface'";
        reference " 1.0.5.";
    }

    revision "2024-12-04" {
        description "Add if-features to missing track-id cli-commands";
        reference " 1.0.4.";
    }

    revision "2024-11-27" {
        description "Fix IPv6 prefix and address format for static routes";
        reference " 1.0.3.";
    }

    revision "2024-11-22" {
        description "Added IPv6 prefix and address validation for static routes";
        reference " 1.0.2.";
    }

    revision "2024-11-05" {
        description "Add recursive knob to the static route parameters";
        reference " 1.0.1.";
    }

    revision "2024-09-17" {
        description "Datamodel restructuring to make interface-name optional for VRF static routes";
        reference " 1.0.0.";
    }

    revision "2024-09-05" {
        description "Updated if-feature for datatype RIB_ROUTE_TYPE_T";
        reference " 0.14.0.";
    }

    revision "2024-05-27" {
        description "Update cliFlag for max-ecmp-paths attribute";
        reference " 0.13.2.";
    }

    revision "2024-05-07" {
        description "Update default for max-ecmp-paths attribute";
        reference " 0.13.1.";
    }

    revision "2024-04-29" {
        description "Added when tag for attribute 'interface-name' to handle dynamic/static channel-group";
        reference " 0.13.0.";
    }

    revision "2023-08-01" {
        description "Removed Leafref for attribute 'interface-name'";
        reference " 0.12.3.";
    }

    revision "2023-07-19" {
        description "Updated 'cliFlag' for objectlist'ipv4/routes/route' and 'ipv4/interface-routes/interface-route'";
        reference " 0.12.2.";
    }

    revision "2023-06-15" {
        description "Added new attribute description for static ipv6 route";
        reference " 0.12.1.";
    }

    revision "2023-05-25" {
        description "Updated datatype RIB_DEBUG_ROUTING_T option";
        reference " 0.12.0.";
    }

    revision "2023-03-30" {
        description "Removing implicit_delete from static-routes ipv4 and ipv6 /routes/route/config";
        reference " 0.11.3.";
    }

    revision "2023-03-06" {
        description "Adding enclosing containers for static-routes objectlists";
        reference " 0.11.2.";
    }

    revision "2023-02-02" {
        description "Updated missing Description";
        reference " 0.11.0.";
    }

    revision "2023-01-05" {
        description "Leafref correction for config container";
        reference " 0.10.2.";
    }

    revision "2022-09-13" {
        description "Updated When tag constraints for attribute 'interface-name'";
        reference " 0.12.4.";
    }

    revision "2022-08-10" {
        description "Debug hierarchy change";
        reference " 0.10.1.";
    }

    revision "2022-07-31" {
        description "Stop using inet:ipv4-prefix and inet:ipv6-prefix due to Cisco NSO iterop";
        reference " 0.10.0.";
    }

    revision "2022-07-11" {
        description "Added utils_func for ipv6 route";
        reference " 0.9.2.";
    }

    revision "2022-06-29" {
        description "Added implicit delete tag for debug-config container";
        reference " 0.9.1.";
    }

    revision "2022-06-01" {
        description "Updated the yang file with feature";
        reference " 0.9.0.";
    }

    revision "2022-03-31" {
        description "Added IPv6 feature flag in needed areas";
        reference " 0.8.0.";
    }

    revision "2022-02-14" {
        description "SRv6 GET API";
        reference " 0.7.0.";
    }

    revision "2022-02-09" {
        description "Added When tag constraints for 'debug' container";
        reference " 0.11.1.";
    }

    revision "2021-12-08" {
        description "Added new attribute track-id to support releated to object-tracking feature";
        reference " 0.7.0.";
    }

    revision "2021-11-16" {
        description "Added some if-feature to fix customer SKU compilation";
        reference " 0.6.0.";
    }

    revision "2021-09-01" {
        description "Changed base interface module's switchport attribute name and the datatype from bool to empty";
        reference " 0.5.0.";
    }

    revision "2021-03-15" {
        description "Removed configuration of Interface name as nexthop for ipv6 mroute commands";
        reference " 0.4.0.";
    }

    revision "2021-01-27" {
        description "Mroute related changes, added description for RPCs";
        reference " 0.3.0.";
    }

    revision "2020-12-15" {
        description "Change to have data-types in lower case instead of camel case";
        reference " 0.2.0.";
    }

    revision "2020-09-07" {
        description "Datamodel restructuring";
        reference " 0.1.0.";
    }

    grouping rib-global-config {
        description
            "Global configuration data for RIB";
        leaf fib-retain  {
            if-feature feature-list:HAVE_L3;
            type  ipi-rib-types:rib_fib_retain_t;
            units "seconds";
            default "60";
            description "Use this attribute to configure retain time for stale routes (forever
                        or specific time in seconds) in FIB after RIB restarts";
        } // END of fib-retain definition.

        leaf max-ecmp-paths  {
            if-feature feature-list:HAVE_MULTIPATH;
            type  uint8 {
                 range "1..64"  {
                    description "1..64: Supported range 1 - 64";
                 }
            }
            default "8";
            description "Use this attribute to set the maximum number of paths to install in
                        the FIB (Forwarding Information Base) for the ECMP (Equal-Cost
                        MultiPath) feature.";
        } // END of max-ecmp-paths definition.

        leaf max-static-routes  {
            type  uint32 {
                 range "1..4294967294"  {
                    description "1..4294967294: Supported range 1 - 4294967294";
                 }
            }
            default "4294967294";
            description "Use this attribute to set the maximum number of static routes.";
        } // END of max-static-routes definition.

        leaf max-fib-routes  {
            type  uint32 {
                 range "1..16384"  {
                    description "1..16384: Supported range 1 - 16384";
                 }
            }
            description "Use this attribute to set the maximum number of FIB (Forwarding
                        Information Base) routes excluding kernel, connected, and static
                        routes.";
        } // END of max-fib-routes definition.

    } // END of rib-global-config definition.
    grouping rib-debug-config {
        description
            "Debug configuration data for RIB";
        leaf rib-options  {
            type  ipi-rib-types:rib_conf_debug_t;
            description "Use this attribute to debug the ribd process.";
        } // END of rib-options definition.

        leaf ipv4-routing-options  {
            type  ipi-rib-types:rib_debug_routing_t;
            description "Use this attribute to debug ip route.";
        } // END of ipv4-routing-options definition.

        leaf ipv6-routing-options  {
            type  ipi-rib-types:rib_debug_routing_t;
            description "Use this attribute to debug ipv6 route.";
        } // END of ipv6-routing-options definition.

    } // END of rib-debug-config definition.
    grouping terminal-debug-state {
        description
            "Terminal debug status for RIB";
        leaf rib-options  {
            type  ipi-rib-types:rib_debug_t;
            description "Terminal debug option";
        } // END of rib-options definition.

        leaf ip-routing-options  {
            type  ipi-rib-types:rib_debug_routing_t;
            description "Terminal debug ipv4 routing option";
        } // END of ip-routing-options definition.

        leaf ipv6-routing-options  {
            type  ipi-rib-types:rib_debug_routing_t;
            description "Terminal debug ipv6 routing option";
        } // END of ipv6-routing-options definition.

    } // END of terminal-debug-state definition.
    grouping srv6-sid-state {
        description
            "SRv6 services state attributes";
        leaf sid  {
            type  inet:ipv6-address;
            description "SRv6 Segment Identifier";
        } // END of sid definition.

        leaf action  {
            type  string {
                length "1..1965";
                pattern "[^?' =,>|]+";
            }
            description "SRv6 Action to be carried out for this entry.";
        } // END of action definition.

        leaf ipv6-nexthop  {
            type  inet:ipv6-address;
            description "IPv6 Nexthop address";
        } // END of ipv6-nexthop definition.

        leaf originator  {
            type  string {
                length "1..1965";
                pattern "[^?' =,>|]+";
            }
            description "SRv6 route originator protocol name";
        } // END of originator definition.

        leaf type  {
            type  string {
                length "1..1965";
                pattern "[^?' =,>|]+";
            }
            description "SRv6 route type";
        } // END of type definition.

        leaf uptime  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "SRv6 Route Up time";
        } // END of uptime definition.

    } // END of srv6-sid-state definition.
    grouping rib-interface-bfd-config {
        description
            "Interface level Configuration attributes related to BFD";
        leaf ipv4-enable-bfd  {
            if-feature feature-list:HAVE_BFD;
            type  ipi-rib-types:rib_bfd_state;
            description "Use this attribute to enable or disable Bidirectional Forwarding
                        Detection static routes.";
        } // END of ipv4-enable-bfd definition.

        leaf ipv6-enable-bfd  {
            if-feature feature-list:HAVE_BFD;
            if-feature feature-list:HAVE_IPV6;
            type  ipi-rib-types:rib_bfd_state;
            description "Use this attribute to enable or disable Bidirectional Forwarding
                        Detection static routes.";
        } // END of ipv6-enable-bfd definition.

    } // END of rib-interface-bfd-config definition.
    grouping rib-interface-config {
        description
            "Interface level Configuration attributes";
        leaf name  {
            type  leafref {
                path  "/ipi-interface:interfaces/ipi-interface:interface/ipi-interface:name";
            }
            description "Reference to the base interface name";
        } // END of name definition.

    } // END of rib-interface-config definition.
    grouping rib-bfd-config {
        description
            "Configuration attributes related to BFD for static routes";
        leaf bfd-state  {
            if-feature feature-list:HAVE_BFD;
            type  ipi-rib-types:rib_static_bfd_enable_disable_t;
            description "Use this attribute to set fall-over detection.";
        } // END of bfd-state definition.

    } // END of rib-bfd-config definition.
    grouping rib-counters-state {
        description
            "Grouping for rib counters attributes";
        leaf total-routes-ipv4-vrf  {
            type  yang:counter32;
            description "Total IPv4 routes from all protocols and for all VRFs";
        } // END of total-routes-ipv4-vrf definition.

        leaf total-routes-ipv6-vrf  {
            type  yang:counter32;
            description "Total IPv6 routes from all protocols and for all VRFs";
        } // END of total-routes-ipv6-vrf definition.

    } // END of rib-counters-state definition.
    grouping rib-counters-top {
        description
            "Grouping for rib counters";
        container counters {
            config false;
            description
                "Container for the rib counters";
            uses rib-counters-state;
        } // END of counters-container definition.
    } // END of rib-counters-top definition.

    grouping  static-routing-grouping {
    description
        "Static Route configurations";
    container static-routing {
        if-feature feature-list:HAVE_RIBD;
        description
            "Static Route configurations";
        container ipv4 {
            description
                "IPV4 Static Route configurations";

            list static-route {
            // when " ipi-rib:static-routing/ipv4/static-route/next-hops-gateway/next-hop-gateway/gateway + ipi-rib:static-routing/ipv4/static-route/next-hops-interface/next-hop-interface/interface ";
                key "prefix";
                description
                    "List for IPv4 static routing";
                leaf prefix  {
                    type  leafref {
                        path  "../config/prefix";
                    }
                    description "Use this attribute to configure a prefix for an IPv4 static route
                                (e.g. 10.0.0.0/8)";
                } // END of prefix definition.

                container config {
                    description
                        "Container for IPv4 static routing configuration";
                    uses ipi-rib-common:rib-ipv4-static-route-config;
                } // END of config-container definition.
                container state {
                    config false;
                    description
                        "Container for IPv4 static routing runtime state";
                    uses ipi-rib-common:rib-ipv4-static-route-config;
                } // END of state-container definition.
                container next-hops-gateway {
                    description
                        "Container for IPv4 next hop gateway static routing";

                    list next-hop-gateway {
                        key "gateway";
                        description
                            "List for IPv4 next hop gateway static routing";
                        leaf gateway  {
                            type  leafref {
                                path  "../config/gateway";
                            }
                            description "Use this attribute to configure an IPv4 gateway address for next hop
                                        for this destination prefix";
                        } // END of gateway definition.

                        container config {
                            description
                                "Container for IPv4 next hop gateway static routing configuration";
                            uses ipi-rib-common:rib-ipv4-next-hop-gateway-config;
                            uses rib-bfd-config;
                        } // END of config-container definition.
                        container state {
                            config false;
                            description
                                "Container for IPv4 next hop gateway static routing runtime state";
                            uses ipi-rib-common:rib-ipv4-next-hop-gateway-config;
                            uses rib-bfd-config;
                        } // END of state-container definition.
                    } // End of next-hop-gateway-list
                } // END of next-hops-gateway-container definition.
                container next-hops-interface {
                    description
                        "Container for IPv4 next hop interface static routing";

                    list next-hop-interface {
                    // when " ipi-interface:interfaces/interface/config/enable-switchport != '1' ";
                        key "interface";
                        description
                            "List for IPv4 next hop interface static routing";
                        leaf interface  {
                            type  leafref {
                                path  "../config/interface";
                            }
                            description "Use this attribute to configure a interface for next hop for this
                                        destination prefix";
                        } // END of interface definition.

                        container config {
                            description
                                "Container for IPv4 next hop interface static routing configuration";
                            uses ipi-rib-common:rib-ipv4-next-hop-interface-config;
                        } // END of config-container definition.
                        container state {
                            config false;
                            description
                                "Container for IPv4 next hop interface static routing runtime state";
                            uses ipi-rib-common:rib-ipv4-next-hop-interface-config;
                        } // END of state-container definition.
                    } // End of next-hop-interface-list
                } // END of next-hops-interface-container definition.
            } // End of static-route-list
        } // END of ipv4-container definition.
        container ipv6 {
            if-feature feature-list:HAVE_IPV6;
            description
                "IPV6 Static Route configurations";

            list static-route {
            // when " ipi-rib:static-routing/ipv6/static-route/next-hops-gateway/next-hop-gateway/gateway + ipi-rib:static-routing/ipv6/static-route/next-hops-interface/next-hop-interface/interface ";
                key "prefix";
                description
                    "List for IPv6 static routing";
                leaf prefix  {
                    type  leafref {
                        path  "../config/prefix";
                    }
                    description "Use this attribute to configure a prefix for an IPv6 static route
                                (e.g. 3ffe:506::/32)";
                } // END of prefix definition.

                container config {
                    description
                        "Container for IPv6 static routing configuration";
                    uses ipi-rib-common:rib-ipv6-static-route-config;
                } // END of config-container definition.
                container state {
                    config false;
                    description
                        "Container for IPv6 static routing runtime state";
                    uses ipi-rib-common:rib-ipv6-static-route-config;
                } // END of state-container definition.
                container next-hops-gateway {
                    description
                        "Container for IPv6 next hop gateway static routing";

                    list next-hop-gateway {
                        key "gateway";
                        description
                            "List for IPv6 next hop gateway static routing";
                        leaf gateway  {
                            type  leafref {
                                path  "../config/gateway";
                            }
                            description "Use this attribute to configure an IPv6 gateway address for next hop
                                        for this destination prefix";
                        } // END of gateway definition.

                        container config {
                            description
                                "Container for IPv6 next hop gateway static routing configuration";
                            uses ipi-rib-common:rib-ipv6-next-hop-gateway-config;
                            uses rib-bfd-config;
                        } // END of config-container definition.
                        container state {
                            config false;
                            description
                                "Container for IPv6 next hop gateway static routing runtime state";
                            uses ipi-rib-common:rib-ipv6-next-hop-gateway-config;
                            uses rib-bfd-config;
                        } // END of state-container definition.
                    } // End of next-hop-gateway-list
                } // END of next-hops-gateway-container definition.
                container next-hops-interface {
                    description
                        "Container for IPv6 next hop interface static routing";

                    list next-hop-interface {
                    // when " ipi-interface:interfaces/interface/config/enable-switchport != '1' ";
                        key "interface";
                        description
                            "List for IPv6 next hop interface static routing";
                        leaf interface  {
                            type  leafref {
                                path  "../config/interface";
                            }
                            description "Use this attribute to configure a interface for next hop for this
                                        destination prefix";
                        } // END of interface definition.

                        container config {
                            description
                                "Container for IPv6 next hop interface static routing configuration";
                            uses ipi-rib-common:rib-ipv6-next-hop-interface-config;
                        } // END of config-container definition.
                        container state {
                            config false;
                            description
                                "Container for IPv6 next hop interface static routing runtime state";
                            uses ipi-rib-common:rib-ipv6-next-hop-interface-config;
                        } // END of state-container definition.
                    } // End of next-hop-interface-list
                } // END of next-hops-interface-container definition.
            } // End of static-route-list
        } // END of ipv6-container definition.
    } // END of static-routing-container definition.
    } // END of static-routing-grouping definition.

    grouping  routing-grouping {
    description
        "RIB Master for system wide configurations";
    container routing {
        if-feature feature-list:HAVE_RIBD;
        description
            "RIB Master for system wide configurations";
        container global {
            description
                "RIB global configurations";
            container config {
                description
                    "RIB global configuration attributes";
                uses rib-global-config;
                uses ipi-rib-common:rib-global-bfd-config;
            } // END of config-container definition.
            container state {
                config false;
                description
                    "Global Operational data for RIB";
                uses rib-global-config;
                uses ipi-rib-common:rib-global-bfd-config;
            } // END of state-container definition.
            uses rib-counters-top;
        } // END of global-container definition.
        container debug {
            description
                "RIB debug configurations";
            container config {
                description
                    "Debug related configuration attributes in RIB";
                uses rib-debug-config;
            } // END of config-container definition.
            container state {
                config false;
                description
                    "Operational data related to debug for RIB";
                container terminal-debug-status {
                    config false;
                    description
                        "Terminal debug status";
                    uses terminal-debug-state;
                } // END of terminal-debug-status-container definition.
                uses rib-debug-config;
            } // END of state-container definition.
        } // END of debug-container definition.
        container static-routes {
            description
                "Static Route configurations";
            container ipv4 {
                description
                    "IPv4 Static Route configurations";
                container multicast-routes {
                    description
                        "Container for IPv4 mroute vrf";

                    list multicast-route {
                        key "source-prefix protocol-type";
                        description
                            "Mroute vrf";
                        leaf source-prefix  {
                            type  leafref {
                                path  "../config/source-prefix";
                            }
                            description "Source prefix";
                        } // END of source-prefix definition.

                        leaf protocol-type  {
                            type  leafref {
                                path  "../config/protocol-type";
                            }
                            description "mroute prototype";
                        } // END of protocol-type definition.

                        container config {
                            description
                                "configuration attributes for IPv4 static mroute";
                            uses ipi-rib-common:rib-ipv4-multicast-config;
                        } // END of config-container definition.
                        container state {
                            config false;
                            description
                                "Operational data for IPv4 static mroute";
                            uses ipi-rib-common:rib-ipv4-multicast-config;
                        } // END of state-container definition.
                    } // End of multicast-route-list
                } // END of multicast-routes-container definition.
            } // END of ipv4-container definition.
            container ipv6 {
                if-feature feature-list:HAVE_IPV6;
                description
                    "IPv6 Static Route configurations";
                container multicast-routes {
                    description
                        "Container for IPv6 mroute vrf";

                    list multicast-route {
                    // when " ipi-rib:routing/static-routes/ipv6/multicast-routes/multicast-route/nexthop/config/gateway-mroute ";
                        key "source-prefix protocol-type";
                        description
                            "ipv6 mroute vrf";
                        leaf source-prefix  {
                            type  leafref {
                                path  "../config/source-prefix";
                            }
                            description "Source prefix";
                        } // END of source-prefix definition.

                        leaf protocol-type  {
                            type  leafref {
                                path  "../config/protocol-type";
                            }
                            description "mroute prototype";
                        } // END of protocol-type definition.

                        container config {
                            description
                                "configuration attributes for IPv6 static mroute";
                            uses ipi-rib-common:rib-ipv6-multicast-config;
                        } // END of config-container definition.
                        container state {
                            config false;
                            description
                                "Operational data for IPv6 static mroute";
                            uses ipi-rib-common:rib-ipv6-multicast-config;
                        } // END of state-container definition.
                        container nexthop {
                            description
                                "ipv6 mroute nexthop information";
                            container config {
                                presence "yes";
                                description
                                    "configuration attributes for IPv6 static mroute gateway";
                                uses ipi-rib-common:rib-ipv6-multicast-gateway-config;
                            } // END of config-container definition.
                            container state {
                                config false;
                                description
                                    "Operational data for IPv6 static mroute";
                                uses ipi-rib-common:rib-ipv6-multicast-gateway-config;
                            } // END of state-container definition.
                        } // END of nexthop-container definition.
                    } // End of multicast-route-list
                } // END of multicast-routes-container definition.
            } // END of ipv6-container definition.
        } // END of static-routes-container definition.
        container srv6-sid-entries {
            if-feature feature-list:HAVE_SRV6;
            config false;
            description
                "Global SRV6 SID table";

            list srv6-sid-entry {
                key "sid";
                config false;
                description
                    "Global SRv6 SID entries";
                leaf sid  {
                    type  leafref {
                        path  "../state/sid";
                    }
                    description "SRv6 Segment Identifier";
                } // END of sid definition.

                container state {
                    config false;
                    description
                        "State Container for SRv6 SID entry";
                    uses srv6-sid-state;
                } // END of state-container definition.
            } // End of srv6-sid-entry-list
        } // END of srv6-sid-entries-container definition.
        container interfaces {
            description
                "RIB BFD interface related operations";

            list interface {
                if-feature feature-list:HAVE_BFD;
                key "name";
                description
                    "RIB BFD interface related operations";
                leaf name  {
                    type  leafref {
                        path  "../config/name";
                    }
                    description "Reference to the base interface name";
                } // END of name definition.

                container config {
                    description
                        "Interface related config attribute";
                    uses rib-interface-config;
                } // END of config-container definition.
                container state {
                    description
                        "Interface related operational attribute";
                    uses rib-interface-config;
                } // END of state-container definition.
                container bfd {
                    if-feature feature-list:HAVE_BFD;
                    description
                        "configuration attributes related to BFD for RIB";
                    container config {
                        description
                            "configuration attributes related to BFD for RIB";
                        uses rib-interface-bfd-config;
                    } // END of config-container definition.
                    container state {
                        config false;
                        description
                            "Operational data related to BFD for RIB";
                        uses rib-interface-bfd-config;
                    } // END of state-container definition.
                } // END of bfd-container definition.
            } // End of interface-list
        } // END of interfaces-container definition.
    } // END of routing-container definition.
    } // END of routing-grouping definition.

    augment /ipi-network-instance:network-instances/ipi-network-instance:network-instance {
        description
            "Static Route configurations";
        uses static-routing-grouping;
    }

    uses routing-grouping;

    rpc rib-snmp-restart {
        if-feature feature-list:HAVE_SNMP;
        if-feature feature-list:HAVE_RIBD;
        description "Use rib-snmp-restart to restart SNMP in Routing Information Base (RIB)";
    }

    rpc clear-ip-stale-kernel-routes {
        if-feature feature-list:HAVE_RIBD;
        description "Use clear-ip-stale-kernel-routes to clear stale IPv4 routes from the
                    RIB (Routing Information Base) and FIB (Forwarding Information Base).";
    }

    rpc clear-ipv6-stale-kernel-routes {
        if-feature feature-list:HAVE_IPV6;
        if-feature feature-list:HAVE_RIBD;
        description "Use clear-ipv6-stale-kernel-routes to clear stale IPv6 routes from the
                    RIB (Routing Information Base) and FIB (Forwarding Information Base).";
    }

    rpc clear-ip-route-all {
        if-feature feature-list:HAVE_RIBD;
        description "Use clear-ip-route-all to clear all IPv4 routes";
    }

    rpc clear-ip-route {
        if-feature feature-list:HAVE_RIBD;
        description "Use clear-ip-route to clear any specific IPv4 prefix route";
        input  {
            leaf prefix-address  {
                type cml-data-types:cml_ipv4_prefix_t;
                mandatory true;
                description "Prefix to be cleared(e.g. 10.0.0.0/8)";
            }
        }
    }

    rpc clear-ipv6-route-all {
        if-feature feature-list:HAVE_IPV6;
        if-feature feature-list:HAVE_RIBD;
        description "Use clear-ipv6-route-all to clear all IPv6 routes";
    }

    rpc clear-ipv6-route {
        if-feature feature-list:HAVE_IPV6;
        if-feature feature-list:HAVE_RIBD;
        description "Use clear-ipv6-route to clear any specific IPv6 prefix route";
        input  {
            leaf prefix-ipv6-address  {
                type cml-data-types:cml_ipv6_prefix_t;
                mandatory true;
                description "Prefix to be cleared(e.g. 3ffe:506::/32)";
            }
        }
    }

    rpc rib-terminal-debug-on {
        if-feature feature-list:HAVE_RIBD;
        description "Use rib-debug-on to enable rib debugging";
        input  {
            leaf terminal-debug-options  {
                type ipi-rib-types:rib_debug_t;
                mandatory true;
                description "Debug-option to be enabled";
            }
        }
    }

    rpc rib-terminal-debug-off {
        if-feature feature-list:HAVE_RIBD;
        description "Use rib-debug-off to disable rib debugging";
        input  {
            leaf terminal-debug-options  {
                type ipi-rib-types:rib_debug_t;
                mandatory true;
                description "Debug-option to be disabled";
            }
        }
    }

    rpc rib-terminal-debug-ipv4-routing-on {
        if-feature feature-list:HAVE_RIBD;
        description "Use rib-ip-routing-debug-on to enable rib debugging for ipv4 route
                    add/delete/modify events";
        input  {
            leaf terminal-debug-options  {
                type ipi-rib-types:rib_debug_routing_t;
                mandatory true;
                description "Debug-route-option to be enabled";
            }
        }
    }

    rpc rib-terminal-debug-ipv4-routing-off {
        if-feature feature-list:HAVE_RIBD;
        description "Use rib-ip-routing-debug-off to disable rib debugging for ipv4 route
                    add/delete/modify events";
        input  {
            leaf terminal-debug-options  {
                type ipi-rib-types:rib_debug_routing_t;
                mandatory true;
                description "Debug-route-option to be disabled";
            }
        }
    }

    rpc rib-terminal-debug-ipv6-routing-on {
        if-feature feature-list:HAVE_IPV6;
        if-feature feature-list:HAVE_RIBD;
        description "Use rib-ipv6-routing-debug-on to enable rib debugging for ipv6 route
                    add/delete/modify events";
        input  {
            leaf terminal-debug-options  {
                type ipi-rib-types:rib_debug_routing_t;
                mandatory true;
                description "Debug-route-option to be enabled";
            }
        }
    }

    rpc rib-terminal-debug-ipv6-routing-off {
        if-feature feature-list:HAVE_IPV6;
        if-feature feature-list:HAVE_RIBD;
        description "Use rib-ipv6-routing-debug-off to disable rib debugging for ipv6 route
                    add/delete/modify events";
        input  {
            leaf terminal-debug-options  {
                type ipi-rib-types:rib_debug_routing_t;
                mandatory true;
                description "Debug-route-option to be disabled";
            }
        }
    }

}
