/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-rib-vrf.yang
*
*/

module ipi-rib-vrf {

    yang-version 1.1;

    namespace   "http://www.ipinfusion.com/yang/ocnos/ipi-rib-vrf";

    prefix "ipi-rib-vrf";

    import ipi-rib-types {
        prefix ipi-rib-types;
        revision-date 2025-02-07;
    }

    import cml-data-types {
        prefix cml-data-types;
        revision-date 2026-05-15;
    }

    import ipi-rib-common {
        prefix ipi-rib-common;
        revision-date 2025-12-01;
    }

    import ipi-network-instance {
        prefix ipi-network-instance;
        revision-date 2026-08-12;
    }

    import ipi-network-instance-types {
        prefix ipi-network-instance-types;
        revision-date 2023-03-14;
    }

    import ietf-yang-types {
        prefix yang;
        revision-date 2013-07-15;
    }

    import ipi-vrf {
        prefix ipi-vrf;
        revision-date 2026-08-12;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for VRF RIB object";


    revision "2026-08-14" {
        description "Added rpf-prefer-longest-prefix-match command";
        reference " 1.3.0.";
    }

    revision "2025-10-09" {
        description "Modified the gateway-address data type under the next-hop object list for IPv4 and IPv6";
        reference " 1.2.2.";
    }

    revision "2025-08-28" {
        description "Add MPLS-Aware RIB counters and next-hop attributes";
        reference " 1.2.1.";
    }

    revision "2025-08-18" {
        description "Added notifications for IPv4 and IPv6 hardware FIB full and clear scenario";
        reference " 1.2.0.";
    }

    revision "2025-03-19" {
        description "Added custom error msg for rejecting max FIB routes config on default and mgmt VRF";
        reference " 1.1.1.";
    }

    revision "2025-02-07" {
        description "Added an option to configure maximum-fib-routes";
        reference " 1.1.0.";
    }

    revision "2024-12-16" {
        description "Fix DB-sync issue for global/config container";
        reference " 1.0.2.";
    }

    revision "2024-11-06" {
        description "Added telemetry support for ribs,ipv4 and ipv6, total-routes attribute";
        reference " 1.0.1.";
    }

    revision "2024-09-17" {
        description "Datamodel restructuring to make interface-name optional for VRF static routes. Module were transfered to ipi-rib";
        reference " 1.0.0.";
    }

    revision "2024-09-05" {
        description "Updated if-feature for datatype RIB_ROUTE_TYPE_T";
        reference " 0.15.2.";
    }

    revision "2024-07-16" {
        description "Removed implicit delete tag 'gateway-interface-route-global' in config container";
        reference " 0.15.1.";
    }

    revision "2024-07-04" {
        description "Removed implicit delete interface-route inside config container";
        reference " 0.15.0.";
    }

    revision "2023-08-31" {
        description "Remove unnecessary import";
        reference " 0.14.3.";
    }

    revision "2023-08-01" {
        description "Removed Leafref for attribute 'interface-name'";
        reference " 0.14.2.";
    }

    revision "2023-06-15" {
        description "Added new attribute description for static ipv6 route";
        reference " 0.14.1.";
    }

    revision "2023-05-25" {
        description "Updated datatype RIB_DEBUG_ROUTING_T option";
        reference " 0.14.0.";
    }

    revision "2023-03-06" {
        description "Adding enclosing containers for static-routes objectlists";
        reference " 0.13.0.";
    }

    revision "2023-01-05" {
        description "Leafref correction for config container";
        reference " 0.12.3.";
    }

    revision "2022-09-13" {
        description "Updated When tag constraints for attribute 'interface-name'";
        reference " 0.14.4.";
    }

    revision "2022-09-07" {
        description "Added if-feature HAVE_IPV6 for custom db trigger ipv6 routes";
        reference " 0.12.2.";
    }

    revision "2022-08-10" {
        description "Debug hierarchy change";
        reference " 0.12.1.";
    }

    revision "2022-07-31" {
        description "Stop using inet:ipv4-prefix and inet:ipv6-prefix due to Cisco NSO iterop";
        reference " 0.12.0.";
    }

    revision "2022-07-11" {
        description "Added utils_func for ipv6 route";
        reference " 0.11.1.";
    }

    revision "2022-06-01" {
        description "Updated the yang file with feature";
        reference " 0.11.0.";
    }

    revision "2022-05-04" {
        description "Added leafref from object-list key to config container leaf for interface-route-global";
        reference " 0.10.0.";
    }

    revision "2022-03-31" {
        description "Added IPV6 feature flag in needed areas";
        reference " 0.9.0.";
    }

    revision "2022-02-14" {
        description "Added new attribute track-id to support releated to object-tracking feature for default static route";
        reference " 0.9.0.";
    }

    revision "2021-12-21" {
        description "Added new attribute track-id to support releated to object-tracking feature";
        reference " 0.8.0.";
    }

    revision "2021-10-06" {
        description "Added flag to skip pre-commit validation for ivr static route with global gateway command";
        reference " 0.7.0.";
    }

    revision "2021-09-01" {
        description "Changed base interface module's switchport attribute name and the datatype from bool to empty";
        reference " 0.6.0.";
    }

    revision "2021-04-12" {
        description "Addition of static route for leaking into VRF";
        reference " 0.5.0.";
    }

    revision "2021-03-15" {
        description "Removed configuration of Interface name as nexthop for ipv6 mroute commands";
        reference " 0.4.0.";
    }

    revision "2021-01-27" {
        description "Mroute related changes, added description for RPCs";
        reference " 0.3.0.";
    }

    revision "2020-12-15" {
        description "Change to have data-types in lower case instead of camel case";
        reference " 0.2.0.";
    }

    revision "2020-09-07" {
        description "Datamodel restructuring";
        reference " 0.1.0.";
    }

    grouping rib-global-vrf-bfd-config {
        description
            "Global BFD Configuration attributes";
        leaf ipv4-enable-bfd-all-interfaces  {
            if-feature feature-list:HAVE_BFD;
            type  empty;
            description "Use this attribute to enable static BFD on all interfaces.";
        } // END of ipv4-enable-bfd-all-interfaces definition.

        leaf ipv6-enable-bfd-all-interfaces  {
            if-feature feature-list:HAVE_BFD;
            if-feature feature-list:HAVE_IPV6;
            type  empty;
            description "Use this attribute to enable ipv6 static BFD on all interfaces.";
        } // END of ipv6-enable-bfd-all-interfaces definition.

    } // END of rib-global-vrf-bfd-config definition.
    grouping rib-global-vrf-mcast-config {
        description
            "Global Multicast Configuration attributes";
        leaf rpf-prefer-longest-prefix-match  {
            type  empty;
            description "Use this attribute to prefer longest prefix match for RPF lookup.";
        } // END of rpf-prefer-longest-prefix-match definition.

    } // END of rib-global-vrf-mcast-config definition.
    grouping maximum-fib-route-config {
        description
            "Maximum FIB Route Configuration attributes";
        leaf max-limit  {
            type  uint32 {
                 range "1..2147483647"  {
                    description "1..2147483647: Supported range 1 - 2147483647";
                 }
            }
            mandatory true;
            description "Use this attribute to limit the maximum number of routes to be
                        installed in VRF FIB.";
        } // END of max-limit definition.

        leaf limit-action  {
            type  ipi-rib-types:rib_max_route_action_t;
            mandatory true;
            description "Use this attribute to define the action to be performed when the limit
                        is reached.";
        } // END of limit-action definition.

        leaf warning-threshold  {
            type  uint8 {
                 range "1..100"  {
                    description "1..100: Supported range 1 - 100";
                 }
            }
            units "%";
            default "80";
            description "Use this attribute to define a percentage of the maximum route limit
                        which when crossed results in a warning message and Netconf
                        notification being raised. Default is 80%.";
        } // END of warning-threshold definition.

    } // END of maximum-fib-route-config definition.
    grouping maximum-fib-route-state {
        description
            "Maximum FIB Route state attributes";
        leaf threshold-exceeded  {
            type  boolean;
            description "This attribute indicates whether the max route threshold is exceeded
                        or not.";
        } // END of threshold-exceeded definition.

        leaf utilization-percentage  {
            type  uint32;
            units "%";
            description "This attribute specifies utilization percentage of routes.";
        } // END of utilization-percentage definition.

    } // END of maximum-fib-route-state definition.

    grouping  global-grouping {
    description
        "RIB global configurations";
    container global {
        if-feature feature-list:HAVE_VRF;
        if-feature feature-list:HAVE_RIBD;
        description
            "RIB global configurations";
        container config {
            description
                "configuration attributes related to BFD for RIB VRF";
            uses rib-global-vrf-bfd-config;
            uses rib-global-vrf-mcast-config;
        } // END of config-container definition.
        container state {
            config false;
            description
                "Operational data related to BFD for RIB VRF";
            uses rib-global-vrf-bfd-config;
            uses rib-global-vrf-mcast-config;
        } // END of state-container definition.
    } // END of global-container definition.
    } // END of global-grouping definition.

    grouping  static-routes-grouping {
    description
        "VRF Static Route configurations";
    container static-routes {
        if-feature feature-list:HAVE_VRF;
        if-feature feature-list:HAVE_RIBD;
        description
            "VRF Static Route configurations";
        container ipv4 {
            description
                "IPV4 Static Route configurations";
            container multicast-routes {
                description
                    "Container for multicast routes";

                list multicast-route {
                    key "source-prefix protocol-type";
                    description
                        "Mroute vrf";
                    leaf source-prefix  {
                        type  leafref {
                            path  "../config/source-prefix";
                        }
                        description "Source prefix";
                    } // END of source-prefix definition.

                    leaf protocol-type  {
                        type  leafref {
                            path  "../config/protocol-type";
                        }
                        description "mroute prototype";
                    } // END of protocol-type definition.

                    container config {
                        description
                            "configuration attributes for IPV4 static mroute";
                        uses ipi-rib-common:rib-ipv4-multicast-config;
                    } // END of config-container definition.
                    container state {
                        config false;
                        description
                            "Operational data for IPV4 static mroute";
                        uses ipi-rib-common:rib-ipv4-multicast-config;
                    } // END of state-container definition.
                } // End of multicast-route-list
            } // END of multicast-routes-container definition.
        } // END of ipv4-container definition.
        container ipv6 {
            if-feature feature-list:HAVE_IPV6;
            description
                "VRF IPV6 Static Route configurations";
            container multicast-routes {
                description
                    "Container for IPv6 multicast routes";

                list multicast-route {
                // when " ipi-rib-vrf:static-routes/ipv6/multicast-routes/multicast-route/nexthop/config/gateway-mroute ";
                    key "source-prefix protocol-type";
                    description
                        "Static IPv6 multicast routes for VRF";
                    leaf source-prefix  {
                        type  leafref {
                            path  "../config/source-prefix";
                        }
                        description "Source prefix";
                    } // END of source-prefix definition.

                    leaf protocol-type  {
                        type  leafref {
                            path  "../config/protocol-type";
                        }
                        description "mroute prototype";
                    } // END of protocol-type definition.

                    container config {
                        description
                            "configuration attributes for IPV6 static mroute";
                        uses ipi-rib-common:rib-ipv6-multicast-config;
                    } // END of config-container definition.
                    container state {
                        config false;
                        description
                            "Operational data for IPV6 static mroute";
                        uses ipi-rib-common:rib-ipv6-multicast-config;
                    } // END of state-container definition.
                    container nexthop {
                        description
                            "IPv6 multicast route nexthop information";
                        container config {
                            presence "yes";
                            description
                                "configuration attributes for IPV6 static mroute gateway";
                            uses ipi-rib-common:rib-ipv6-multicast-gateway-config;
                        } // END of config-container definition.
                        container state {
                            config false;
                            description
                                "Operational data for IPV6 static mroute";
                            uses ipi-rib-common:rib-ipv6-multicast-gateway-config;
                        } // END of state-container definition.
                    } // END of nexthop-container definition.
                } // End of multicast-route-list
            } // END of multicast-routes-container definition.
        } // END of ipv6-container definition.
    } // END of static-routes-container definition.
    } // END of static-routes-grouping definition.

    grouping  ribs-grouping {
    description
        "RIB run-time attributes";
    container ribs {
        if-feature feature-list:HAVE_VRF;
        if-feature feature-list:HAVE_RIBD;
        config false;
        description
            "RIB run-time attributes";
        container ipv4 {
            config false;
            description
                "IPV4 routes";

            list ecmp-path-summary {
                key "path-count";
                config false;
                description
                    "RIB ecmp path information";
                leaf path-count  {
                    type  leafref {
                        path  "../state/path-count";
                    }
                    description "Number of paths";
                } // END of path-count definition.

                container state {
                    config false;
                    description
                        "IPV4 route ecmp path statistics";
                    container counters {
                        config false;
                        description
                            "IPV4 route ecmp path  statistics";
                        uses ipi-rib-common:rib-ecmp-route-count;
                    } // END of counters-container definition.
                    uses ipi-rib-common:rib-ecmp-path-count;
                } // END of state-container definition.
            } // End of ecmp-path-summary-list

            list protocol-rib-summary {
                key "protocol-type";
                config false;
                description
                    "Protocol RIB statistics";
                leaf protocol-type  {
                    type  leafref {
                        path  "../state/protocol-type";
                    }
                    description "route type";
                } // END of protocol-type definition.

                container state {
                    config false;
                    description
                        "IPV4 route statistics";
                    container counters {
                        config false;
                        description
                            "IPV4 route statistics";
                        uses ipi-rib-common:rib-protocol-route-count;
                    } // END of counters-container definition.
                    uses ipi-rib-common:rib-protocol-type;
                } // END of state-container definition.
            } // End of protocol-rib-summary-list

            list protocol-rib-mpls-summary {
                if-feature feature-list:HAVE_MPLS_AWARE_RIB;
                key "protocol-type";
                config false;
                description
                    "Protocol RIB statistics for routes with MPLS nexthop";
                leaf protocol-type  {
                    type  leafref {
                        path  "../state/protocol-type";
                    }
                    description "BGP or Static";
                } // END of protocol-type definition.

                container state {
                    config false;
                    description
                        "IPV4 route statistics for routes with MPLS nexthop";
                    container counters {
                        config false;
                        description
                            "IPV4 route statistics";
                        uses ipi-rib-common:rib-protocol-route-count;
                    } // END of counters-container definition.
                    uses ipi-rib-common:rib-protocol-type;
                } // END of state-container definition.
            } // End of protocol-rib-mpls-summary-list
            container routes {
                config false;
                description
                    "IPV4 routes";

                list route {
                    key "destination-prefix protocol-type";
                    config false;
                    description
                        "RIB run-time attributes";
                    leaf destination-prefix  {
                        type  leafref {
                            path  "../state/destination-prefix";
                        }
                        description "IP destination prefix (e.g. 10.0.0.0/8)";
                    } // END of destination-prefix definition.

                    leaf protocol-type  {
                        type  leafref {
                            path  "../state/protocol-type";
                        }
                        description "route type";
                    } // END of protocol-type definition.


                    list next-hop {
                        key "gateway-address";
                        config false;
                        description
                            "next-hop run-time attributes";
                        leaf gateway-address  {
                            type  leafref {
                                path  "../state/gateway-address";
                            }
                            description "Nexthop ip address";
                        } // END of gateway-address definition.

                        container state {
                            config false;
                            description
                                "Operational data related to route next-hop";
                            uses ipi-rib-common:rib-route-nexthop-state;
                            uses ipi-rib-common:rib-mpls-route-nexthop-state;
                        } // END of state-container definition.
                    } // End of next-hop-list
                    container state {
                        config false;
                        description
                            "Operational data for IPV4 route";
                        uses ipi-rib-common:rib-ipv4-destination-prefix;
                        uses ipi-rib-common:rib-route-state;
                    } // END of state-container definition.
                } // End of route-list
                container state {
                    config false;
                    description
                        "IPV4 default-gateway";
                    uses ipi-rib-common:rib-route-default-gateway-state;
                } // END of state-container definition.
            } // END of routes-container definition.
            container state {
                config false;
                description
                    "IPV4 route statistics";
                container counters {
                    config false;
                    description
                        "IPV4 route statistics";
                    uses ipi-rib-common:rib-global-statistics-state;
                    uses ipi-rib-common:rib-mpls-global-statistics-state;
                } // END of counters-container definition.
            } // END of state-container definition.
        } // END of ipv4-container definition.
        container ipv6 {
            if-feature feature-list:HAVE_IPV6;
            config false;
            description
                "IPV6 routes";

            list ecmp-path-summary {
                key "path-count";
                config false;
                description
                    "RIB ecmp path information";
                leaf path-count  {
                    type  leafref {
                        path  "../state/path-count";
                    }
                    description "Number of paths";
                } // END of path-count definition.

                container state {
                    config false;
                    description
                        "IPV6 route ecmp path statistics";
                    container counters {
                        config false;
                        description
                            "IPV6 route ecmp path  statistics";
                        uses ipi-rib-common:rib-ecmp-route-count;
                    } // END of counters-container definition.
                    uses ipi-rib-common:rib-ecmp-path-count;
                } // END of state-container definition.
            } // End of ecmp-path-summary-list

            list protocol-rib-summary {
                key "protocol-type";
                config false;
                description
                    "Protocol RIB statistics";
                leaf protocol-type  {
                    type  leafref {
                        path  "../state/protocol-type";
                    }
                    description "route type";
                } // END of protocol-type definition.

                container state {
                    config false;
                    description
                        "IPV6 route statistics";
                    container counters {
                        config false;
                        description
                            "IPV6 route statistics";
                        uses ipi-rib-common:rib-protocol-route-count;
                    } // END of counters-container definition.
                    uses ipi-rib-common:rib-protocol-type;
                } // END of state-container definition.
            } // End of protocol-rib-summary-list
            container routes {
                config false;
                description
                    "IPV6 routes";

                list route {
                    key "destination-prefix protocol-type";
                    config false;
                    description
                        "RIB run-time attributes";
                    leaf destination-prefix  {
                        type  leafref {
                            path  "../state/destination-prefix";
                        }
                        description "IP destination prefix (e.g. 10.0.0.0/8)";
                    } // END of destination-prefix definition.

                    leaf protocol-type  {
                        type  leafref {
                            path  "../state/protocol-type";
                        }
                        description "route type";
                    } // END of protocol-type definition.


                    list next-hop {
                        key "gateway-address";
                        config false;
                        description
                            "next-hop run-time attributes";
                        leaf gateway-address  {
                            type  leafref {
                                path  "../state/gateway-address";
                            }
                            description "Nexthop ip address";
                        } // END of gateway-address definition.

                        container state {
                            config false;
                            description
                                "Operational data related to route next-hop";
                            uses ipi-rib-common:rib-route-nexthop-state;
                        } // END of state-container definition.
                    } // End of next-hop-list
                    container state {
                        config false;
                        description
                            "Operational data for IPV6 route";
                        uses ipi-rib-common:rib-ipv6-destination-prefix;
                        uses ipi-rib-common:rib-route-state;
                    } // END of state-container definition.
                } // End of route-list
            } // END of routes-container definition.
            container state {
                config false;
                description
                    "IPV6 route statistics";
                container counters {
                    config false;
                    description
                        "IPV6 route statistics";
                    uses ipi-rib-common:rib-global-statistics-state;
                } // END of counters-container definition.
            } // END of state-container definition.
        } // END of ipv6-container definition.
    } // END of ribs-container definition.
    } // END of ribs-grouping definition.

    grouping  maximum-fib-routes-grouping {
    description
        "VRF Max Route configurations";
    container maximum-fib-routes {
        if-feature feature-list:HAVE_VRF;
        if-feature feature-list:HAVE_RIBD;
        description
            "VRF Max Route configurations";
        container ipv4 {
            description
                "IPV4 Max Route configurations";
            container config {
                presence "To configure max IPv4 fib routes";
                description
                    "Configuration attributes for IPv4 max routes";
                uses maximum-fib-route-config;
            } // END of config-container definition.
            container state {
                config false;
                description
                    "Operational data for IPv4 max routes";
                uses maximum-fib-route-config;
                uses maximum-fib-route-state;
            } // END of state-container definition.
        } // END of ipv4-container definition.
        container ipv6 {
            if-feature feature-list:HAVE_IPV6;
            description
                "IPV6 Max Route configurations";
            container config {
                presence "To configure max IPv6 fib routes";
                description
                    "Configuration attributes for IPv6 max routes";
                uses maximum-fib-route-config;
            } // END of config-container definition.
            container state {
                config false;
                description
                    "Operational data for IPv6 max routes";
                uses maximum-fib-route-config;
                uses maximum-fib-route-state;
            } // END of state-container definition.
        } // END of ipv6-container definition.
    } // END of maximum-fib-routes-container definition.
    } // END of maximum-fib-routes-grouping definition.

    augment /ipi-network-instance:network-instances/ipi-network-instance:network-instance/ipi-vrf:vrf {
        if-feature feature-list:HAVE_VRF;
        description
            "RIB global configurations";
        uses global-grouping;
    }

    augment /ipi-network-instance:network-instances/ipi-network-instance:network-instance/ipi-vrf:vrf {
        if-feature feature-list:HAVE_VRF;
        description
            "VRF Static Route configurations";
        uses static-routes-grouping;
    }

    augment /ipi-network-instance:network-instances/ipi-network-instance:network-instance/ipi-vrf:vrf {
        if-feature feature-list:HAVE_VRF;
        description
            "RIB run-time attributes";
        uses ribs-grouping;
    }

    augment /ipi-network-instance:network-instances/ipi-network-instance:network-instance/ipi-vrf:vrf {
    when " /ipi-network-instance:network-instances/ipi-network-instance:network-instance/ipi-network-instance:instance-type = 'vrf' and /ipi-network-instance:network-instances/ipi-network-instance:network-instance/ipi-vrf:vrf/ipi-vrf:config/ipi-vrf:vrf-name != 'default' and /ipi-network-instance:network-instances/ipi-network-instance:network-instance/ipi-vrf:vrf/ipi-vrf:config/ipi-vrf:vrf-name != 'management' ";
        if-feature feature-list:HAVE_VRF;
        description
            "VRF Max Route configurations";
        uses maximum-fib-routes-grouping;
    }


    rpc clear-ip-vrf-route-all {
        if-feature feature-list:HAVE_VRF;
        if-feature feature-list:HAVE_RIBD;
        description "Use clear-ip-vrf-route-all to clear all IPv4 VRF routes of any
                    particular VRF name";
        input  {
            leaf vrf-name  {
                type string;
                mandatory true;
                description "vrf name";
            }
        }
    }

    rpc clear-ip-vrf-route {
        if-feature feature-list:HAVE_VRF;
        if-feature feature-list:HAVE_RIBD;
        description "Use clear-ip-vrf-route to clear any specific prefix IPv4 VRF route of
                    any particular VRF name";
        input  {
            leaf vrf-name  {
                type string;
                mandatory true;
                description "vrf name";
            }
            leaf prefix-address  {
                type cml-data-types:cml_ipv4_prefix_t;
                mandatory true;
                description "Prefix to be cleared(e.g. 10.0.0.0/8)";
            }
        }
    }

    rpc clear-ipv6-vrf-route-all {
        if-feature feature-list:HAVE_VRF;
        if-feature feature-list:HAVE_IPV6;
        if-feature feature-list:HAVE_RIBD;
        description "Use clear-ipv6-vrf-route-all to clear all IPv6 VRF routes of any
                    particular VRF name";
        input  {
            leaf vrf-name  {
                type string;
                mandatory true;
                description "vrf name";
            }
        }
    }

    rpc clear-ipv6-vrf-route {
        if-feature feature-list:HAVE_VRF;
        if-feature feature-list:HAVE_IPV6;
        if-feature feature-list:HAVE_RIBD;
        description "Use clear-ipv6-vrf-route to clear any specific prefix IPv6 VRF route
                    of any particular VRF name";
        input  {
            leaf vrf-name  {
                type string;
                mandatory true;
                description "Virtual router id";
            }
            leaf prefix-ipv6-address  {
                type cml-data-types:cml_ipv6_prefix_t;
                mandatory true;
                description "Prefix to be cleared(e.g. 3ffe:506::/32)";
            }
        }
    }

    notification vrf-ipv4-fib-routes-above-threshold {
        if-feature feature-list:HAVE_VRF;
        if-feature feature-list:HAVE_RIBD;

        description "Notify when the installed VRF FIB IPv4 routes crosses the configured threshold.";

        leaf severity {
            type cml-data-types:cml_notif_severity_t;
            description "Notification severity level (value: WARNING)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf max-limit {
            type  uint32;
        description
            "Use this attribute to limit the maximum number of routes to be
                    installed in VRF FIB.";
        }

        leaf warning-threshold {
            type  uint8;
        description
            "Use this attribute to define a percentage of the maximum route limit
                    which when crossed results in a warning message and Netconf
                    notification being raised. Default is 80%.";
        }

        leaf threshold-exceeded {
            type  boolean;
        description
            "This attribute indicates whether the max route threshold is exceeded
                    or not.";
        }

        leaf total-routes {
            type  yang:counter32;
        description
            "Total routes in the RIB from all protocols";
        }
    }

    notification vrf-ipv4-fib-routes-below-threshold {
        if-feature feature-list:HAVE_VRF;
        if-feature feature-list:HAVE_RIBD;

        description "Notify when the installed VRF FIB IPv4 routes fall below the configured threshold.";

        leaf severity {
            type cml-data-types:cml_notif_severity_t;
            description "Notification severity level (value: WARNING)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf max-limit {
            type  uint32;
        description
            "Use this attribute to limit the maximum number of routes to be
                    installed in VRF FIB.";
        }

        leaf warning-threshold {
            type  uint8;
        description
            "Use this attribute to define a percentage of the maximum route limit
                    which when crossed results in a warning message and Netconf
                    notification being raised. Default is 80%.";
        }

        leaf threshold-exceeded {
            type  boolean;
        description
            "This attribute indicates whether the max route threshold is exceeded
                    or not.";
        }

        leaf total-routes {
            type  yang:counter32;
        description
            "Total routes in the RIB from all protocols";
        }
    }

    notification vrf-ipv6-fib-routes-above-threshold {
        if-feature feature-list:HAVE_VRF;
        if-feature feature-list:HAVE_RIBD;
        if-feature feature-list:HAVE_IPV6;

        description "Notify when the installed VRF FIB IPv6 routes crosses the configured threshold.";

        leaf severity {
            type cml-data-types:cml_notif_severity_t;
            description "Notification severity level (value: WARNING)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf max-limit {
            type  uint32;
        description
            "Use this attribute to limit the maximum number of routes to be
                    installed in VRF FIB.";
        }

        leaf warning-threshold {
            type  uint8;
        description
            "Use this attribute to define a percentage of the maximum route limit
                    which when crossed results in a warning message and Netconf
                    notification being raised. Default is 80%.";
        }

        leaf threshold-exceeded {
            type  boolean;
        description
            "This attribute indicates whether the max route threshold is exceeded
                    or not.";
        }

        leaf total-routes {
            type  yang:counter32;
        description
            "Total routes in the RIB from all protocols";
        }
    }

    notification vrf-ipv6-fib-routes-below-threshold {
        if-feature feature-list:HAVE_VRF;
        if-feature feature-list:HAVE_RIBD;
        if-feature feature-list:HAVE_IPV6;

        description "Notify when the installed VRF FIB IPv6 routes fall below the configured threshold.";

        leaf severity {
            type cml-data-types:cml_notif_severity_t;
            description "Notification severity level (value: WARNING)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf max-limit {
            type  uint32;
        description
            "Use this attribute to limit the maximum number of routes to be
                    installed in VRF FIB.";
        }

        leaf warning-threshold {
            type  uint8;
        description
            "Use this attribute to define a percentage of the maximum route limit
                    which when crossed results in a warning message and Netconf
                    notification being raised. Default is 80%.";
        }

        leaf threshold-exceeded {
            type  boolean;
        description
            "This attribute indicates whether the max route threshold is exceeded
                    or not.";
        }

        leaf total-routes {
            type  yang:counter32;
        description
            "Total routes in the RIB from all protocols";
        }
    }

    notification vrf-ipv4-max-fib-routes-limit-reached {
        if-feature feature-list:HAVE_VRF;
        if-feature feature-list:HAVE_RIBD;

        description "Notify when the installed VRF FIB IPv4 routes reaches the configured limit.";

        leaf severity {
            type cml-data-types:cml_notif_severity_t;
            description "Notification severity level (value: WARNING)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf max-limit {
            type  uint32;
        description
            "Use this attribute to limit the maximum number of routes to be
                    installed in VRF FIB.";
        }

        leaf limit-action {
            type ipi-rib-types:rib_max_route_action_t;
        description
            "Use this attribute to define the action to be performed when the limit
                    is reached.";
        }

        leaf total-routes {
            type  yang:counter32;
        description
            "Total routes in the RIB from all protocols";
        }
    }

    notification vrf-ipv4-max-fib-routes-below-route-limit {
        if-feature feature-list:HAVE_VRF;
        if-feature feature-list:HAVE_RIBD;

        description "Notify when the installed VRF FIB IPv4 routes fall below the configured limit.";

        leaf severity {
            type cml-data-types:cml_notif_severity_t;
            description "Notification severity level (value: WARNING)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf max-limit {
            type  uint32;
        description
            "Use this attribute to limit the maximum number of routes to be
                    installed in VRF FIB.";
        }

        leaf limit-action {
            type ipi-rib-types:rib_max_route_action_t;
        description
            "Use this attribute to define the action to be performed when the limit
                    is reached.";
        }

        leaf total-routes {
            type  yang:counter32;
        description
            "Total routes in the RIB from all protocols";
        }
    }

    notification vrf-ipv6-max-fib-routes-limit-reached {
        if-feature feature-list:HAVE_VRF;
        if-feature feature-list:HAVE_RIBD;
        if-feature feature-list:HAVE_IPV6;

        description "Notify when the installed VRF FIB IPv6 routes reaches the configured limit.";

        leaf severity {
            type cml-data-types:cml_notif_severity_t;
            description "Notification severity level (value: WARNING)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf max-limit {
            type  uint32;
        description
            "Use this attribute to limit the maximum number of routes to be
                    installed in VRF FIB.";
        }

        leaf limit-action {
            type ipi-rib-types:rib_max_route_action_t;
        description
            "Use this attribute to define the action to be performed when the limit
                    is reached.";
        }

        leaf total-routes {
            type  yang:counter32;
        description
            "Total routes in the RIB from all protocols";
        }
    }

    notification vrf-ipv6-max-fib-routes-below-route-limit {
        if-feature feature-list:HAVE_VRF;
        if-feature feature-list:HAVE_RIBD;
        if-feature feature-list:HAVE_IPV6;

        description "Notify when the installed VRF FIB IPv6 routes fall below the configured limit.";

        leaf severity {
            type cml-data-types:cml_notif_severity_t;
            description "Notification severity level (value: WARNING)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf max-limit {
            type  uint32;
        description
            "Use this attribute to limit the maximum number of routes to be
                    installed in VRF FIB.";
        }

        leaf limit-action {
            type ipi-rib-types:rib_max_route_action_t;
        description
            "Use this attribute to define the action to be performed when the limit
                    is reached.";
        }

        leaf total-routes {
            type  yang:counter32;
        description
            "Total routes in the RIB from all protocols";
        }
    }

    notification ipv4-hw-fib-full {
        if-feature feature-list:HAVE_VRF;
        if-feature feature-list:HAVE_RIBD;

        description "Notify when the installed VRF/global FIB IPv4 routes reaches hardware limit.";

        leaf severity {
            type cml-data-types:cml_notif_severity_t;
            description "Notification severity level (value: MAJOR)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf total-routes {
            type  yang:counter32;
        description
            "Total routes in the RIB from all protocols";
        }
    }

    notification ipv4-hw-fib-full-cleared {
        if-feature feature-list:HAVE_VRF;
        if-feature feature-list:HAVE_RIBD;

        description "Notify when the installed VRF/global FIB IPv4 routes reaches below hardware limit.";

        leaf severity {
            type cml-data-types:cml_notif_severity_t;
            description "Notification severity level (value: MINOR)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf total-routes {
            type  yang:counter32;
        description
            "Total routes in the RIB from all protocols";
        }
    }

    notification ipv6-hw-fib-full {
        if-feature feature-list:HAVE_VRF;
        if-feature feature-list:HAVE_RIBD;
        if-feature feature-list:HAVE_IPV6;

        description "Notify when the installed VRF/global FIB IPv6 routes reaches hardware limit.";

        leaf severity {
            type cml-data-types:cml_notif_severity_t;
            description "Notification severity level (value: MAJOR)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf total-routes {
            type  yang:counter32;
        description
            "Total routes in the RIB from all protocols";
        }
    }

    notification ipv6-hw-fib-full-cleared {
        if-feature feature-list:HAVE_VRF;
        if-feature feature-list:HAVE_RIBD;
        if-feature feature-list:HAVE_IPV6;

        description "Notify when the installed VRF/global FIB IPv6 routes reaches below hardware limit.";

        leaf severity {
            type cml-data-types:cml_notif_severity_t;
            description "Notification severity level (value: MINOR)";
        }

        leaf eventClass {
            type cml-data-types:cml_notif_class_t;
            description "Notification event class (value: STATE)";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.
                    For Bridge-domain, instance, instance name has to be a number between
                    (1-2147483647).";
        }

        leaf total-routes {
            type  yang:counter32;
        description
            "Total routes in the RIB from all protocols";
        }
    }

}
