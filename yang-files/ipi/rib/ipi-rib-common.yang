/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-rib-common.yang
*
*/

module ipi-rib-common {

    yang-version 1.1;

    namespace   "http://www.ipinfusion.com/yang/ocnos/ipi-rib-common";

    prefix "ipi-rib-common";

    import cml-data-types {
        prefix cml-data-types;
        revision-date 2026-05-15;
    }

    import ipi-rib-types {
        prefix ipi-rib-types;
        revision-date 2025-02-07;
    }

    import ietf-yang-types {
        prefix yang;
        revision-date 2013-07-15;
    }

    import ietf-inet-types {
        prefix inet;
        revision-date 2013-07-15;
    }

    import ipi-network-instance {
        prefix ipi-network-instance;
        revision-date 2026-08-12;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Common groupings in ipi-rib and ipi-rib-vrf-modules";


    revision "2025-12-01" {
        description "Add CML_SKIP_HITLESS_MERGE flag to enable-global-table-lookup attribute.";
        reference " 1.3.1.";
    }

    revision "2025-08-28" {
        description "Add MPLS-Aware RIB counters and next-hop attributes";
        reference " 1.2.0.";
    }

    revision "2025-02-07" {
        description "Added an option to configure maximum-fib-routes";
        reference " 1.1.0.";
    }

    revision "2024-11-27" {
        description "Added IPv6 prefix and address format for static routes";
        reference " 1.0.2.";
    }

    revision "2024-11-05" {
        description "Add recursive knob to the static route parameters";
        reference " 1.0.1.";
    }

    revision "2024-09-17" {
        description "Datamodel restructuring to make interface-name optional for VRF static routes";
        reference " 1.0.0.";
    }

    revision "2024-09-05" {
        description "Updated if-feature for datatype RIB_ROUTE_TYPE_T";
        reference " 0.11.0.";
    }

    revision "2023-05-25" {
        description "Updated datatype RIB_DEBUG_ROUTING_T option";
        reference " 0.10.0.";
    }

    revision "2022-08-10" {
        description "Debug hierarchy change";
        reference " 0.9.0.";
    }

    revision "2022-06-01" {
        description "Updated the yang file with feature";
        reference " 0.8.0.";
    }

    revision "2022-02-14" {
        description "Added new attribute object-tracking-reachability to support releated to object-tracking feature";
        reference " 0.7.0.";
    }

    revision "2021-12-08" {
        description "Added new attribute track-id to support releated to object-tracking feature";
        reference " 0.6.0.";
    }

    revision "2021-09-03" {
        description "Update descriptions of attribute";
        reference " 0.5.0.";
    }

    revision "2021-03-15" {
        description "Removed configuration of Interface name as nexthop for ipv6 mroute commands";
        reference " 0.4.0.";
    }

    revision "2021-01-27" {
        description "Mroute related changes";
        reference " 0.3.0.";
    }

    revision "2020-12-15" {
        description "Change to have data-types in lower case instead of camel case";
        reference " 0.2.0.";
    }

    revision "2020-09-07" {
        description "Datamodel restructuring";
        reference " 0.1.0.";
    }

    grouping rib-route-state {
        description
            "Operational data for routes";
        leaf protocol-type  {
            type  ipi-rib-types:rib_route_type_t;
            config false;
            description "Route type,  protocol which installed this route";
        } // END of protocol-type definition.

        leaf sub-type  {
            type  ipi-rib-types:rib_route_sub_type_t;
            config false;
            description "Route sub-type";
        } // END of sub-type definition.

        leaf distance  {
            type  uint8;
            config false;
            description "Administrative distance, Criterion that a router uses to determine
                        which routing protocol to use if two protocols provide route
                        information for the same destination.";
        } // END of distance definition.

        leaf metric  {
            type  uint32;
            config false;
            description "Indicates the cost of the route from the perspective of the routing
                        protocol installing the route. In general, routes with a lower metric
                        installed by the same routing protocol are lower cost to reach and are
                        preferable to routes with a higher metric.";
        } // END of metric definition.

        leaf black-hole  {
            type  empty;
            config false;
            description "Indicates whether black-hole filtering is enabled, a method for
                        quickly dropping undesirable traffic at the edge of the network, by
                        forwarding it to a null0 interface.";
        } // END of black-hole definition.

        leaf up-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            config false;
            description "Indicated up-time for the route";
        } // END of up-time definition.

        leaf selected  {
            type  empty;
            config false;
            description "Indicates RIB selected route";
        } // END of selected definition.

        leaf stale  {
            type  empty;
            config false;
            description "Indicates if the route is marked as stale";
        } // END of stale definition.

    } // END of rib-route-state definition.
    grouping rib-route-nexthop-state {
        description
            "Operational data of nexthop for routes";
        leaf gateway-address  {
            type  string {
                length "1..1965";
                pattern "[^?' =,>|]+";
            }
            config false;
            description "Indicates next-hop IP address or interface name";
        } // END of gateway-address definition.

        leaf-list recursive-hop  {
            type  string {
                length "1..1965";
                pattern "[^?' =,>|]+";
            }
            config false;
            description "Indicates recursive hops (IP address or interface name) to reach this
                        next-hop";
        } // END of recursive-hop definition.

        leaf interface-name  {
            type  string {
                length "1..1965";
                pattern "[^?' =,>|]+";
            }
            config false;
            description "Indicates outgoing interface (valid only if gateway-address is IP
                        address)";
        } // END of interface-name definition.

        leaf active  {
            type  empty;
            config false;
            description "Indicates whether the nexthop is alive";
        } // END of active definition.

        leaf fib-installed  {
            type  empty;
            config false;
            description "Indicates whether it is installed in FIB";
        } // END of fib-installed definition.

        leaf object-tracking-reachability  {
            if-feature feature-list:HAVE_OBJ_TRACKING;
            type  ipi-rib-types:rib_object_tracking_reachability_status_t;
            config false;
            description "Indicates whether route object tracking reachability status up/down";
        } // END of object-tracking-reachability definition.

    } // END of rib-route-nexthop-state definition.
    grouping rib-mpls-route-nexthop-state {
        description
            "Operational data of nexthop for routes";
        leaf recursive-mpls-active  {
            if-feature feature-list:HAVE_MPLS_AWARE_RIB;
            type  empty;
            description "The recursive next-hop is resolved via MPLS nexthop";
        } // END of recursive-mpls-active definition.

        leaf recursive-mpls-ftn-id  {
            if-feature feature-list:HAVE_MPLS_AWARE_RIB;
            type  uint32;
            description "MPLS nexthop FTN-ID";
        } // END of recursive-mpls-ftn-id definition.

        leaf recursive-mpls-nhlfe-ix  {
            if-feature feature-list:HAVE_MPLS_AWARE_RIB;
            type  uint32;
            description "MPLS nexthop nhlfe-ix";
        } // END of recursive-mpls-nhlfe-ix definition.

        leaf recursive-mpls-fib-installed  {
            if-feature feature-list:HAVE_MPLS_AWARE_RIB;
            type  empty;
            description "Whether the MPLS nexthop is installed in FIB";
        } // END of recursive-mpls-fib-installed definition.

    } // END of rib-mpls-route-nexthop-state definition.
    grouping rib-route-default-gateway-state {
        description
            "Default gateway for routes";
        leaf gateway-last-resort  {
            type  string {
                length "1..1965";
                pattern "[^?' =,>|]+";
            }
            config false;
            description "Default gateway or route used by the router when no other known route
                        exists (nexthop for prefix 0.0.0.0/0)";
        } // END of gateway-last-resort definition.

    } // END of rib-route-default-gateway-state definition.
    grouping rib-global-statistics-state {
        description
            "RIB global statistics";
        leaf total-routes  {
            type  yang:counter32;
            config false;
            description "Total routes in the RIB from all protocols";
        } // END of total-routes definition.

        leaf total-paths  {
            type  yang:counter32;
            config false;
            description "Total number of paths/nexthops";
        } // END of total-paths definition.

        leaf total-routes-in-fib  {
            type  yang:counter32;
            config false;
            description "Total number of routes installed in FIB";
        } // END of total-routes-in-fib definition.

        leaf ecmp-routes  {
            type  yang:counter32;
            config false;
            description "Total number of Equal-Cost-Mult-Path (ECMP) routes";
        } // END of ecmp-routes definition.

        leaf ecmp-paths  {
            type  yang:counter32;
            config false;
            description "Total number of Equal-Cost-Mult-Path (ECMP) paths";
        } // END of ecmp-paths definition.

    } // END of rib-global-statistics-state definition.
    grouping rib-mpls-global-statistics-state {
        description
            "RIB global statistics for routes with MPLS next-hop";
        leaf total-routes-mpls  {
            if-feature feature-list:HAVE_MPLS_AWARE_RIB;
            type  yang:counter32;
            description "Total routes in the RIB resolved with MPLS nexthop";
        } // END of total-routes-mpls definition.

        leaf total-routes-nhlfe-mpls  {
            if-feature feature-list:HAVE_MPLS_AWARE_RIB;
            type  yang:counter32;
            description "Total number of MPLS nexthops which resolve recursive routes in the
                        RIB";
        } // END of total-routes-nhlfe-mpls definition.

        leaf total-routes-in-fib-mpls  {
            if-feature feature-list:HAVE_MPLS_AWARE_RIB;
            type  yang:counter32;
            description "Total number of routes installed in FIB, resolved with MPLS nexthop";
        } // END of total-routes-in-fib-mpls definition.

    } // END of rib-mpls-global-statistics-state definition.
    grouping rib-ecmp-path-count {
        description
            "RIB ECMP path count";
        leaf path-count  {
            type  uint32;
            config false;
            description "Number of paths";
        } // END of path-count definition.

    } // END of rib-ecmp-path-count definition.
    grouping rib-ecmp-route-count {
        description
            "RIB ECMP route count";
        leaf number-of-routes  {
            type  yang:counter32;
            config false;
            description "Number of routes which have 'path-count' ecmp paths";
        } // END of number-of-routes definition.

    } // END of rib-ecmp-route-count definition.
    grouping rib-protocol-type {
        description
            "RIB protocol type";
        leaf protocol-type  {
            type  ipi-rib-types:rib_route_type_t;
            config false;
            description "Route Source - Routing protocol, static route, Kernel route";
        } // END of protocol-type definition.

    } // END of rib-protocol-type definition.
    grouping rib-protocol-route-count {
        description
            "RIB protocol route count";
        leaf number-of-routes  {
            type  yang:counter32;
            config false;
            description "Total number of routes for protocol in the RIB";
        } // END of number-of-routes definition.

    } // END of rib-protocol-route-count definition.
    grouping rib-ipv4-destination-prefix {
        description
            "RIB IPV4 destination prefix";
        leaf destination-prefix  {
            type  cml-data-types:cml_ipv4_prefix_t;
            description "IP destination prefix (e.g. 10.0.0.0/8)";
        } // END of destination-prefix definition.

    } // END of rib-ipv4-destination-prefix definition.
    grouping rib-ipv6-destination-prefix {
        description
            "RIB IPV6 destination prefix";
        leaf destination-prefix  {
            type  cml-data-types:cml_ipv6_prefix_t;
            description "IPV6 destination prefix";
        } // END of destination-prefix definition.

    } // END of rib-ipv6-destination-prefix definition.
    grouping rib-attr-config {
        description
            "Common configuration attributes for static routes";
        leaf distance  {
            type  uint32 {
                 range "1..255"  {
                    description "1..255: Supported range 1 - 255";
                 }
            }
            default "1";
            description "Use this attribute to set the distance value for this route.";
        } // END of distance definition.

        leaf track-id  {
            if-feature feature-list:HAVE_OBJ_TRACKING;
            type  uint16 {
                 range "1..500"  {
                    description "1..500: Supported range 1 - 500";
                 }
            }
            description "Use this attribute to track a object.";
        } // END of track-id definition.

        leaf description  {
            type  cml-data-types:cml_line_t {
                length "1..1965";
            }
            description "Use this attribute to set the description of this static route.";
        } // END of description definition.

        leaf enable-global-table-lookup  {
            when " /ipi-network-instance:network-instances/ipi-network-instance:network-instance/ipi-network-instance:config/ipi-network-instance:instance-name != 'default' ";
            // when " ../interface ";
            type  empty;
            description "Use this attribute to create an VRF static route with gateway in
                        default VRF table.";
        } // END of enable-global-table-lookup definition.

    } // END of rib-attr-config definition.
    grouping rib-attr-config-tag {
        description
            "Common configuration attribute tag for static routes";
        leaf tag  {
            type  uint32 {
                 range "0..4294967295"  {
                    description "0..4294967295: Supported range 0 - 4294967295";
                 }
            }
            default "0";
            description "Use this attribute to set the tag for this route.";
        } // END of tag definition.

    } // END of rib-attr-config-tag definition.
    grouping rib-attr-config-recursive {
        description
            "Common configuration attribute recursive for static routes";
        leaf recursive  {
            type  empty;
            description "Use this attribute to enable recursive resolution for this route.";
        } // END of recursive definition.

    } // END of rib-attr-config-recursive definition.
    grouping rib-ipv4-static-route-config {
        description
            "Configuration attributes for IPv4 static routes";
        leaf prefix  {
            type  cml-data-types:cml_ipv4_prefix_t;
            description "Use this attribute to configure a prefix for an IPv4 static route
                        (e.g. 10.0.0.0/8)";
        } // END of prefix definition.

    } // END of rib-ipv4-static-route-config definition.
    grouping rib-ipv4-next-hop-gateway-config {
        description
            "Configuration attributes for IPv4 next hop gateway static routes";
        leaf gateway  {
            type  inet:ipv4-address;
            description "Use this attribute to configure an IPv4 gateway address for this
                        destination prefix";
        } // END of gateway definition.

        leaf interface  {
            // when " not(/ipi-interface:interfaces/ipi-interface:interface/ipi-interface:config/ipi-interface:enable-switchport) ";
            type  string {
                length "1..1965";
                pattern "[^?' =,>|]+";
            }
            description "Use this attribute to set the interface for this route.";
        } // END of interface definition.

        uses rib-attr-config-tag;
        uses rib-attr-config-recursive;
        uses rib-attr-config;
    } // END of rib-ipv4-next-hop-gateway-config definition.
    grouping rib-ipv4-next-hop-interface-config {
        description
            "Configuration attributes for IPv4 next hop interface static routes";
        leaf interface  {
            type  string {
                length "1..1965";
                pattern "[^?' =,>|]+";
            }
            description "Use this attribute to set the interface for this route.";
        } // END of interface definition.

        uses rib-attr-config-tag;
        uses rib-attr-config;
    } // END of rib-ipv4-next-hop-interface-config definition.
    grouping rib-ipv6-static-route-config {
        description
            "Configuration attributes for IPv6 static routes";
        leaf prefix  {
            type  cml-data-types:cml_ipv6_prefix_t;
            description "Use this attribute to configure a prefix for an IPv6 static route
                        (e.g. 3ffe:506::/32)";
        } // END of prefix definition.

    } // END of rib-ipv6-static-route-config definition.
    grouping rib-ipv6-next-hop-gateway-config {
        description
            "Configuration attributes for IPv6 next hop gateway static routes";
        leaf gateway  {
            type  inet:ipv6-address;
            description "Use this attribute to configure an IPv6 gateway address for this
                        destination prefix";
        } // END of gateway definition.

        leaf interface  {
            // when " not(/ipi-interface:interfaces/ipi-interface:interface/ipi-interface:config/ipi-interface:enable-switchport) ";
            type  string {
                length "1..1965";
                pattern "[^?' =,>|]+";
            }
            description "Use this attribute to set the interface for this route.";
        } // END of interface definition.

        uses rib-attr-config-recursive;
        uses rib-attr-config;
    } // END of rib-ipv6-next-hop-gateway-config definition.
    grouping rib-ipv6-next-hop-interface-config {
        description
            "Configuration attributes for IPv6 next hop interface static routes";
        leaf interface  {
            type  string {
                length "1..1965";
                pattern "[^?' =,>|]+";
            }
            description "Use this attribute to set the interface for this route.";
        } // END of interface definition.

        uses rib-attr-config;
    } // END of rib-ipv6-next-hop-interface-config definition.
    grouping rib-global-bfd-config {
        description
            "Global BFD Configuration attributes";
        leaf ipv4-enable-bfd-all-interfaces  {
            if-feature feature-list:HAVE_BFD;
            type  empty;
            description "Use this attribute to enable static BFD on all interfaces.";
        } // END of ipv4-enable-bfd-all-interfaces definition.

        leaf ipv6-enable-bfd-all-interfaces  {
            if-feature feature-list:HAVE_BFD;
            if-feature feature-list:HAVE_IPV6;
            type  empty;
            description "Use this attribute to enable ipv6 static BFD on all interfaces.";
        } // END of ipv6-enable-bfd-all-interfaces definition.

    } // END of rib-global-bfd-config definition.
    grouping rib-ipv4-multicast-config {
        description
            "Mroute IPV4 level Configuration attributes";
        leaf source-prefix  {
            type  cml-data-types:cml_ipv4_prefix_t;
            description "Source prefix";
        } // END of source-prefix definition.

        leaf protocol-type  {
            type  ipi-rib-types:rib_mroute_route_type_t;
            default "default";
            description "mroute prototype";
        } // END of protocol-type definition.

        leaf gateway-address  {
            type  inet:ipv4-address;
            mandatory true;
            description "Use this attribute to configure static multicast routes.";
        } // END of gateway-address definition.

        leaf distance  {
            type  uint32 {
                 range "0..255"  {
                    description "0..255: Supported range 0 - 255";
                 }
            }
            description "Use this attribute to configure administrative distance for mroute.";
        } // END of distance definition.

    } // END of rib-ipv4-multicast-config definition.
    grouping rib-ipv6-multicast-config {
        description
            "Mroute IPV6 level Configuration attributes";
        leaf source-prefix  {
            type  cml-data-types:cml_ipv6_prefix_t;
            description "Source prefix";
        } // END of source-prefix definition.

        leaf protocol-type  {
            type  ipi-rib-types:rib_mroute_ipv6_route_type_t;
            default "default";
            description "mroute prototype";
        } // END of protocol-type definition.

    } // END of rib-ipv6-multicast-config definition.
    grouping rib-ipv6-multicast-gateway-config {
        description
            "Mroute IPV6 level Gateway Configuration attributes";
        leaf gateway-mroute  {
            type  inet:ipv6-address;
            mandatory true;
            description "Use this attribute to configure gateway for static multicast routes.";
        } // END of gateway-mroute definition.

        leaf distance  {
            type  uint32 {
                 range "0..255"  {
                    description "0..255: Supported range 0 - 255";
                 }
            }
            description "Use this attribute to configure administrative distance for mroute.";
        } // END of distance definition.

    } // END of rib-ipv6-multicast-gateway-config definition.


}
