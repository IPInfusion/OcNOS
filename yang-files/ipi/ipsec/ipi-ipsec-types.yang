/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ipsec-types.yang
*
*/

module ipi-ipsec-types {

    yang-version 1.1;

    namespace   "http://www.ipinfusion.com/yang/ocnos/ipi-ipsec-types";

    prefix "ipi-ipsec-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "IPsec types";


    revision "2022-08-22" {
        description "Updated SPI range to support 0 spi";
        reference " 0.2.3.";
    }

    revision "2022-06-27" {
        description "Updated SPI range";
        reference " 0.2.2.";
    }

    revision "2022-06-24" {
        description "Corrected Ipsec Authentication Values ";
        reference " 0.2.1.";
    }

    revision "2022-06-01" {
        description "Updated the yang file with feature";
        reference " 0.2.0.";
    }

    revision "2022-05-10" {
        description "Initial version";
        reference " 0.1.0.";
    }



    typedef  ipsec_diffie_hellman_group_t {
        type enumeration {
            enum 1 {
                value 1;
                description "Group 1  - 768 bits long (modp768)";
            }
            enum 2 {
                value 2;
                description "Group 2  - 1024 bits long (modp1024)";
            }
            enum 5 {
                value 5;
                description "Group 5  - 1536 bits long (modp1536)";
            }
            enum 14 {
                value 14;
                description "Group 14 - 2048 bits long (modp2048)";
            }
            enum 15 {
                value 15;
                description "Group 15 - 3072 bits long (modp3072)";
            }
            enum 16 {
                value 16;
                description "Group 16 - 4096 bits long (modp4096)";
            }
            enum 17 {
                value 17;
                description "Group 17 - 6144 bits long (modp6144)";
            }
            enum 18 {
                value 18;
                description "Group 18 - 8192 bits long (modp8192)";
            }
        }
        description "type definition for IPSEC_DIFFIE_HELLMAN_GROUP_T";
    }

    typedef  ipsec_ike_version_t {
        type enumeration {
            enum 1 {
                value 1;
                description "IKE version 1";
            }
            enum 2 {
                value 2;
                description "IKE version 2";
            }
            enum both {
                value 3;
                description "both IKE versions";
            }
        }
        description "type definition for IPSEC_IKE_VERSION_T";
    }

    typedef  ipsec_authentication_algorithm_t {
        type enumeration {
            enum md5 {
                value 2;
                description "MD5 algorithm";
            }
            enum sha1 {
                value 3;
                description "SHA1 algorithm";
            }
            enum sha256 {
                value 4;
                description "SHA2 256bit algorithm";
            }
            enum sha384 {
                value 5;
                description "SHA2 384bit algorithm";
            }
            enum sha512 {
                value 6;
                description "SHA2 512bit algorithm";
            }
        }
        description "type definition for IPSEC_AUTHENTICATION_ALGORITHM_T";
    }

    typedef  ipsec_authentication_method_t {
        type enumeration {
            enum pre-share {
                value 1;
                description "Select pre-shared key message as the authentication method";
            }
        }
        description "type definition for IPSEC_AUTHENTICATION_METHOD_T";
    }

    typedef  ipsec_encryption_algorithm_t {
        type enumeration {
            enum 3des {
                value 1;
                description "Specifies 168-bit DES (3DES) as the encryption algorithm";
            }
            enum aes {
                value 2;
                description "Specifies 56-bit AES-CBC as the encryption algorithm";
            }
            enum blowfish {
                value 3;
                description "Specifies 128-bit Blowfish as the encryption algorithm";
            }
            enum cast {
                value 4;
                description "Specifies cast as the encryption algorithm";
            }
            enum blowfish192 {
                value 5;
                description "Specifies 192-bit Blowfish as the encryption algorithm";
            }
            enum blowfish256 {
                value 6;
                description "Specifies 256-bit Blowfish as the encryption algorithm";
            }
            enum aes192 {
                value 7;
                description "Specifies 192-bit AES as the encryption algorithm";
            }
            enum aes256 {
                value 8;
                description "Specifies 256-bit AES as the encryption algorithm";
            }
        }
        description "type definition for IPSEC_ENCRYPTION_ALGORITHM_T";
    }

    typedef  ipsec_ah_authentication_t {
        type enumeration {
            enum none {
                value 0;
                description "No Authentication";
            }
            enum ah-md5 {
                value 2;
                description "MD5 Authentication Algorithm";
            }
            enum ah-sha1 {
                value 3;
                description "Alternative SHA1 Authentication Algorithm";
            }
            enum ah-sha256 {
                value 5;
                description "Alternative SHA256 Authentication Algorithm";
            }
            enum ah-sha384 {
                value 6;
                description "Alternative SHA384 Authentication Algorithm";
            }
            enum ah-sha512 {
                value 7;
                description "Alternative SHA512 Authentication Algorithm";
            }
        }
        description "type definition for IPSEC_AH_AUTHENTICATION_T";
    }

    typedef  ipsec_esp_authentication_t {
        type enumeration {
            enum none {
                value 0;
                description "No Authentication Algorithm";
            }
            enum esp-md5 {
                value 2;
                description "MD5 authentication algorithm";
            }
            enum esp-sha1 {
                value 3;
                description "Alternative SHA1 Authentication Algorithm";
            }
            enum esp-sha256 {
                value 5;
                description "Alternative SHA256 Authentication Algorithm";
            }
            enum esp-sha384 {
                value 6;
                description "Alternative SHA384 Authentication Algorithm";
            }
            enum esp-sha512 {
                value 7;
                description "Alternative SHA512 Authentication Algorithm";
            }
        }
        description "type definition for IPSEC_ESP_AUTHENTICATION_T";
    }

    typedef  ipsec_esp_encryption_t {
        type enumeration {
            enum esp-null {
                value 0;
                description "No encryption algorithm";
            }
            enum esp-3des {
                value 3;
                description "3DES encryption algorithm";
            }
            enum esp-cast {
                value 6;
                description "CAST encryption algorithm";
            }
            enum esp-blf {
                value 7;
                description "BLF encryption algorithm";
            }
            enum esp-blf192 {
                value 8;
                description "BLF192 encryption algorithm";
            }
            enum esp-blf256 {
                value 9;
                description "BLF256 encryption algorithm";
            }
            enum esp-aes {
                value 12;
                description "AES encryption algorithm";
            }
            enum esp-aes192 {
                value 31;
                description "AES192 encryption algorithm";
            }
            enum esp-aes256 {
                value 32;
                description "AES256 encryption algorithm";
            }
        }
        description "type definition for IPSEC_ESP_ENCRYPTION_T";
    }

    typedef  ipsec_session_key_direction_t {
        type enumeration {
            enum inbound {
                value 0;
                description "Inbound direction";
            }
            enum outbound {
                value 1;
                description "Outbound direction";
            }
        }
        description "type definition for IPSEC_SESSION_KEY_DIRECTION_T";
    }

    typedef  ipsec_session_key_protocol_t {
        type enumeration {
            enum esp {
                value 1;
                description "Encapsulating Security Payload (ESP)";
            }
        }
        description "type definition for IPSEC_SESSION_KEY_PROTOCOL_T";
    }

    typedef  ipsec_ts_protocol_t {
        type enumeration {
            enum none {
                value 0;
                description "None protocol";
            }
            enum unspec {
                value 1;
                description "Protocol unspecified";
            }
            enum ah {
                value 2;
                description "Authentication Header (AH)";
            }
            enum esp {
                value 3;
                description "Encapsulating Security Payload (ESP)";
            }
        }
        description "type definition for IPSEC_TS_PROTOCOL_T";
    }

    typedef  ipsec_ts_mode_t {
        type enumeration {
            enum tunnel {
                value 0;
                if-feature feature-list:HAVE_IPSEC_HW;
                description "In this mode the entire original IP packet is protected";
            }
            enum transport {
                value 1;
                description "In this mode only payload (data) of the original IP packet is protected";
            }
        }
        description "type definition for IPSEC_TS_MODE_T";
    }

    typedef  ipsec_sa_type_t {
        type enumeration {
            enum ipsec-isakmp {
                value 1;
                if-feature feature-list:HAVE_IPSEC_HW;
                description "IPsec isakmp";
            }
            enum ipsec-manual {
                value 2;
                description "IPsec manual";
            }
        }
        description "type definition for IPSEC_SA_TYPE_T";
    }

    typedef  ipsec_peer_spi_t {
        type uint16 {
             range 0..4096;
        }
        description "type definition for IPSEC_PEER_SPI_T";
    }

}
