/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ipsec.yang
*
*/

module ipi-ipsec {

    yang-version 1.1;

    namespace   "http://www.ipinfusion.com/yang/ocnos/ipi-ipsec";

    prefix "ipi-ipsec";

    import ietf-inet-types {
        prefix inet;
        revision-date 2013-07-15;
    }

    import ipi-ipsec-types {
        prefix ipi-ipsec-types;
        revision-date 2022-08-22;
    }

    import feature-list {
        prefix feature-list;
        revision-date 2026-09-15;
    }

    include ipi-ipsec-interface { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Internet Protocol Security";


    revision "2024-07-01" {
        description "Added implicit_delete to ah-authentication config container";
        reference " 0.3.0.";
    }

    revision "2024-02-15" {
        description "Updated max length of authentication-key attribute as 32";
        reference " 0.1.1.";
    }

    revision "2023-07-07" {
        description "Removing the misplaced initialized from ah-authentication";
        reference " 0.1.0.";
    }

    revision "2022-08-22" {
        description "Updated SPI range to support 0 spi";
        reference " 0.2.5.";
    }

    revision "2022-06-27" {
        description "Updated SPI range";
        reference " 0.2.4.";
    }

    revision "2022-06-24" {
        description "Internal fixes handling transform-set";
        reference " 0.2.3.";
    }

    revision "2022-06-13" {
        description "Removed sa-lifetime attribute";
        reference " 0.2.2.";
    }

    revision "2022-06-07" {
        description "Changed the config IPsec Transform-set ESP Configuration data container to a presence container";
        reference " 0.2.1.";
    }

    revision "2022-06-01" {
        description "Updated the yang file with feature";
        reference " 0.2.0.";
    }

    revision "2022-05-10" {
        description "Initial Version";
        reference " 0.1.0.";
    }

    grouping ipsec-policy-peer-config {
        description
            "IPsec Policy Peer Configuration Grouping";
        leaf address  {
            type  inet:ip-address;
            description "This attribute configures peer IP address in ISAKMP policy.";
        } // END of address definition.

        leaf pre-shared-key  {
            type  string {
                length "1..128";
                pattern "[^?' =,>|]+";
            }
            description "This attribute configures IPsec pre-shared key in ISAKMP policy.";
        } // END of pre-shared-key definition.

    } // END of ipsec-policy-peer-config definition.
    grouping ipsec-policy-peer-top {
        description
            "IPsec Policy Peer grouping";
        container peer {
            description
                "IPsec Policy Peer";
            container config {
                description
                    "Configuration data for IPsec Policy Peer";
                uses ipsec-policy-peer-config;
            } // END of config-container definition.
            container state {
                config false;
                description
                    "Operational state data for IPsec Policy Peer";
                uses ipsec-policy-peer-config;
            } // END of state-container definition.
        } // END of peer-container definition.
    } // END of ipsec-policy-peer-top definition.
    grouping ipsec-policy-authentication-config {
        description
            "IPsec Policy Authentication Configuration Grouping";
        leaf algorithm  {
            type  ipi-ipsec-types:ipsec_authentication_algorithm_t;
            description "This attribute configures IPsec authentication algorithm in ISAKMP
                        policy.";
        } // END of algorithm definition.

        leaf method  {
            type  ipi-ipsec-types:ipsec_authentication_method_t;
            description "This attribute configures IPsec authentication method in ISAKMP
                        policy.";
        } // END of method definition.

    } // END of ipsec-policy-authentication-config definition.
    grouping ipsec-policy-authentication-top {
        description
            "IPsec Policy Authentication grouping";
        container authentication {
            description
                "IPsec Policy Authentication";
            container config {
                description
                    "Configuration data for IPsec Policy Authentication";
                uses ipsec-policy-authentication-config;
            } // END of config-container definition.
            container state {
                config false;
                description
                    "Operational state data for IPsec Policy Authentication";
                uses ipsec-policy-authentication-config;
            } // END of state-container definition.
        } // END of authentication-container definition.
    } // END of ipsec-policy-authentication-top definition.
    grouping ipsec-policy-isakmp-enable-config {
        description
            "IPsec Policy isakmp enable Configuration Grouping";
        leaf isakmp-enable  {
            type  empty;
            description "This attribute enable or disable the ISAKMP policy";
        } // END of isakmp-enable definition.

    } // END of ipsec-policy-isakmp-enable-config definition.
    grouping ipsec-policy-isakmp-enable-top {
        description
            "IPsec Policy isakmp enable grouping";
        container isakmp-enable {
            description
                "IPsec Policy isakmp-enable";
            container config {
                description
                    "Configuration data for IPsec Policy isakmp-enable";
                uses ipsec-policy-isakmp-enable-config;
            } // END of config-container definition.
            container state {
                config false;
                description
                    "Operational state data for IPsec Policy isakmp-enable";
                uses ipsec-policy-isakmp-enable-config;
            } // END of state-container definition.
        } // END of isakmp-enable-container definition.
    } // END of ipsec-policy-isakmp-enable-top definition.
    grouping ipsec-policy-config {
        description
            "IPsec policy configuration grouping";
        leaf sequence-number  {
            type  uint16 {
                 range "1..10000"  {
                    description "1..10000: Supported range 1 - 10000";
                 }
            }
            description "This attribute configures the sequence number that identifies the
                        ISAKMP policy.";
        } // END of sequence-number definition.

        leaf diffie-hellman-group  {
            type  ipi-ipsec-types:ipsec_diffie_hellman_group_t;
            description "This attribute configures IPsec Diffie Hellman Group for ISAKMP
                        policy.";
        } // END of diffie-hellman-group definition.

        leaf lifetime  {
            type  uint32 {
                 range "60..86400"  {
                    description "60..86400: Supported range 60 - 86400";
                 }
            }
            description "This attribute configures IPsec lifetime for ISAKMP policy.";
        } // END of lifetime definition.

        leaf ike-version  {
            type  ipi-ipsec-types:ipsec_ike_version_t;
            description "This attribute configures IKE version for ISAKMP policy.";
        } // END of ike-version definition.

        leaf encryption  {
            type  ipi-ipsec-types:ipsec_encryption_algorithm_t;
            description "This attribute configures IPsec Encryption algorithm for ISAKMP
                        policy.";
        } // END of encryption definition.

    } // END of ipsec-policy-config definition.
    grouping ipsec-policy-top {
        description
            "IPsec policy grouping";
        container policies {
            if-feature feature-list:HAVE_IPSEC_HW;
            description
                "Used to configure IPsec security services";

            list policy {
                key "sequence-number";
                description
                    "IPsec policy";
                leaf sequence-number  {
                    type  leafref {
                        path  "../config/sequence-number";
                    }
                    description "Sequence number";
                } // END of sequence-number definition.

                container config {
                    description
                        "IPsec policy configuration data";
                    uses ipsec-policy-config;
                } // END of config-container definition.
                container state {
                    config false;
                    description
                        "IPsec policy operational state data";
                    uses ipsec-policy-config;
                } // END of state-container definition.
                uses ipsec-policy-authentication-top;
                uses ipsec-policy-peer-top;
                uses ipsec-policy-isakmp-enable-top;
            } // End of policy-list
        } // END of policies-container definition.
    } // END of ipsec-policy-top definition.
    grouping ipsec-transform-set-state {
        description
            "IPsec Transform-set State Grouping";
        leaf transform-set-protocol  {
            type  ipi-ipsec-types:ipsec_ts_protocol_t;
            description "This attribute is used to get transform-set protocol information.";
        } // END of transform-set-protocol definition.

    } // END of ipsec-transform-set-state definition.
    grouping ipsec-transform-set-config {
        description
            "IPsec Transform-set Configuration Grouping";
        leaf transform-set-name  {
            type  string {
                length "1..127";
                pattern "[^?' =,>|]+";
            }
            description "This attribute configures IPsec transform-set name.";
        } // END of transform-set-name definition.

        leaf transform-set-mode  {
            type  ipi-ipsec-types:ipsec_ts_mode_t;
            default "transport";
            description "This attribute is used to configure mode for a transform-set.";
        } // END of transform-set-mode definition.

    } // END of ipsec-transform-set-config definition.
    grouping ipsec-transform-set-ah-config {
        description
            "IPsec Transform-set AH Authentication Configuration Grouping";
        leaf ah-authentication  {
            type  ipi-ipsec-types:ipsec_ah_authentication_t;
            description "This attribute configures IPsec AH authentication type.";
        } // END of ah-authentication definition.

    } // END of ipsec-transform-set-ah-config definition.
    grouping ipsec-transform-set-ah-top {
        description
            "IPsec Transform-set AH Configuration Grouping Top";
        container ah-auth {
            description
                "IPsec Transform-set AH Authentication Top Grouping";
            container config {
                description
                    "IPsec Transform-set Configuration data";
                uses ipsec-transform-set-ah-config;
            } // END of config-container definition.
            container state {
                config false;
                description
                    "IPsec Transform-set Operational state data";
                uses ipsec-transform-set-ah-config;
            } // END of state-container definition.
        } // END of ah-auth-container definition.
    } // END of ipsec-transform-set-ah-top definition.
    grouping ipsec-transform-set-esp-config {
        description
            "IPsec Transform-set ESP Configuration Grouping";
        leaf esp-authentication  {
            type  ipi-ipsec-types:ipsec_esp_authentication_t;
            mandatory true;
            description "This attribute configures IPsec ESP authentication type.";
        } // END of esp-authentication definition.

        leaf esp-encryption  {
            type  ipi-ipsec-types:ipsec_esp_encryption_t;
            mandatory true;
            description "This attribute configures IPsec ESP encryption type.";
        } // END of esp-encryption definition.

    } // END of ipsec-transform-set-esp-config definition.
    grouping ipsec-transform-set-esp-top {
        description
            "IPsec Transform-set ESP Configuration Grouping Top";
        container esp-auth {
            description
                "IPsec Transform-set ESP Top Grouping";
            container config {
                presence "yes";
                description
                    "IPsec Transform-set ESP Configuration data";
                uses ipsec-transform-set-esp-config;
            } // END of config-container definition.
            container state {
                config false;
                description
                    "IPsec Transform-set ESP Operational state data";
                uses ipsec-transform-set-esp-config;
            } // END of state-container definition.
        } // END of esp-auth-container definition.
    } // END of ipsec-transform-set-esp-top definition.
    grouping ipsec-transform-set-top {
        description
            "IPsec Transform Set Grouping Top";
        container transform-sets {
            description
                "IPsec transform-sets Set Grouping";

            list transform-set {
                key "transform-set-name";
                description
                    "IPsec transform-set";
                leaf transform-set-name  {
                    type  leafref {
                        path  "../config/transform-set-name";
                    }
                    description "IPsec transform-set name";
                } // END of transform-set-name definition.

                container config {
                    description
                        "IPsec transform-set configuration data";
                    uses ipsec-transform-set-config;
                } // END of config-container definition.
                container state {
                    config false;
                    description
                        "IPsec transform-set operational state data";
                    uses ipsec-transform-set-config;
                    uses ipsec-transform-set-state;
                } // END of state-container definition.
                uses ipsec-transform-set-ah-top;
                uses ipsec-transform-set-esp-top;
            } // End of transform-set-list
        } // END of transform-sets-container definition.
    } // END of ipsec-transform-set-top definition.
    grouping ipsec-crypto-map-session-match-config {
        description
            "IPsec Crypto Map Session Match Configuration Grouping";
        leaf ipv4-acl  {
            type  string {
                length "1..128";
                pattern "[^?' =,>|]+";
            }
            description "This attributes associates IPsec crypto-map to an IPv4 ACL object.";
        } // END of ipv4-acl definition.

        leaf ipv6-acl  {
            type  string {
                length "1..128";
                pattern "[^?' =,>|]+";
            }
            description "This attributes associates IPsec crypto-map to an IPv6 ACL object.";
        } // END of ipv6-acl definition.

    } // END of ipsec-crypto-map-session-match-config definition.
    grouping ipsec-crypto-map-session-match-top {
        description
            "IPsec Crypto Map Session Match grouping";
        container match-rule {
            if-feature feature-list:HAVE_IPSEC_HW;
            description
                "IPsec Crypto Map Session Match";
            container config {
                description
                    "Configuration data for IPsec Crypto Map Session Match";
                uses ipsec-crypto-map-session-match-config;
            } // END of config-container definition.
            container state {
                config false;
                description
                    "Operational state data for IPsec Crypto Map Session Match";
                uses ipsec-crypto-map-session-match-config;
            } // END of state-container definition.
        } // END of match-rule-container definition.
    } // END of ipsec-crypto-map-session-match-top definition.
    grouping ipsec-crypto-map-session-key-config {
        description
            "IPsec Crypto Map Session Key Configuration Grouping";
        leaf direction  {
            type  ipi-ipsec-types:ipsec_session_key_direction_t;
            description "This attributes configures IPsec Crypto Map session key.";
        } // END of direction definition.

        leaf protocol  {
            type  ipi-ipsec-types:ipsec_session_key_protocol_t;
            description "This attributes configures IPsec Map session key protocol.";
        } // END of protocol definition.

        leaf security-parameter-index  {
            type  uint16 {
                 range "0..4096"  {
                    description "0..4096: Supported range 0 - 4096";
                 }
            }
            description "This attributes configures IPsec Map session key security parameter
                        index (SPI).";
        } // END of security-parameter-index definition.

        leaf cipher  {
            type  string {
                length "1..128";
                pattern "[^?' =,>|]+";
            }
            mandatory true;
            description "This attributes configures IPsec Map session key cipher.";
        } // END of cipher definition.

        leaf authentication-key  {
            type  string {
                length "1..32";
                pattern "[^?' =,>|]+";
            }
            mandatory true;
            description "This attributes configures IPsec Map session key authenticator.";
        } // END of authentication-key definition.

    } // END of ipsec-crypto-map-session-key-config definition.
    grouping ipsec-crypto-map-session-key-top {
        description
            "IPsec Crypto Map Session Key grouping";
        container session-keys {
            description
                "IPsec Crypto Map Session Keys";

            list session-key {
                key "direction protocol security-parameter-index";
                description
                    "IPsec Crypto Map Session Key";
                leaf direction  {
                    type  leafref {
                        path  "../config/direction";
                    }
                    description "Crypto Map session key";
                } // END of direction definition.

                leaf protocol  {
                    type  leafref {
                        path  "../config/protocol";
                    }
                    description "Crypto Map session key protocol";
                } // END of protocol definition.

                leaf security-parameter-index  {
                    type  leafref {
                        path  "../config/security-parameter-index";
                    }
                    description "Crypto Map session key security parameter index (SPI)";
                } // END of security-parameter-index definition.

                container config {
                    description
                        "Configuration data for IPsec Crypto Map Session Key";
                    uses ipsec-crypto-map-session-key-config;
                } // END of config-container definition.
                container state {
                    config false;
                    description
                        "Operational state data for IPsec Crypto Map Session Key";
                    uses ipsec-crypto-map-session-key-config;
                } // END of state-container definition.
            } // End of session-key-list
        } // END of session-keys-container definition.
    } // END of ipsec-crypto-map-session-key-top definition.
    grouping ipsec-crypto-map-session-peer-config {
        description
            "IPsec Crypto Map Session Peer Configuration Grouping";
        leaf peer  {
            type  inet:ip-address;
            description "This attribute configures the Map session peer IP address.";
        } // END of peer definition.

        leaf spi  {
            type  ipi-ipsec-types:ipsec_peer_spi_t;
            mandatory true;
            description "This attribute configures the peer security parameter index (SPI).";
        } // END of spi definition.

    } // END of ipsec-crypto-map-session-peer-config definition.
    grouping ipsec-crypto-map-session-peer-top {
        description
            "IPsec Crypto Map Session Peer Address grouping";
        container peer-addresses {
            description
                "IPsec Crypto Map Session Peer Addresses";

            list peer-address {
                key "peer";
                description
                    "IPsec Crypto Map Session Peer Address";
                leaf peer  {
                    type  leafref {
                        path  "../config/peer";
                    }
                    description "Map session peer IP address";
                } // END of peer definition.

                container config {
                    description
                        "Configuration data for IPsec Crypto Map Session Peer Address";
                    uses ipsec-crypto-map-session-peer-config;
                } // END of config-container definition.
                container state {
                    config false;
                    description
                        "Operational state data for IPsec Crypto Map Session Peer Address";
                    uses ipsec-crypto-map-session-peer-config;
                } // END of state-container definition.
            } // End of peer-address-list
        } // END of peer-addresses-container definition.
    } // END of ipsec-crypto-map-session-peer-top definition.
    grouping ipsec-crypto-map-session-ts-config {
        description
            "IPsec Crypto Map Session TS Configuration Grouping";
        leaf transform-set-name  {
            type  leafref {
                path  "/ipsec/transform-sets/transform-set/transform-set-name";
            }
            description "This attributes associates and Transform-Set object to a Crypto Map
                        session object.";
        } // END of transform-set-name definition.

    } // END of ipsec-crypto-map-session-ts-config definition.
    grouping ipsec-crypto-map-session-ts-top {
        description
            "IPsec Crypto Map Session Transform Set Grouping";
        container transform-sets {
            description
                "IPsec Crypto Map Session Transform Sets";

            list transform-set {
                key "transform-set-name";
                description
                    "IPsec Crypto Map Session Transform Set";
                leaf transform-set-name  {
                    type  leafref {
                        path  "../config/transform-set-name";
                    }
                    description "Map session transform-set name";
                } // END of transform-set-name definition.

                container config {
                    description
                        "Configuration data for IPsec Crypto Map Session Transform Set";
                    uses ipsec-crypto-map-session-ts-config;
                } // END of config-container definition.
                container state {
                    config false;
                    description
                        "Operational state data for IPsec Crypto Map Session Transform Set";
                    uses ipsec-crypto-map-session-ts-config;
                } // END of state-container definition.
            } // End of transform-set-list
        } // END of transform-sets-container definition.
    } // END of ipsec-crypto-map-session-ts-top definition.
    grouping ipsec-crypto-map-session-config {
        description
            "IPsec Crypto Map Session Configuration Grouping";
        leaf sequence-id  {
            type  uint16 {
                 range "1..65535"  {
                    description "1..65535: Supported range 1 - 65535";
                 }
            }
            description "This attribute configures the Cripto Map entry sequence number.";
        } // END of sequence-id definition.

    } // END of ipsec-crypto-map-session-config definition.
    grouping ipsec-crypto-map-session-top {
        description
            "IPsec Crypto Map Session Grouping";
        container sessions {
            description
                "IPsec Crypto Map Sessions";

            list session {
                key "sequence-id";
                description
                    "IPsec Crypto Map Session";
                leaf sequence-id  {
                    type  leafref {
                        path  "../config/sequence-id";
                    }
                    description "Map sequence-id";
                } // END of sequence-id definition.

                container config {
                    description
                        "Configuration data for IPsec Crypto Map Session";
                    uses ipsec-crypto-map-session-config;
                } // END of config-container definition.
                container state {
                    config false;
                    description
                        "Operational state data for IPsec Crypto Map Session";
                    uses ipsec-crypto-map-session-config;
                } // END of state-container definition.
                uses ipsec-crypto-map-session-ts-top;
                uses ipsec-crypto-map-session-peer-top;
                uses ipsec-crypto-map-session-key-top;
                uses ipsec-crypto-map-session-match-top;
            } // End of session-list
        } // END of sessions-container definition.
    } // END of ipsec-crypto-map-session-top definition.
    grouping ipsec-crypto-map-local-address-config {
        description
            "IPsec Crypto Map Local Address Configuration Grouping";
        leaf interface-name  {
            type  string {
                length "1..33";
                pattern "[^?' =,>|]+";
            }
            description "This attribute configure a system interface on crypto map to identify
                        itself to a remote peer.";
        } // END of interface-name definition.

    } // END of ipsec-crypto-map-local-address-config definition.
    grouping ipsec-crypto-map-local-address-top {
        description
            "IPsec Crypto Map Local Address Configuration Grouping Top";
        container local-address {
            if-feature feature-list:HAVE_IPSEC_HW;
            description
                "IPsec Crypto Map Local Address Top";
            container config {
                description
                    "IPsec Crypto Map Local Address Configuration data";
                uses ipsec-crypto-map-local-address-config;
            } // END of config-container definition.
            container state {
                config false;
                description
                    "IPsec Crypto Map Local Address Operational state data";
                uses ipsec-crypto-map-local-address-config;
            } // END of state-container definition.
        } // END of local-address-container definition.
    } // END of ipsec-crypto-map-local-address-top definition.
    grouping ipsec-crypto-map-config {
        description
            "IPsec Crypto Map Configuration Grouping";
        leaf name  {
            type  string {
                length "1..127";
                pattern "[^?' =,>|]+";
            }
            description "This attribute configures the IPsec Crypto Map name.";
        } // END of name definition.

        leaf sa-type  {
            type  ipi-ipsec-types:ipsec_sa_type_t;
            mandatory true;
            description "This attribute configures the IPsec Crypto Map Security Association
                        type.";
        } // END of sa-type definition.

    } // END of ipsec-crypto-map-config definition.
    grouping ipsec-crypto-map-top {
        description
            "IPsec Crypto Map grouping";
        container crypto-maps {
            description
                "IPsec Crypto Maps";

            list crypto-map {
                key "name";
                description
                    "IPsec Crypto Map";
                leaf name  {
                    type  leafref {
                        path  "../config/name";
                    }
                    description "IPsec Crypto Map name";
                } // END of name definition.

                container config {
                    description
                        "IPsec Crypto Map configuration data";
                    uses ipsec-crypto-map-config;
                } // END of config-container definition.
                container state {
                    config false;
                    description
                        "IPsec Crypto Map operational state data";
                    uses ipsec-crypto-map-config;
                } // END of state-container definition.
                uses ipsec-crypto-map-local-address-top;
                uses ipsec-crypto-map-session-top;
            } // End of crypto-map-list
        } // END of crypto-maps-container definition.
    } // END of ipsec-crypto-map-top definition.

    grouping  ipsec-grouping {
    description
        "IPsec";
    container ipsec {
        if-feature feature-list:HAVE_IPSEC;
        if-feature feature-list:HAVE_TUNNEL;
        description
            "IPsec";
        uses ipsec-policy-top;
        uses ipsec-transform-set-top;
        uses ipsec-crypto-map-top;
        uses ipsec-interface-top;
        uses ipsec-interface-tunnel-top;
    } // END of ipsec-container definition.
    } // END of ipsec-grouping definition.

    uses ipsec-grouping;

    rpc ipsec-clear-crypto-isakmp {
        if-feature feature-list:HAVE_IPSEC_HW;
        if-feature feature-list:HAVE_TUNNEL;
        if-feature feature-list:HAVE_IPSEC;
        description "Clear crypto isakmp";
    }

    rpc ipsec-clear-crypto-sa-map {
        if-feature feature-list:HAVE_IPSEC_HW;
        if-feature feature-list:HAVE_TUNNEL;
        if-feature feature-list:HAVE_IPSEC;
        description "Clear crypto sa map";
        input  {
            leaf name  {
                type string {
                    length "1..127";
                }
                mandatory true;
                description "Use this attribute to specify IPsec crypto map sa name to clear data.";
            }
        }
    }

    rpc ipsec-clear-crypto-sa-peer {
        if-feature feature-list:HAVE_IPSEC_HW;
        if-feature feature-list:HAVE_TUNNEL;
        if-feature feature-list:HAVE_IPSEC;
        description "Clear crypto sa peer";
        input  {
            leaf peer  {
                type inet:ip-address;
                mandatory true;
                description "Use this attribute to specify IPsec crypto map sa peer to clear data.";
            }
        }
    }

}
