/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-nsm-arp.yang
*
*/

module ipi-nsm-arp {

    yang-version 1.1;

    namespace   "http://www.ipinfusion.com/yang/ocnos/ipi-nsm-arp";

    prefix "ipi-nsm-arp";

    import cml-data-types {
        prefix cml-data-types;
        revision-date 2026-05-15;
    }

    import ipi-interface {
        prefix ipi-interface;
        revision-date 2026-03-10;
    }

    import ietf-inet-types {
        prefix inet;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Address Resolution Protocol";


    revision "2025-11-17" {
        description "MAC normalization function for the vlan mac-address attribute.";
        reference " 0.7.4.";
    }

    revision "2024-09-18" {
        description "Updating top container as nsm-arp";
        reference " 0.7.3.";
    }

    revision "2023-01-05" {
        description "Leafref correction for config container";
        reference " 0.7.2.";
    }

    revision "2022-11-29" {
        description "Addressed make cmlgen warnings";
        reference " 0.7.1.";
    }

    revision "2022-10-31" {
        description "Enclosed the objectlist with container";
        reference " 0.7.0.";
    }

    revision "2022-06-01" {
        description "Updated the yang file with feature";
        reference " 0.5.0.";
    }

    revision "2021-11-16" {
        description "Added some if-feature to fix customer SKU compilation";
        reference " 0.4.0.";
    }

    revision "2021-09-01" {
        description "Changed base interface module's switchport attribute name and the datatype from bool to empty";
        reference " 0.3.0.";
    }

    revision "2020-12-15" {
        description "Change to have data-types in lower case instead of camel case";
        reference " 0.2.0.";
    }

    revision "2020-07-30" {
        description "Initial Version";
        reference " 0.1.0.";
    }



    typedef  cml_arp_type_t {
        type enumeration {
            enum static {
                value 1;
                description "Static ARP";
            }
            enum dynamic {
                value 2;
                description "Dynamic ARP";
            }
        }
        description "type definition for CML_ARP_TYPE_T";
    }    grouping ip-arp-state {
        description
            "ARP state information";
        leaf interface-name  {
            type  string {
                length "1..1965";
                pattern "[^?' =,>|]+";
            }
            description "Name of the interface";
        } // END of interface-name definition.

        leaf arp-type  {
            type  cml_arp_type_t;
            description "This attribute describes the ARP type";
        } // END of arp-type definition.

    } // END of ip-arp-state definition.
    grouping ip-arp-mac-address-top {
        description
            "Top level grouping for ARP mac address information";
        container link-layer-addresses {
            description
                "link-layer addresses of the neighbor";

            list link-layer-address {
                key "mac-address";
                description
                    "link-layer address of the neighbor";
                leaf mac-address  {
                    type  leafref {
                        path  "../config/mac-address";
                    }
                    description "This attribute describes the MAC address of the ARP";
                } // END of mac-address definition.

                container config {
                    description
                        "link-layer address information";
                    uses link-layer-top;
                } // END of config-container definition.
                container state {
                    config false;
                    description
                        "Operational state data";
                    uses link-layer-top;
                    uses ip-arp-state;
                } // END of state-container definition.
            } // End of link-layer-address-list
        } // END of link-layer-addresses-container definition.
    } // END of ip-arp-mac-address-top definition.
    grouping link-layer-top {
        description
            "link-layer address information";
        leaf mac-address  {
            type  cml-data-types:cml_mac_addr_t {
                length "1..1965";
            }
            description "This attribute describes the MAC address of the ARP";
        } // END of mac-address definition.

        leaf respond-to-arp-request  {
            type  empty;
            description "This attribute is used to respond the ARP requests for the IP address";
        } // END of respond-to-arp-request definition.

    } // END of link-layer-top definition.
    grouping global-dynamic-ip-arp {
        description
            "Dynamic ARP entry information";
        container dynamic-entries {
            config false;
            description
                "Top level Dynamic ARP entry information";
            leaf arp-type  {
                type  cml_arp_type_t;
                description "This attribute describes the ARP type";
            } // END of arp-type definition.


            list entry {
                key "ip-address";
                config false;
                description
                    "Dynamic ARP entry";
                leaf ip-address  {
                    type  inet:ipv4-address;
                    description "This attribute describes the IP address of the ARP";
                } // END of ip-address definition.

                leaf mac-address  {
                    type  cml-data-types:cml_mac_addr_t {
                        length "1..1965";
                    }
                    description "This attribute describes the MAC address of the ARP";
                } // END of mac-address definition.

                leaf interface-name  {
                    type  string {
                        length "1..1965";
                        pattern "[^?' =,>|]+";
                    }
                    description "Name of the Interface";
                } // END of interface-name definition.

            } // End of entry-list
        } // END of dynamic-entries-container definition.
    } // END of global-dynamic-ip-arp definition.
    grouping global-ip-arp {
        description
            "static ARP entry information";
        container entries {
            description
                "static ARP entries information";

            list entry {
            // when " ipi-nsm-arp:nsm-arp/entries/entry/link-layer-addresses/link-layer-address/mac-address ";
                key "ip-address";
                description
                    "static ARP entry information";
                leaf ip-address  {
                    type  leafref {
                        path  "../config/ip-address";
                    }
                    description "This attribute describes the IP address of the ARP";
                } // END of ip-address definition.

                container config {
                    description
                        "static ARP entry information";
                    leaf ip-address  {
                        type  inet:ipv4-address;
                        description "This attribute describes the IP address of the ARP";
                    } // END of ip-address definition.

                } // END of config-container definition.
                container state {
                    config false;
                    description
                        "Operational state data";
                    leaf ipv4-address  {
                        type  inet:ipv4-address;
                        description "This attribute describes the IP address of the ARP";
                    } // END of ipv4-address definition.

                } // END of state-container definition.
                uses ip-arp-mac-address-top;
            } // End of entry-list
        } // END of entries-container definition.
    } // END of global-ip-arp definition.
    grouping arp-interface-config {
        description
            "Configuration data for arp on each interface";
        leaf name  {
            type  leafref {
                path  "/ipi-interface:interfaces/ipi-interface:interface/ipi-interface:name";
            }
            description "Name of the Interface";
        } // END of name definition.

        leaf enable-proxy-arp  {
            type  empty;
            description "Use this Attribute to set the Internet protocol proxy arp";
        } // END of enable-proxy-arp definition.

        leaf arp-ageing-timeout  {
            type  uint16 {
                 range "1..3000"  {
                    description "1..3000: Supported range 1 - 3000";
                 }
            }
            default "3000";
            description "This attribute is used to set ARP Ageing timeout in sec and arp age
                        timeout value to interface";
        } // END of arp-ageing-timeout definition.

    } // END of arp-interface-config definition.
    grouping arp-interface-top {
        description
            "Top level container for arp on each interface";
        container interfaces {
            description
                "Top level container for arp on each interface";

            list interface {
            // when " not(/ipi-interface:interfaces/ipi-interface:interface/ipi-interface:config/ipi-interface:enable-switchport) ";
                key "name";
                description
                    "List of interfaces on which arp is enabled/available";
                leaf name  {
                    type  leafref {
                        path  "../config/name";
                    }
                    description "The textual name of the interface. The value of this object should be
                                the name of the interface as assigned by the local device and should
                                be suitable for use in commands entered at the device's `console'.
                                This might be a text name, such as `le0' or a simple port number, such
                                as `1', depending on the interface naming syntax of the device. If
                                several entries in the ifTable together represent a single interface
                                as named by the device, then each will have the same value of name.
                                Note that for an agent which responds to SNMP queries concerning an
                                interface on some other (proxied) device, then the value of name for
                                such an interface is the proxied device's local name for it. If there
                                is no local name, or this object is otherwise not applicable, then
                                this object contains a zero-length string.";
                } // END of name definition.

                container config {
                    description
                        "Configuration data for ndd on each interface";
                    uses arp-interface-config;
                } // END of config-container definition.
                container state {
                    config false;
                    description
                        "Operational state data";
                    uses arp-interface-config;
                } // END of state-container definition.
            } // End of interface-list
        } // END of interfaces-container definition.
    } // END of arp-interface-top definition.

    grouping  nsm-arp-grouping {
    description
        "arp global level information";
    container nsm-arp {
        if-feature feature-list:HAVE_L3;
        if-feature feature-list:NOT_HAVE_NDD;
        description
            "arp global level information";
        uses global-ip-arp;
        uses global-dynamic-ip-arp;
        uses arp-interface-top;
    } // END of nsm-arp-container definition.
    } // END of nsm-arp-grouping definition.

    uses nsm-arp-grouping;

    rpc clear-arp-cache {
        if-feature feature-list:HAVE_L3;
        if-feature feature-list:NOT_HAVE_NDD;
        description "clear arp cache";
    }

}
