/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-vrrp-ipv6.yang
*
*/

submodule ipi-vrrp-ipv6 {

    yang-version 1.1;

    belongs-to  ipi-vrrp { prefix ipi-vrrp; }

    import feature-list {
        prefix feature-list;
        revision-date 2026-09-15;
    }

    import ietf-inet-types {
        prefix inet;
        revision-date 2013-07-15;
    }

    include ipi-vrrp-common { revision-date 2025-02-19;}
    organization
        "IP Infusion Inc.";

    contact
        "Address: 3965 Freedom Circle, Suite 200, Santa Clara, CA 95054
         Phone: +1 408-400-1900
         E-mail: support@ipinfusion.com
         Web: http://www.ipinfusion.com/";

    description
        "Virtual Router Redundancy Protocol IPV6 configuration";


    revision "2024-03-27" {
        description "Implicit delete tag removed for 'ipv6-instances/ipv6-instance/interfaces/interface/config' container";
        reference " 0.7.1.";
    }

    revision "2023-09-28" {
        description "Added implicit delete tag for config";
        reference " 0.7.0.";
    }

    revision "2023-02-02" {
        description "Updated missing Description";
        reference " 0.6.0.";
    }

    revision "2022-08-24" {
        description "Update to add global IPV6 address as virtual ip";
        reference " 0.5.2.";
    }

    revision "2022-08-10" {
        description "Debug hierarchy change";
        reference " 0.5.0.";
    }

    revision "2022-06-01" {
        description "Updated the yang file with feature";
        reference " 0.4.0.";
    }

    revision "2022-04-22" {
        description "Enable of VRRP protocol on its own container";
        reference " 0.3.0.";
    }

    revision "2021-09-03" {
        description "Update descriptions of attribute";
        reference " 0.1.2.";
    }

    revision "2021-08-26" {
        description "Change containers to use IPV6 string";
        reference " 0.1.1.";
    }

    revision "2021-06-18" {
        description "Restructured module in accordance with OpenConfig style";
        reference " 0.1.0.";
    }

    grouping vrrp-interface-state-ipv6-addresses-top {
        description
            "Grouping for VRRP IPV6 interface instance state";
        container addresses {
            config false;
            description
                "Virtual Router Redundancy Protocol Socket interface IPV6 instance
                        adresses";
            container state {
                config false;
                description
                    "Virtual Router Redundancy Protocol Socket interface IPV6 instance
                            adresses state";
                leaf operational-primary-ipv6  {
                    type  inet:ipv6-address;
                    description "Operational primary IPV6 address";
                } // END of operational-primary-ipv6 definition.

                leaf operational-master-ipv6  {
                    type  inet:ipv6-address;
                    description "Operational master IPV6 address";
                } // END of operational-master-ipv6 definition.

            } // END of state-container definition.
        } // END of addresses-container definition.
    } // END of vrrp-interface-state-ipv6-addresses-top definition.
    grouping vrrp-ipv6-protocol-enable-top {
        description
            "Grouping for VRRP IPv6 protocol enable";
        container protocol-enable {
            description
                "VRRP IPv6 protocol enable container";
            container config {
                description
                    "VRRP IPv6 protocol enable configuration";
                uses vrrp-protocol-enable-config;
            } // END of config-container definition.
            container state {
                config false;
                description
                    "VRRP IPv6 protocol enable state";
                uses vrrp-protocol-enable-config;
            } // END of state-container definition.
        } // END of protocol-enable-container definition.
    } // END of vrrp-ipv6-protocol-enable-top definition.
    grouping vrrp-ipv6-interface-virtual-ip-config {
        description
            "Grouping for VRRP IPV6 Virtual IP configuration";
        leaf virtual-ip-address  {
            type  inet:ipv6-address;
            description "VRRP Virtual IPV6 address";
        } // END of virtual-ip-address definition.

        leaf ip-address-owner  {
            type  boolean;
            description "Use this attribute to set the virtual IP address for the VRRP virtual
                        router as VRRP Owner. This is the IP address used by end hosts to
                        address their default gateway.";
        } // END of ip-address-owner definition.

    } // END of vrrp-ipv6-interface-virtual-ip-config definition.
    grouping vrrp-ipv6-interface-virtual-ip-top {
        description
            "Grouping for VRRP IPV6 Virtual IP";
        container virtual-ip-addresses {
            if-feature feature-list:HAVE_IPV6;
            description
                "Virtual Router Redundancy Protocol IPV6 addresses";

            list virtual-ip-address {
                key "virtual-ip-address";
                description
                    "IPV6 Session Virtual IP";
                leaf virtual-ip-address  {
                    type  leafref {
                        path  "../config/virtual-ip-address";
                    }
                    description "VRRP Virtual IPV6 address";
                } // END of virtual-ip-address definition.

                container config {
                    description
                        "Configuration data for IPV6 Session Virtual IP";
                    uses vrrp-ipv6-interface-virtual-ip-config;
                } // END of config-container definition.
                container state {
                    config false;
                    description
                        "Virtual Router Redundancy Protocol IPV6 Interface State";
                    uses vrrp-ipv6-interface-virtual-ip-config;
                } // END of state-container definition.
            } // End of virtual-ip-address-list
        } // END of virtual-ip-addresses-container definition.
    } // END of vrrp-ipv6-interface-virtual-ip-top definition.
    grouping vrrp-ipv6-interface-config {
        description
            "Grouping for VRRP IPV6 instances configuration";
        leaf primary-ip-address  {
            type  inet:ipv6-address;
            description "Use this attribute to set the operational-ip address for the virtual
                        router";
        } // END of primary-ip-address definition.

    } // END of vrrp-ipv6-interface-config definition.
    grouping vrrp-ipv6-interfaces-top {
        description
            "Grouping for VRRP IPV6 interfaces";
        container interfaces {
            description
                "Virtual Router Redundancy Protocol IPV6 Interfaces";

            list interface {
                key "interface-name";
                description
                    "VRRP IPV6 Interface list";
                leaf interface-name  {
                    type  leafref {
                        path  "../config/interface-name";
                    }
                    description "Use this attribute to configure an VRRP routing process for an
                                interface.";
                } // END of interface-name definition.

                container config {
                    description
                        "Virtual Router Redundancy Protocol IPV6 Interface Configuration";
                    uses vrrp-ipv6-interface-config;
                    uses vrrp-common-config;
                } // END of config-container definition.
                container state {
                    config false;
                    description
                        "Virtual Router Redundancy Protocol IPV6 Interface State";
                    uses vrrp-ipv6-interface-config;
                    uses vrrp-common-config;
                } // END of state-container definition.
                uses vrrp-ipv6-protocol-enable-top;
                uses vrrp-ipv6-interface-virtual-ip-top;
                uses vrrp-interface-tracking-top;
                uses vrrp-interface-state-ipv6-addresses-top;
                uses vrrp-interface-state-session-info-top;
                uses vrrp-interface-state-reasons-top;
                uses vrrp-interface-state-session-status-top;
                uses vrrp-interface-state-timers-top;
                uses vrrp-interface-statistic-top;
                uses vrrp-interface-errors-top;
                uses vrrp-object-tracking-top;
            } // End of interface-list
        } // END of interfaces-container definition.
    } // END of vrrp-ipv6-interfaces-top definition.
    grouping vrrp-ipv6-instances-top {
        description
            "Grouping for VRRP IPV6 instances";
        container ipv6-instances {
            description
                "Virtual Router Redundancy Protocol IPV6 Instances";

            list ipv6-instance {
                key "virtual-router-id";
                description
                    "VRRP IPV6 instance related operations";
                leaf virtual-router-id  {
                    type  leafref {
                        path  "../config/virtual-router-id";
                    }
                    description "Virtual router identifier";
                } // END of virtual-router-id definition.

                container config {
                    description
                        "Virtual Router Redundancy Protocol IPV6 Instances Configuration";
                    uses vrrp-ip-instance-config;
                } // END of config-container definition.
                container state {
                    config false;
                    description
                        "Virtual Router Redundancy Protocol IPV6 Instances State";
                    uses vrrp-ip-instance-config;
                } // END of state-container definition.
                uses vrrp-ipv6-interfaces-top;
            } // End of ipv6-instance-list
        } // END of ipv6-instances-container definition.
    } // END of vrrp-ipv6-instances-top definition.


}
