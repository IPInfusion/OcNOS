/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-vrrp-ipv4.yang
*
*/

submodule ipi-vrrp-ipv4 {

    yang-version 1.1;

    belongs-to  ipi-vrrp { prefix ipi-vrrp; }

    import feature-list {
        prefix feature-list;
        revision-date 2026-09-15;
    }

    import ietf-inet-types {
        prefix inet;
        revision-date 2013-07-15;
    }

    include ipi-vrrp-common { revision-date 2025-02-19;}
    organization
        "IP Infusion Inc.";

    contact
        "Address: 3965 Freedom Circle, Suite 200, Santa Clara, CA 95054
         Phone: +1 408-400-1900
         E-mail: support@ipinfusion.com
         Web: http://www.ipinfusion.com/";

    description
        "Virtual Router Redundancy Protocol IPV4 configuration";


    revision "2024-03-27" {
        description "Implicit delete tag removed for 'ipv4-instances/ipv4-instance/interfaces/interface/config' container.";
        reference " 0.7.1.";
    }

    revision "2023-09-28" {
        description "Added implicit delete tag for config";
        reference " 0.7.0.";
    }

    revision "2023-02-02" {
        description "Updated missing Description";
        reference " 0.6.0.";
    }

    revision "2022-08-10" {
        description "Debug hierarchy change";
        reference " 0.5.0.";
    }

    revision "2022-06-01" {
        description "Updated the yang file with feature";
        reference " 0.4.0.";
    }

    revision "2022-04-22" {
        description "Enable of VRRP protocol on its own container";
        reference " 0.3.0.";
    }

    revision "2021-09-03" {
        description "Update descriptions of attribute";
        reference " 0.1.1.";
    }

    revision "2021-06-18" {
        description "Restructured module in accordance with OpenConfig style";
        reference " 0.1.0.";
    }

    grouping vrrp-interface-state-addresses-top {
        description
            "Grouping for VRRP IPV4 interface instance state";
        container addresses {
            config false;
            description
                "Virtual Router Redundancy Protocol Socket interface IPV4 instance
                        adresses";
            container state {
                config false;
                description
                    "Virtual Router Redundancy Protocol Socket interface IPV4 instance
                            adresses state";
                leaf operational-primary-address  {
                    type  inet:ipv4-address;
                    description "Operational primary IP address";
                } // END of operational-primary-address definition.

                leaf operational-master-address  {
                    type  inet:ipv4-address;
                    description "Operational master IP address";
                } // END of operational-master-address definition.

            } // END of state-container definition.
        } // END of addresses-container definition.
    } // END of vrrp-interface-state-addresses-top definition.
    grouping vrrp-ipv4-protocol-enable-top {
        description
            "Grouping for VRRP IPv4 protocol enable";
        container protocol-enable {
            description
                "VRRP IPv4 protocol enable container";
            container config {
                description
                    "VRRP IPv4 protocol enable configuration";
                uses vrrp-protocol-enable-config;
            } // END of config-container definition.
            container state {
                config false;
                description
                    "VRRP IPv4 protocol enable state";
                uses vrrp-protocol-enable-config;
            } // END of state-container definition.
        } // END of protocol-enable-container definition.
    } // END of vrrp-ipv4-protocol-enable-top definition.
    grouping vrrp-ipv4-interface-virtual-ip-config {
        description
            "Grouping for VRRP IPV4 Virtual IP configuration";
        leaf virtual-ip-address  {
            type  inet:ipv4-address;
            mandatory true;
            description "VRRP Virtual ip address";
        } // END of virtual-ip-address definition.

        leaf ip-address-owner  {
            type  boolean;
            mandatory true;
            description "Use this attribute to set the virtual IP address for the VRRP virtual
                        router as VRRP Owner. This is the IP address used by end hosts to
                        address their default gateway.";
        } // END of ip-address-owner definition.

    } // END of vrrp-ipv4-interface-virtual-ip-config definition.
    grouping vrrp-ipv4-interface-virtual-ip-top {
        description
            "Grouping for VRRP IPV4 Virtual IP";
        container virtual-ip {
            description
                "IPV4 Session Virtual IP";
            container config {
                presence "yes";
                description
                    "Configuration data for IPV4 Session Virtual IP";
                uses vrrp-ipv4-interface-virtual-ip-config;
            } // END of config-container definition.
            container state {
                config false;
                description
                    "Virtual Router Redundancy Protocol IPV4 Interface State";
                uses vrrp-ipv4-interface-virtual-ip-config;
            } // END of state-container definition.
        } // END of virtual-ip-container definition.
    } // END of vrrp-ipv4-interface-virtual-ip-top definition.
    grouping vrrp-ipv4-interface-config {
        description
            "Grouping for VRRP IPV4 instances configuration";
        leaf vrrp-v2-compatible  {
            type  empty;
            description "Use this attribute to enable or disable the backward-compatibility
                        feature";
        } // END of vrrp-v2-compatible definition.

        leaf ipv4-exclude-pseudo-header  {
            type  empty;
            description "Use this attribute to excludes the pseudo-header in IPv4 VRRPv3
                        checksum calculation";
        } // END of ipv4-exclude-pseudo-header definition.

        leaf authentication-data  {
            type  string {
                length "1..1965";
                pattern "[^?' =,>|]+";
            }
            description "Use this attribute to include authentication simple text";
        } // END of authentication-data definition.

        leaf primary-ip-address  {
            type  inet:ipv4-address;
            description "Use this attribute to set the operational-ip address for the virtual
                        router";
        } // END of primary-ip-address definition.

        leaf mlag-active-standby  {
            if-feature feature-list:HAVE_MLAG;
            type  empty;
            description "Use this attribute to set active-standby mlag mode";
        } // END of mlag-active-standby definition.

    } // END of vrrp-ipv4-interface-config definition.
    grouping vrrp-ipv4-interfaces-top {
        description
            "Grouping for VRRP IPV4 interfaces";
        container interfaces {
            description
                "Virtual Router Redundancy Protocol IPV4 Interfaces";

            list interface {
                key "interface-name";
                description
                    "VRRP IPV4 Interface list";
                leaf interface-name  {
                    type  leafref {
                        path  "../config/interface-name";
                    }
                    description "Use this attribute to configure an VRRP routing process for an
                                interface.";
                } // END of interface-name definition.

                container config {
                    description
                        "Virtual Router Redundancy Protocol IPV4 Interface Configuration";
                    uses vrrp-ipv4-interface-config;
                    uses vrrp-common-config;
                } // END of config-container definition.
                container state {
                    config false;
                    description
                        "Virtual Router Redundancy Protocol IPV4 Interface State";
                    uses vrrp-ipv4-interface-config;
                    uses vrrp-common-config;
                } // END of state-container definition.
                uses vrrp-ipv4-protocol-enable-top;
                uses vrrp-ipv4-interface-virtual-ip-top;
                uses vrrp-interface-tracking-top;
                uses vrrp-interface-state-addresses-top;
                uses vrrp-interface-state-session-info-top;
                uses vrrp-interface-state-reasons-top;
                uses vrrp-interface-state-session-status-top;
                uses vrrp-interface-state-timers-top;
                uses vrrp-interface-statistic-top;
                uses vrrp-interface-errors-top;
                uses vrrp-object-tracking-top;
            } // End of interface-list
        } // END of interfaces-container definition.
    } // END of vrrp-ipv4-interfaces-top definition.
    grouping vrrp-ipv4-instances-top {
        description
            "Grouping for VRRP IPV4 instances";
        container ipv4-instances {
            description
                "Virtual Router Redundancy Protocol IPV4 Instances";

            list ipv4-instance {
                key "virtual-router-id";
                description
                    "VRRP IPV4 instance related operations";
                leaf virtual-router-id  {
                    type  leafref {
                        path  "../config/virtual-router-id";
                    }
                    description "Virtual router identifier";
                } // END of virtual-router-id definition.

                container config {
                    description
                        "Virtual Router Redundancy Protocol IPV4 Instances Configuration";
                    uses vrrp-ip-instance-config;
                } // END of config-container definition.
                container state {
                    config false;
                    description
                        "Virtual Router Redundancy Protocol IPV4 Instances State";
                    uses vrrp-ip-instance-config;
                } // END of state-container definition.
                uses vrrp-ipv4-interfaces-top;
            } // End of ipv4-instance-list
        } // END of ipv4-instances-container definition.
    } // END of vrrp-ipv4-instances-top definition.


}
