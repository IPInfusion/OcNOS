/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-vrrp.yang
*
*/

module ipi-vrrp {

    yang-version 1.1;

    namespace   "http://www.ipinfusion.com/yang/ocnos/ipi-vrrp";

    prefix "ipi-vrrp";

    import cml-data-types {
        prefix cml-data-types;
        revision-date 2026-05-15;
    }

    import ietf-inet-types {
        prefix inet;
        revision-date 2013-07-15;
    }

    import ipi-vrrp-types {
        prefix ipi-vrrp-types;
        revision-date 2022-11-03;
    }

    import feature-list {
        prefix feature-list;
        revision-date 2026-09-15;
    }

    include ipi-vrrp-debug { revision-date 2022-08-17;}
    include ipi-vrrp-global { revision-date 2022-08-17;}
    include ipi-vrrp-ipv4 { revision-date 2024-03-27;}
    include ipi-vrrp-ipv6 { revision-date 2024-03-27;}
    include ipi-vrrp-common { revision-date 2025-02-19;}
    organization
        "IP Infusion Inc.";

    contact
        "Address: 3965 Freedom Circle, Suite 200, Santa Clara, CA 95054
         Phone: +1 408-400-1900
         E-mail: support@ipinfusion.com
         Web: http://www.ipinfusion.com/";

    description
        "Virtual Router Redundancy Protocol Configurations";


    revision "2025-02-19" {
        description "Added streaming telemetry support";
        reference " 0.8.0.";
    }

    revision "2024-03-27" {
        description "Implicit delete tag removed for IPv4 and IPv6 container";
        reference " 0.7.1.";
    }

    revision "2023-09-28" {
        description "Added implicit delete tag for config";
        reference " 0.7.0.";
    }

    revision "2023-02-02" {
        description "Updated missing Description";
        reference " 0.6.0.";
    }

    revision "2022-11-03" {
        description "Updated element mac-table-full in init-message-code";
        reference " 0.5.4.";
    }

    revision "2022-10-13" {
        description "Updated attribute 'decrement' cliFlag to remove option from unset cli";
        reference " 0.5.3.";
    }

    revision "2022-09-30" {
        description "Import cml-data-types used by notifications";
        reference " 0.3.0.";
    }

    revision "2022-08-24" {
        description "Update to add global IPV6 address as virtual ip";
        reference " 0.5.2.";
    }

    revision "2022-08-17" {
        description "Added implicit delete tag for global-config and debug-config container";
        reference " 0.5.1.";
    }

    revision "2022-08-10" {
        description "Debug hierarchy change";
        reference " 0.5.0.";
    }

    revision "2022-06-01" {
        description "Updated the yang file with feature";
        reference " 0.4.0.";
    }

    revision "2022-04-22" {
        description "Enable of VRRP protocol on its own container";
        reference " 0.3.0.";
    }

    revision "2021-12-01" {
        description "Added support for object tracking";
        reference " 0.2.7.";
    }

    revision "2021-09-23" {
        description "Added new notification vrrp-packet-error";
        reference " 0.2.6.";
    }

    revision "2021-09-08" {
        description "Add attributes wrong-authentication-password and refresh-rate-interval";
        reference " 0.2.4.";
    }

    revision "2021-09-03" {
        description "Update descriptions of attribute";
        reference " 0.2.5.";
    }

    revision "2021-08-26" {
        description "Change error-reason description";
        reference " 0.2.3.";
    }

    revision "2021-07-15" {
        description "Tracking interface priority as mandatoty leaf";
        reference " 0.2.2.";
    }

    revision "2021-07-02" {
        description "Add global error status attributes";
        reference " 0.2.1.";
    }

    revision "2021-06-18" {
        description "Restructured module in accordance with OpenConfig style";
        reference " 0.2.0.";
    }

    revision "2018-06-16" {
        description "Initial Version";
        reference " 0.1.0.";
    }


    grouping  vrrp-grouping {
    description
        "Virtual Router Redundancy Protocol";
    container vrrp {
        if-feature feature-list:HAVE_VRRPD;
        description
            "Virtual Router Redundancy Protocol";
        uses vrrp-global-top;
        uses vrrp-debug-top;
        uses vrrp-ipv4-instances-top;
        uses vrrp-ipv6-instances-top;
    } // END of vrrp-container definition.
    } // END of vrrp-grouping definition.

    uses vrrp-grouping;

    rpc vrrp-snmp-restart {
        if-feature feature-list:HAVE_SNMP;
        if-feature feature-list:HAVE_VRRPD;
        description "Restart SNMP in Virtual Routing Redundancy Protocol (VRRP).";
    }

    rpc vrrp-clear-statistics {
        if-feature feature-list:HAVE_VRRPD;
        description "Clear vrrp statistics";
    }

    rpc vrrp-clear-ipv4-statistics {
        if-feature feature-list:HAVE_VRRPD;
        description "Clear IPv4 vrrp statistics";
    }

    rpc vrrp-clear-ipv6-statistics {
        if-feature feature-list:HAVE_VRRPD;
        description "Clear IPv6 vrrp statistics";
    }

    rpc vrrp-clear-session-ipv4-statistics {
        if-feature feature-list:HAVE_VRRPD;
        description "Clear vrrp IPv4 statistics";
        input  {
            leaf vrrp-id  {
                type uint8 {
                    range "1..255";
                }
                mandatory true;
                description "VRRP router id";
            }
            leaf interface-name  {
                type string;
                mandatory true;
                description "Interface name";
            }
        }
    }

    rpc vrrp-clear-session-ipv6-statistics {
        if-feature feature-list:HAVE_VRRPD;
        description "Clear vrrp IPv6 statistics";
        input  {
            leaf vrrp-id  {
                type uint8 {
                    range "1..255";
                }
                mandatory true;
                description "VRRP router id";
            }
            leaf interface-name  {
                type string;
                mandatory true;
                description "Interface name";
            }
        }
    }

    rpc vrrp-terminal-debug-all-on {
        if-feature feature-list:HAVE_VRRPD;
        description "Enable all VRRP debugs";
    }

    rpc vrrp-terminal-debug-all-off {
        if-feature feature-list:HAVE_VRRPD;
        description "Disable all VRRP debugs";
    }

    rpc vrrp-terminal-debug-on {
        if-feature feature-list:HAVE_VRRPD;
        description "Enable VRRP debug";
        input  {
            leaf terminal-debug-options  {
                type ipi-vrrp-types:vrrp_debug_t;
                mandatory true;
                description "Debug options";
            }
        }
    }

    rpc vrrp-terminal-debug-off {
        if-feature feature-list:HAVE_VRRPD;
        description "Disable VRRP debugs";
        input  {
            leaf terminal-debug-options  {
                type ipi-vrrp-types:vrrp_debug_t;
                mandatory true;
                description "Debug options";
            }
        }
    }

    notification vrrp-new-master {
        if-feature feature-list:HAVE_VRRPD;

        description "Notification for VRRP new master state change.";

        leaf severity {
            type cml-data-types:cml_notif_severity_t;
            description "Notification severity level (value: WARNING)";
        }

        leaf eventClass {
            type cml-data-types:cml_notif_class_t;
            description "Notification event class (value: STATE)";
        }

        leaf operational-master-address {
            type  inet:ip-address;
        description
            "Operational Master address";
        }

        leaf virtual-router-id {
            type  uint8;
        description
            "Virtual router id";
        }

        leaf new-master-reason {
            type ipi-vrrp-types:vrrp_new_master_reason_t;
        description
            "New Master reason";
        }

        leaf uptime {
            type  string;
        description
            "This attribute provides session uptime";
        }
    }

    notification vrrp-protocol-error {
        if-feature feature-list:HAVE_VRRPD;

        description "Notification for VRRP protocol error.";

        leaf severity {
            type cml-data-types:cml_notif_severity_t;
            description "Notification severity level (value: CRITICAL)";
        }

        leaf eventClass {
            type cml-data-types:cml_notif_class_t;
            description "Notification event class (value: STATE)";
        }

        leaf operational-master-address {
            type  inet:ip-address;
        description
            "Operational Master address";
        }

        leaf virtual-router-id {
            type  uint8;
        description
            "Virtual router id";
        }

        leaf error-reason {
            type ipi-vrrp-types:vrrp_error_reason_t;
        description
            "Protocol error reason";
        }

        leaf uptime {
            type  string;
        description
            "This attribute provides session uptime";
        }
    }

    notification vrrp-packet-error {
        if-feature feature-list:HAVE_VRRPD;

        description "Notification for VRRP packet error.";

        leaf severity {
            type cml-data-types:cml_notif_severity_t;
            description "Notification severity level (value: CRITICAL)";
        }

        leaf eventClass {
            type cml-data-types:cml_notif_class_t;
            description "Notification event class (value: STATE)";
        }

        leaf error-reason {
            type ipi-vrrp-types:vrrp_error_reason_t;
        description
            "Protocol error reason";
        }
    }

}
