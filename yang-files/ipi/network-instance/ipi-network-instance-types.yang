/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-network-instance-types.yang
*
*/

module ipi-network-instance-types {

    yang-version 1.1;

    namespace   "http://www.ipinfusion.com/yang/ocnos/ipi-network-instance-types";

    prefix "ipi-network-instance-types";

    organization
        "IP Infusion Inc.";

    contact
        "Address: 3965 Freedom Circle, Suite 200, Santa Clara, CA 95054
         Phone: +1 408-400-1900
         E-mail: support@ipinfusion.com
         Web: http://www.ipinfusion.com/";

    description
        "Generic Network Instance Types";


    revision "2023-03-14" {
        description "Added bridge-domain type on NET_INST_TYPE_T datatype";
        reference " 0.6.0.";
    }

    revision "2022-06-01" {
        description "Updated the yang file with feature";
        reference " 0.5.0.";
    }

    revision "2021-11-10" {
        description "Added cross-connect type on NET_INST_TYPE_T datatype";
        reference " 0.4.0.";
    }

    revision "2021-09-03" {
        description "Update descriptions of attribute";
        reference " 0.3.0.";
    }

    revision "2020-12-15" {
        description "Change to have data-types in lower case instead of camel case";
        reference " 0.2.0.";
    }

    revision "2020-08-11" {
        description "Datamodel restructuring";
        reference " 0.1.0.";
    }



    typedef  net_inst_type_t {
        type enumeration {
            enum vrf {
                value 1;
                description "VRF Instance";
            }
            enum mac-vrf {
                value 2;
                description "MAC VRF Instance";
            }
            enum l2ni {
                value 3;
                description "Layer2 Network Instance";
            }
            enum vpls {
                value 4;
                description "VPLS Instance";
            }
            enum vpws {
                value 5;
                description "VPWS Instance";
            }
            enum evpn {
                value 6;
                description "EVPN Instance";
            }
            enum cross-connect {
                value 7;
                description "Cross-connect Instance";
            }
            enum bridge-domain {
                value 8;
                description "Bridge-domain Instance";
            }
        }
        description "type definition for NET_INST_TYPE_T";
    }

}
