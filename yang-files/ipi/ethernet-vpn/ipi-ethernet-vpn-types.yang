/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ethernet-vpn-types.yang
*
*/

module ipi-ethernet-vpn-types {

    yang-version 1.1;

    namespace   "http://www.ipinfusion.com/yang/ocnos/ipi-ethernet-vpn-types";

    prefix "ipi-ethernet-vpn-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-ethernet-vpn-types";


    revision "2025-09-11" {
        description "Added EVPN_MAC_RELOCATE_T type";
        reference " 0.3.1.";
    }

    revision "2025-07-31" {
        description "Added support for etree scenario-2";
        reference " 0.3.0.";
    }

    revision "2024-09-18" {
        description "Block service-carving off and dont-pre-empt attr";
        reference " 0.2.0.";
    }

    revision "2023-08-16" {
        description "Initial Version";
        reference " 0.1.0.";
    }



    typedef  evpn_acc_if_t {
        type enumeration {
            enum access-if {
                value 1;
                description "EVPN Access interface mode change";
            }
            enum access-if-evpn {
                value 2;
                description "EVPN Access interface mode change";
            }
        }
        description "type definition for EVPN_ACC_IF_T";
    }

    typedef  evpn_esi_load_balance_mode_t {
        type enumeration {
            enum single-active {
                value 1;
                description "load-balancing mode single-active";
            }
            enum port-active {
                value 2;
                description "load-balancing mode port-active";
            }
        }
        description "type definition for EVPN_ESI_LOAD_BALANCE_MODE_T";
    }

    typedef  evpn_esi_svc_carving_df_election_t {
        type enumeration {
            enum preference-based {
                value 1;
                description "Preference Based DF Election";
            }
            enum auto {
                value 2;
                description "modulo based DF election";
            }
        }
        description "type definition for EVPN_ESI_SVC_CARVING_DF_ELECTION_T";
    }

    typedef  evpn_etree_enable_scenario_t {
        type enumeration {
            enum enable {
                value 0;
                description "Enable";
            }
            enum enable-scenario-2 {
                value 1;
                description "Enable,EVPN ETREE Scenario-2";
            }
        }
        description "type definition for EVPN_ETREE_ENABLE_SCENARIO_T";
    }

    typedef  evpn_mac_relocate_t {
        type enumeration {
            enum enable {
                value 1;
                description "enable";
            }
            enum disable {
                value 2;
                description "disable";
            }
        }
        description "type definition for EVPN_MAC_RELOCATE_T";
    }

}
