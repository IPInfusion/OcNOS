/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ethernet-vpn.yang
*
*/

module ipi-ethernet-vpn {

    yang-version 1.1;

    namespace   "http://www.ipinfusion.com/yang/ocnos/ipi-ethernet-vpn";

    prefix "ipi-ethernet-vpn";

    import cml-data-types {
        prefix cml-data-types;
        revision-date 2026-05-15;
    }

    import ietf-inet-types {
        prefix inet;
        revision-date 2013-07-15;
    }

    import ipi-vrf {
        prefix ipi-vrf;
        revision-date 2026-08-12;
    }

    import ipi-network-instance {
        prefix ipi-network-instance;
        revision-date 2026-08-12;
    }

    import ipi-interface {
        prefix ipi-interface;
        revision-date 2026-03-10;
    }

    import ipi-mac-limit {
        prefix ipi-mac-limit;
        revision-date 2025-05-22;
    }

    import ipi-evpn-mpls {
        prefix ipi-evpn-mpls;
        revision-date 2026-07-13;
    }

    import ipi-evpn-srv6 {
        prefix ipi-evpn-srv6;
        revision-date 2025-03-24;
    }

    import ipi-if-extended {
        prefix ipi-if-extended;
        revision-date 2026-05-25;
    }

    import ipi-ethernet-vpn-types {
        prefix ipi-ethernet-vpn-types;
        revision-date 2025-09-11;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for EVPN protocol";


    revision "2026-05-07" {
        description "Added CML_SKIP_HITLESS_MERGE flag for service-carving weight";
        reference " 0.15.5.";
    }

    revision "2026-05-05" {
        description "Changed the type of max-mac-move-count";
        reference " 0.15.4.";
    }

    revision "2026-04-21" {
        description "Added cli-command for no map-vnid command";
        reference " 0.15.3.";
    }

    revision "2026-03-26" {
        description "Added dependency between segment-routing global block and evpn global config";
        reference " 0.14.16.";
    }

    revision "2026-03-25" {
        description "Added support to replace the redundancy mode without delete and re-add";
        reference " 0.14.15.";
    }

    revision "2025-11-11" {
        description "Added when tag for evpn-mac-holdtime";
        reference " 0.14.14.";
    }

    revision "2025-10-27" {
        description "Updated when tag for etree-leaf";
        reference " 0.14.13.";
    }

    revision "2025-10-23" {
        description "Added support to ignore EVPN Type 2 MAC Advertisement with sequence 0 when higher seqence exists";
        reference " 0.14.12.";
    }

    revision "2025-10-10" {
        description "Updated cli-command for unset map vpn-id from delete to unset as the attribute is not a RDN";
        reference " 0.14.11.";
    }

    revision "2025-10-06" {
        description "Added when tag for access-interfaces config container";
        reference " 0.14.10.";
    }

    revision "2025-09-22" {
        description "map vpn-id fix for ipbase sku ";
        reference " 0.14.9.";
    }

    revision "2025-09-19" {
        description "compilation issue for etree-leaf ";
        reference " 0.14.8.";
    }

    revision "2025-09-18" {
        description "Added when tag for etree-leaf attr ";
        reference " 0.14.7.";
    }

    revision "2025-09-11" {
        description "Added attribute evpn mh-mac-relocate-scan ";
        reference " 0.14.6.";
    }

    revision "2025-09-10" {
        description "Added support for etree scenario-2";
        reference " 0.14.5.";
    }

    revision "2025-09-04" {
        description "Removed EVPN_IRB_IF_MODE while configuring IRB interface";
        reference " 0.14.4.";
    }

    revision "2025-08-11" {
        description "CLI implementation evpn mac-move-count";
        reference " 0.14.3.";
    }

    revision "2025-07-30" {
        description "Added CML_SKIP_HITLESS_MERGE flag for multi-homing attributes";
        reference " 0.14.2.";
    }

    revision "2025-07-22" {
        description "For the evpn-mac-holdtime attribute, the when condition on switchport has been removed, and the attribute has been added under interfaces container";
        reference " 0.14.1.";
    }

    revision "2025-07-10" {
        description "Added evpn-mac-holdtime attribute";
        reference " 0.14.0.";
    }

    revision "2025-05-20" {
        description "Added attribute for EVPN arp-nd storm control";
        reference " 0.13.5.";
    }

    revision "2025-05-16" {
        description "Updated the type and validate_func for the attributes 'evpn-segment-id' and 'system-mac' in the cli-command";
        reference " 0.13.4.";
    }

    revision "2025-05-09" {
        description "Fix compilation warnings";
        reference " 0.13.3.";
    }

    revision "2025-05-05" {
        description "Added input displayString and helpString for ac-learning-limit";
        reference " 0.13.2.";
    }

    revision "2025-04-08" {
        description "Added ac-learning-limit for access-if-evpn mode";
        reference " 0.13.1.";
    }

    revision "2025-03-24" {
        description "Added 'CML_UNIQUE' for attributes 'evpn-segment-id' and 'system-mac'";
        reference " 0.13.0.";
    }

    revision "2024-12-03" {
        description "Added attribute for LLF under access-interface";
        reference " 0.12.6.";
    }

    revision "2024-11-18" {
        description "Added dependency for VxLAN delete";
        reference " 0.12.5.";
    }

    revision "2024-09-19" {
        description "Added ARP/ND CoS attribute for AC access-if";
        reference " 0.12.4.";
    }

    revision "2024-09-18" {
        description "Blocking service-carving off and dont-pre-empt attr";
        reference " 0.12.3.";
    }

    revision "2024-09-12" {
        description "Changed the validate api for evpn-identifier";
        reference " 0.12.2.";
    }

    revision "2024-08-26" {
        description "Addition of EVPN-MPLS-MH Filter dependentObject for evpn mpls irb";
        reference " 0.12.2.";
    }

    revision "2024-08-19" {
        description "Restrict Active-Standby CLI for DC boards";
        reference " 0.11.5.";
    }

    revision "2024-08-14" {
        description "Changed the grouping and added dependentObject for evpn-identifier";
        reference " 0.12.1.";
    }

    revision "2024-07-20" {
        description "Changed displayString and helpString in cliattr access-interface/config/evpn-identifier";
        reference " 0.12.0.";
    }

    revision "2024-05-30" {
        description "Added utils_func 'cml_ipv6_format' for ipv6-address attribute";
        reference " 0.11.2.";
    }

    revision "2024-05-24" {
        description "Removed UNSET_FIRST flag to evpn-identifier";
        reference " 0.11.1.";
    }

    revision "2024-03-11" {
        description "Added force-unset to mac-address attribute";
        reference " 0.11.0.";
    }

    revision "2024-02-21" {
        description "Disabling VXLAN IRB CLIs in Celestica E1070, Ufi Space S6301-56ST-2 boards";
        reference " 0.10.3.";
    }

    revision "2024-02-14" {
        description "Added when tag for etree enable attribute";
        reference " 0.10.2.";
    }

    revision "2024-01-06" {
        description "Added support for EVPN ETREE";
        reference " 0.10.1.";
    }

    revision "2024-01-03" {
        description "Added is-bit-map-check for reduncdancy mode cli-command";
        reference " 0.10.0.";
    }

    revision "2023-10-10" {
        description "Disabling VXLAN IRB in Celestica E1070, Ufi Space S6301-56ST-2 boards";
        reference " 0.9.6.";
    }

    revision "2023-09-13" {
        description "Added dependentObject for global/config container";
        reference " 0.9.5.";
    }

    revision "2023-09-11" {
        description "Added dependent object for irb anycast mac";
        reference " 0.9.4.";
    }

    revision "2023-08-16" {
        description "Added support for ESI load-balancing";
        reference " 0.9.3.";
    }

    revision "2023-08-02" {
        description "Add UNSET_FIRST flag to evpn-identifier";
        reference " 0.9.2.";
    }

    revision "2023-06-26" {
        description "Added module-init-condition to disable the cli's for TH3 platform";
        reference " 0.9.1.";
    }

    revision "2023-05-26" {
        description "garp-gna-enable attribute addition in evpn-access-interface-config grouping";
        reference " 0.9.0.";
    }

    revision "2023-04-20" {
        description "updated when tag for evpn-segment-id attribute";
        reference " 0.8.6.";
    }

    revision "2023-04-04" {
        description "Updated when tag for system-mac attribute";
        reference " 0.8.5.";
    }

    revision "2023-03-09" {
        description "Added a dependentObject in /access-interfaces/access-interface";
        reference " 0.8.4.";
    }

    revision "2023-02-17" {
        description "Fixed prependstr warning";
        reference " 0.8.3.";
    }

    revision "2023-02-15" {
        description "Add enclosing container for vrf and irb-interface";
        reference " 0.8.2.";
    }

    revision "2023-02-02" {
        description "EVPN-SRv6 Multi-homing feature";
        reference " 0.8.1.";
    }

    revision "2023-01-27" {
        description "Added a dependentObject in /evpn/global/config";
        reference " 0.8.0.";
    }

    revision "2023-01-16" {
        description "Added a dependentObject in /evpn/global/config";
        reference " 0.7.5.";
    }

    revision "2023-01-12" {
        description "Updated input for RDN attrs";
        reference " 0.7.4.";
    }

    revision "2023-01-05" {
        description "Leafref correction for config container";
        reference " 0.7.3.";
    }

    revision "2022-12-15" {
        description "removed vxlan if-feature check for evpn-irb-anycast-config";
        reference " 0.7.2.";
    }

    revision "2022-12-08" {
        description "Added if-feature check for evpn-irb-anycast-config";
        reference " 0.7.1.";
    }

    revision "2022-10-11" {
        description "Addition of EVPN-SRv6 dependency at access-if";
        reference " 0.6.9.";
    }

    revision "2022-10-07" {
        description "Add implicit-delete tag for evpn-global-config container";
        reference " 0.6.8.";
    }

    revision "2022-10-04" {
        description "Add implicit-delete for multi-homing container";
        reference " 0.6.7.";
    }

    revision "2022-09-15" {
        description "Updated MAC_ADDR macro with it's value";
        reference " 0.6.6.";
    }

    revision "2022-08-16" {
        description "Updated when and implicit-delete tags for EVPN-IRB";
        reference " 0.6.5.";
    }

    revision "2022-08-12" {
        description "Enable anycast mac configuration for physical ports";
        reference " 0.6.4.";
    }

    revision "2022-07-30" {
        description "Updated when expressions in yang";
        reference " 0.6.3.";
    }

    revision "2022-07-11" {
        description "Updated the subinterface encapsulation dependencies correctly";
        reference " 0.6.2.";
    }

    revision "2022-07-06" {
        description "Updated imported ipi-evpn-mpls xml with mpls multipath attributes";
        reference " 0.6.1.";
    }

    revision "2022-06-27" {
        description "Updated when expressions in yang file";
        reference " 0.6.0.";
    }

    revision "2022-06-12" {
        description "Updated when expressions";
        reference " 0.7.0.";
    }

    revision "2022-06-01" {
        description "Updated the yang file with feature";
        reference " 0.5.0.";
    }

    revision "2022-04-28" {
        description "Addition of EVPN-MPLS IRB CLI";
        reference " 0.4.0.";
    }

    revision "2022-03-08" {
        description "Addition of VXLAN dependencies for EVPN access-interfaces";
        reference " 0.3.2.";
    }

    revision "2022-02-12" {
        description "Updated when expressions for access-interface objectlist";
        reference " 0.6.10.";
    }

    revision "2022-01-14" {
        description "Addition of when tag for EVPN access-interfaces";
        reference " 0.3.1.";
    }

    revision "2021-10-13" {
        description "Unification of evpn access interface CLI common to vxlan and evpn-mpls";
        reference " 0.3.0.";
    }

    revision "2021-09-29" {
        description "Addition of when tag for evpn mpls related CLI";
        reference " 0.2.1.";
    }

    revision "2021-05-08" {
        description "addition of esi/system-mac for MH interface";
        reference " 0.2.0.";
    }

    revision "2021-01-27" {
        description "anycast gateway mac changes for IRB forwarding interface";
        reference " 0.1.2.";
    }

    revision "2020-12-15" {
        description "Change to have data-types in lower case instead of camel case";
        reference " 0.1.1.";
    }

    revision "2020-06-02" {
        description "Restructured as per Openconfig style";
        reference " 0.1.0.";
    }

    grouping evpn-global-config {
        description
            "Grouping for global evpn configuration";
        leaf enable-vxlan-multihoming  {
            if-feature feature-list:HAVE_TUNNEL;
            if-feature feature-list:HAVE_NVO;
            type  empty;
            description "Use this attribute to enable multihoming module on vxlan. Without this
                        attribute  multihomig functionality can not be achieved";
        } // END of enable-vxlan-multihoming definition.

        leaf enable-evpn-mpls-multihoming  {
            when " /ipi-evpn-mpls:evpn-mpls/ipi-evpn-mpls:global/ipi-evpn-mpls:config/ipi-evpn-mpls:enable-evpn-mpls ";
            if-feature feature-list:HAVE_MPLS;
            if-feature feature-list:HAVE_BGP_EVPN;
            if-feature feature-list:HAVE_NVO;
            type  empty;
            description "Use this attribute to enable multihoming module on evpn mpls. Without
                        this attribute  multihomig functionality can not be achieved";
        } // END of enable-evpn-mpls-multihoming definition.

        leaf enable-evpn-srv6-multihoming  {
            when " /ipi-evpn-srv6:evpn-srv6/ipi-evpn-srv6:global/ipi-evpn-srv6:config/ipi-evpn-srv6:enabled ";
            if-feature feature-list:HAVE_SRV6;
            if-feature feature-list:HAVE_BGP_EVPN;
            type  empty;
            description "Use this attribute to enable multihoming module on EVPN SRv6. Without
                        this attribute  multihomig functionality can not be achieved";
        } // END of enable-evpn-srv6-multihoming definition.

        leaf enable-irb  {
            if-feature feature-list:HAVE_TUNNEL;
            if-feature feature-list:HAVE_NVO;
            type  empty;
            description "Use this attribute to enable integrated routing and bridging module.
                        Without this attribute IRB functionality can not be achieved";
        } // END of enable-irb definition.

        leaf enable-mpls-irb  {
            when " /ipi-evpn-mpls:evpn-mpls/ipi-evpn-mpls:global/ipi-evpn-mpls:config/ipi-evpn-mpls:enable-evpn-mpls ";
            if-feature feature-list:HAVE_TUNNEL;
            if-feature feature-list:HAVE_MPLS;
            if-feature feature-list:HAVE_BGP_EVPN;
            if-feature feature-list:HAVE_NVO;
            type  empty;
            description "Use this attribute to enable integrated routing and bridging module.
                        Without this attribute IRB functionality can not be achieved";
        } // END of enable-mpls-irb definition.

        leaf enable-evpn-etree  {
            if-feature feature-list:HAVE_BGP_EVPN;
            if-feature feature-list:HAVE_NVO;
            type  ipi-ethernet-vpn-types:evpn_etree_enable_scenario_t;
            description "Use this attribute to enable evpn etree module on evpn mpls or vxlan.";
        } // END of enable-evpn-etree definition.

        leaf enable-evpn-storm-control  {
            if-feature feature-list:HAVE_DNX;
            if-feature feature-list:HAVE_BGP_EVPN;
            if-feature feature-list:HAVE_NVO;
            type  empty;
            description "Use this attribute to enable evpn arp/nd storm-control on evpn mpls or
                        vxlan.";
        } // END of enable-evpn-storm-control definition.

        leaf mh-mac-relocate-scan  {
            if-feature feature-list:HAVE_BGP_EVPN;
            if-feature feature-list:NOT_HAVE_DNX;
            type  ipi-ethernet-vpn-types:evpn_mac_relocate_t;
            description "Use this attribute to set the vxlan mh mac relocate scan";
        } // END of mh-mac-relocate-scan definition.

        leaf mac-seq-zero-handle  {
            if-feature feature-list:HAVE_BGP_EVPN;
            if-feature feature-list:HAVE_NVO;
            type  empty;
            description "Use this attribute to ignore MAC Advertisment Route (Type 2) with
                        sequence 0 from other PE if higher sequence exists";
        } // END of mac-seq-zero-handle definition.

    } // END of evpn-global-config definition.
    grouping evpn-multihoming-config {
        description
            "Grouping for evpn multihoming configuration";
        leaf esi-hold-time  {
            if-feature feature-list:HAVE_BGP_EVPN;
            type  uint32 {
                 range "10..300"  {
                    description "10..300: Supported range 10 - 300";
                 }
            }
            units "seconds";
            description "Use this attribute to set time before ESI can be made up on enabling
                        evpn";
        } // END of esi-hold-time definition.

    } // END of evpn-multihoming-config definition.
    grouping evpn-interface-config {
        description
            "Grouping for interface configuration";
        leaf name  {
            type  leafref {
                path  "/ipi-interface:interfaces/ipi-interface:interface/ipi-interface:name";
            }
            description "Use this attribute to map a physical interface to identify
                        the tenant traffic and to enter access interface mode";
        } // END of name definition.

    } // END of evpn-interface-config definition.
    grouping mh-load-balance-esi-top {
        description
            "Top-Level Grouping for MH Load-balancing";
        container mh-load-balance-esi {
            if-feature feature-list:HAVE_DUNE;
            description
                "Multihoming ESI and load-balancing";
            container config {
                when " /ipi-ethernet-vpn:evpn/ipi-ethernet-vpn:interfaces/ipi-ethernet-vpn:interface/ipi-ethernet-vpn:config/ipi-ethernet-vpn:redundancy-mode ";
                presence "yes";
                description
                    "Configuration data related to EVPN multi-homing ESI load-balancing";
                uses mh-load-balance-esi-config;
            } // END of config-container definition.
            container state {
                config false;
                description
                    "Operational state data related to EVPN multi-homing ESI load-balancing";
                uses mh-load-balance-esi-config;
            } // END of state-container definition.
        } // END of mh-load-balance-esi-container definition.
    } // END of mh-load-balance-esi-top definition.
    grouping mh-load-balance-esi-config {
        description
            "MH interface configuration for ESI";
        leaf service-carving  {
            type  ipi-ethernet-vpn-types:evpn_esi_svc_carving_df_election_t;
            mandatory true;
            description "Use this attribute to create or delete service-carving configuration";
        } // END of service-carving definition.

        leaf preference-weight  {
            type  uint16 {
                 range "1..65535"  {
                    description "1..65535: Supported range 1 - 65535";
                 }
            }
            description "Use this attribute to add preference to which should be elected as DF";
        } // END of preference-weight definition.

        leaf no-preempt  {
            type  empty;
            description "Use this attribute to set revertive DF capability";
        } // END of no-preempt definition.

        leaf ac-driven  {
            type  empty;
            description "Use this attribute to set AC Influenced DF capability";
        } // END of ac-driven definition.

    } // END of mh-load-balance-esi-config definition.
    grouping mh-interface-config {
        description
            "MH interface configuration for esi";
        leaf evpn-segment-id  {
            type  string {
                length "1..1965";
                pattern "[^?' =,>|]+";
            }
            description "This Object is used to configure the evpn multi-homed Ethernet Segment
                        Identifier value";
        } // END of evpn-segment-id definition.

        leaf system-mac  {
            type  cml-data-types:cml_mac_addr_t {
                length "1..1965";
            }
            description "This Object is used to configure evpn multi-homed system-mac";
        } // END of system-mac definition.

        leaf redundancy-mode  {
            type  ipi-ethernet-vpn-types:evpn_esi_load_balance_mode_t;
            description "Use this attribute to configure load balancing type";
        } // END of redundancy-mode definition.

    } // END of mh-interface-config definition.
    grouping evpn-hold-time-config {
        description
            "Grouping for evpn hold-time configuration";
        leaf evpn-mac-holdtime  {
            type  uint32 {
                 range "1..600"  {
                    description "1..600: Supported range 1 - 600";
                 }
            }
            units "seconds";
            description "Use this attribute to set the evpn mac hold time";
        } // END of evpn-mac-holdtime definition.

    } // END of evpn-hold-time-config definition.
    grouping evpn-irb-anycast-config {
        description
            "Grouping for evpn irb configuration";
        leaf mac-address  {
            if-feature feature-list:HAVE_TUNNEL;
            if-feature feature-list:HAVE_NVO;
            if-feature feature-list:HAVE_BGP_EVPN;
            type  cml-data-types:cml_mac_addr_t {
                length "1..1965";
            }
            description "Use this attribute to configure common anycast mac-address for all IRB
                        interfaces";
        } // END of mac-address definition.

    } // END of evpn-irb-anycast-config definition.
    grouping irb-interface-anycast-config {
        description
            "IRB interface forwarding for anycast gateway mac";
        leaf name  {
            when " /ipi-ethernet-vpn:evpn/ipi-ethernet-vpn:irb-forwarding/ipi-ethernet-vpn:config/ipi-ethernet-vpn:mac-address ";
            if-feature feature-list:HAVE_TUNNEL;
            if-feature feature-list:HAVE_NVO;
            if-feature feature-list:HAVE_BGP_EVPN;
            type  leafref {
                path  "/ipi-interface:interfaces/ipi-interface:interface/ipi-interface:name";
            }
            description "Use this attribute to map a physical interface to identify the tenant
                        traffic and to enter NVO access interface mode";
        } // END of name definition.

        leaf gateway-mac  {
            when " /ipi-ethernet-vpn:evpn/ipi-ethernet-vpn:irb-forwarding/ipi-ethernet-vpn:config/ipi-ethernet-vpn:mac-address ";
            if-feature feature-list:HAVE_TUNNEL;
            if-feature feature-list:HAVE_NVO;
            if-feature feature-list:HAVE_VXLAN;
            if-feature feature-list:HAVE_BGP_EVPN;
            type  empty;
            description "Use this attribute to configure anycast mac-address for an IRB
                        interface";
        } // END of gateway-mac definition.

    } // END of irb-interface-anycast-config definition.
    grouping evpn-access-interface-config {
        description
            "Grouping for EVPN access interface configuration";
        leaf access-if  {
            type  ipi-ethernet-vpn-types:evpn_acc_if_t;
            description "evpn access port";
        } // END of access-if definition.

        leaf dynamic-learning-disable  {
            type  empty;
            description "Use this attribute to disable dynamic learning of MACs
                        and MAC/IP at the access port";
        } // END of dynamic-learning-disable definition.

        leaf arp-nd-flood-suppress  {
            type  empty;
            description "Use this attribute to restrict the flood of ARP/ND packets
                        towards remote VTEPs or other access ports";
        } // END of arp-nd-flood-suppress definition.

        leaf cos  {
            type  int16 {
                 range "0..7"  {
                    description "0..7: Supported range 0 - 7";
                 }
            }
            description "Use this attribute to set CoS for the ARP/ND proxy reply";
        } // END of cos definition.

        leaf arp-cache-disable  {
            type  empty;
            description "Use this attribute to disable the ARP cache for MAC/IP";
        } // END of arp-cache-disable definition.

        leaf nd-cache-disable  {
            type  empty;
            description "Use this attribute to disable ND-cache on access interface";
        } // END of nd-cache-disable definition.

        leaf mac-hold-time  {
            type  int16 {
                 range "-1..300"  {
                    description "-1..300: Supported range -1 - 300";
                 }
            }
            units "seconds";
            default "0";
            description "Use this attribute to set the time a host MAC entry will persist after
                        unconfig";
        } // END of mac-hold-time definition.

        leaf-list mac-address  {
            type  cml-data-types:cml_mac_addr_t {
                length "1..1965";
            }
            description "Use this attribute to configure static MAC only Host under Access
                        Circuit";
        } // END of mac-address definition.

        leaf garp-gna-enable  {
            if-feature feature-list:HAVE_BGP_EVPN;
            type  empty;
            description "Use this attribute to allow garp-gna packets advertisement";
        } // END of garp-gna-enable definition.

        leaf llf-enable  {
            type  empty;
            description "This attribute is used to enable link loss forwarding on subif";
        } // END of llf-enable definition.

        leaf ac-learning-limit  {
            type  leafref {
                path  "/ipi-mac-limit:mac-limit-global/ipi-mac-limit:mac-limit-profiles/ipi-mac-limit:mac-limit-profile-inst/ipi-mac-limit:config/ipi-mac-limit:mac-lim-profile-name";
            }
            description "Attach MAC learning limit profile for EVPN AC";
        } // END of ac-learning-limit definition.

    } // END of evpn-access-interface-config definition.
    grouping evpn-access-interface-map-vpn-id-config {
        description
            "Grouping for EVPN map vpn-id access interface config";
        leaf evpn-identifier  {
            if-feature feature-list:HAVE_BGP_EVPN;
            if-feature feature-list:HAVE_NVO;
            if-feature feature-list:HAVE_MPLS_OR_HAVE_VXLAN_OR_HAVE_SRV6;
            type  uint32 {
                 range "1..16777215"  {
                    description "1..16777215: Supported range 1 - 16777215";
                 }
            }
            description "Map already created tenant id";
        } // END of evpn-identifier definition.

        leaf evpn-etree-leaf  {
            // when " ipi-ethernet-vpn/evpn/global/config/enable-evpn-etree + ipi-ethernet-vpn/evpn/interfaces/interface/access-interfaces/access-interface/evpn-id-mappings/config/evpn-identifier ";
            if-feature feature-list:HAVE_BGP_EVPN;
            if-feature feature-list:HAVE_NVO;
            if-feature feature-list:HAVE_DNX;
            if-feature feature-list:HAVE_MPLS;
            type  empty;
            description "Set access-port as etree-leaf";
        } // END of evpn-etree-leaf definition.

    } // END of evpn-access-interface-map-vpn-id-config definition.
    grouping evpn-mpls-access-mac-ipv4-config {
        description
            "Grouping for access interface configuration";
        leaf mac-address  {
            type  cml-data-types:cml_mac_addr_t {
                length "1..1965";
            }
            description "MAC Address of host connected to evpn-mpls access port";
        } // END of mac-address definition.

        leaf ipv4-address  {
            type  inet:ipv4-address;
            description "USe this attribute to associate a static IPv4 address on an access
                        interface.";
        } // END of ipv4-address definition.

    } // END of evpn-mpls-access-mac-ipv4-config definition.
    grouping evpn-mpls-access-mac-ipv6-config {
        description
            "Grouping for access host configuration";
        leaf mac-address  {
            type  cml-data-types:cml_mac_addr_t {
                length "1..1965";
            }
            description "MAC Address of host connected to evpn-mpls access port";
        } // END of mac-address definition.

        leaf ipv6-address  {
            type  inet:ipv6-address;
            description "USe this attribute to associate a static IPv6 address on an access
                        interface.";
        } // END of ipv6-address definition.

    } // END of evpn-mpls-access-mac-ipv6-config definition.
    grouping evpn-interface-top {
        description
            "Top-Level Grouping for evpn interface";
        container interfaces {
            description
                "Top level container for evpn interface";

            list interface {
                key "name";
                unique "config/evpn-segment-id config/system-mac";
                description
                    "EVPN interface related operations";
                leaf name  {
                    type  leafref {
                        path  "../config/name";
                    }
                    description "Reference to interface name";
                } // END of name definition.

                container config {
                    description
                        "Configuration data";
                    uses evpn-interface-config;
                    uses mh-interface-config;
                    uses evpn-hold-time-config;
                } // END of config-container definition.
                container state {
                    config false;
                    description
                        "Operational state data";
                    uses evpn-interface-config;
                    uses mh-interface-config;
                    uses evpn-hold-time-config;
                } // END of state-container definition.
                uses mh-load-balance-esi-top;
                uses evpn-access-interface-top;
            } // End of interface-list
        } // END of interfaces-container definition.
    } // END of evpn-interface-top definition.
    grouping irb-interface-anycast-top {
        description
            "Top-Level Grouping for IRB interface";
        container irb-interfaces {
            description
                "IRB interface list enclosing container";

            list irb-interface {
            // when " not(/ipi-interface:interfaces/ipi-interface:interface/ipi-interface:config/ipi-interface:enable-switchport) ";
                key "name";
                description
                    "IRB interface related configurations";
                leaf name  {
                    type  leafref {
                        path  "../config/name";
                    }
                    description "Use this attribute to map a physical interface to identify the tenant
                                traffic and to enter NVO access interface mode";
                } // END of name definition.

                container config {
                    description
                        "Configuration data";
                    uses irb-interface-anycast-config;
                } // END of config-container definition.
                container state {
                    config false;
                    description
                        "Operational state data";
                    uses irb-interface-anycast-config;
                } // END of state-container definition.
            } // End of irb-interface-list
        } // END of irb-interfaces-container definition.
    } // END of irb-interface-anycast-top definition.
    grouping evpn-vlan-service-mapping-top {
        description
            "Top-Level Grouping for vrf to vlan-service mapping";
        container vrfs {
            description
                "EVPN VRF list enclosing container";

            list vrf {
                key "vrf-name";
                description
                    "List of vrfs which holds evpn vlan service type";
                leaf vrf-name  {
                    type  leafref {
                        path  "../config/vrf-name";
                    }
                    description "Vrf Name under which evpn vlan service can be mapped.";
                } // END of vrf-name definition.

                container config {
                    description
                        "Configuration data";
                    uses evpn-vlan-service-config;
                } // END of config-container definition.
                container state {
                    config false;
                    description
                        "Operational state data";
                    uses evpn-vlan-service-config;
                } // END of state-container definition.
            } // End of vrf-list
        } // END of vrfs-container definition.
    } // END of evpn-vlan-service-mapping-top definition.
    grouping evpn-vlan-service-config {
        description
            "EVPN vlan service config related data";
        leaf vrf-name  {
            type  leafref {
                path  "/ipi-network-instance:network-instances/ipi-network-instance:network-instance/ipi-vrf:vrf/ipi-vrf:config/ipi-vrf:vrf-name";
            }
            description "VRF Name under which evpn vlan service can be mapped.";
        } // END of vrf-name definition.

        leaf service-type  {
            type  cml-data-types:cml_evpn_service_type_t;
            description "Use this attribute to configure Vlan-Based EVPN-Service Type";
        } // END of service-type definition.

    } // END of evpn-vlan-service-config definition.
    grouping evpn-mac-move-config {
        description
            "Grouping for EVPN MAC move count configuration";
        leaf max-mac-move-count  {
            type  uint16 {
                 range "5..1000"  {
                    description "5..1000: Supported range 5 - 1000";
                 }
            }
            mandatory true;
            description "Use this attribute to set the max MAC move count";
        } // END of max-mac-move-count definition.

        leaf duration  {
            type  uint16 {
                 range "180..3600"  {
                    description "180..3600: Supported range 180 - 3600";
                 }
            }
            units "seconds";
            default "180";
            description "Set the time in terms of seconds";
        } // END of duration definition.

        leaf freeze-time  {
            type  uint32 {
                 range "60..86400"  {
                    description "60..86400: Supported range 60 - 86400";
                 }
            }
            units "seconds";
            default "300";
            description "Set the time in terms of seconds";
        } // END of freeze-time definition.

    } // END of evpn-mac-move-config definition.
    grouping evpn-access-interface-top {
        description
            "Top level grouping for interface config";
        container access-interfaces {
            description
                "Top level container for interface level configuration";

            list access-interface {
            when " /ipi-interface:interfaces/ipi-interface:interface/ipi-if-extended:extended/ipi-if-extended:subinterface-encapsulation/ipi-if-extended:single-tag-vlan-matches/ipi-if-extended:single-tag-vlan-match or /ipi-interface:interfaces/ipi-interface:interface/ipi-if-extended:extended/ipi-if-extended:subinterface-encapsulation/ipi-if-extended:double-tag-vlan-matches/ipi-if-extended:double-tag-vlan-match or /ipi-interface:interfaces/ipi-interface:interface/ipi-if-extended:extended/ipi-if-extended:subinterface-encapsulation/ipi-if-extended:config/ipi-if-extended:encap-default or /ipi-interface:interfaces/ipi-interface:interface/ipi-if-extended:extended/ipi-if-extended:subinterface-encapsulation/ipi-if-extended:config/ipi-if-extended:encap-untagged and /ipi-interface:interfaces/ipi-interface:interface/ipi-interface:config/ipi-interface:enable-switchport and (/ipi-interface:interfaces/ipi-interface:interface/ipi-if-extended:extended/ipi-if-extended:subinterface-encapsulation/ipi-if-extended:single-tag-vlan-matches/ipi-if-extended:single-tag-vlan-match or /ipi-interface:interfaces/ipi-interface:interface/ipi-if-extended:extended/ipi-if-extended:subinterface-encapsulation/ipi-if-extended:double-tag-vlan-matches/ipi-if-extended:double-tag-vlan-match or /ipi-interface:interfaces/ipi-interface:interface/ipi-if-extended:extended/ipi-if-extended:subinterface-encapsulation/ipi-if-extended:config/ipi-if-extended:encap-default or /ipi-interface:interfaces/ipi-interface:interface/ipi-if-extended:extended/ipi-if-extended:subinterface-encapsulation/ipi-if-extended:config/ipi-if-extended:encap-untagged) ";
            // when " ipi-interface:interfaces/interface/config/enable-switchport == '1' ";
                if-feature feature-list:HAVE_SUBINTERFACE;
                if-feature feature-list:HAVE_NVO;
                key "access-if";
                description
                    "Configuration and state information";
                leaf access-if  {
                    type  leafref {
                        path  "../config/access-if";
                    }
                    description "evpn-mpls access port";
                } // END of access-if definition.

                container config {
                    description
                        "Configuration data";
                    uses evpn-access-interface-config;
                } // END of config-container definition.
                container state {
                    config false;
                    description
                        "Operational state data";
                    uses evpn-access-interface-config;
                } // END of state-container definition.
                uses evpn-access-interface-map-vpn-id-top;
                uses evpn-mpls-access-interface-mac-ipv4-list-top;
                uses evpn-mpls-access-interface-mac-ipv6-list-top;
            } // End of access-interface-list
        } // END of access-interfaces-container definition.
    } // END of evpn-access-interface-top definition.
    grouping evpn-access-interface-map-vpn-id-top {
        description
            "Grouping for map vpn-id configuration for access port";
        container evpn-id-mappings {
            if-feature feature-list:HAVE_SUBINTERFACE;
            if-feature feature-list:HAVE_NVO;
            description
                "Top level container for map vpn-id configuration for access port";
            container config {
                description
                    "configuration data";
                uses evpn-access-interface-map-vpn-id-config;
            } // END of config-container definition.
            container state {
                config false;
                description
                    "Operational state data";
                uses evpn-access-interface-map-vpn-id-config;
            } // END of state-container definition.
        } // END of evpn-id-mappings-container definition.
    } // END of evpn-access-interface-map-vpn-id-top definition.
    grouping evpn-mpls-access-interface-mac-ipv4-list-top {
        description
            "Grouping for mac-ipv4 configuration for access port";
        container ipv4-host-mac-mappings {
            description
                "Top level container for mac-ipv4 configuration for access port";

            list ipv4-host-mac-mapping {
                if-feature feature-list:HAVE_SUBINTERFACE;
                if-feature feature-list:HAVE_NVO;
                key "mac-address ipv4-address";
                description
                    "access side host related configurations";
                leaf mac-address  {
                    type  leafref {
                        path  "../config/mac-address";
                    }
                    description "Use this attribute to configure static MAC address of the host";
                } // END of mac-address definition.

                leaf ipv4-address  {
                    type  leafref {
                        path  "../config/ipv4-address";
                    }
                    description "USe this attribute to associate a static IPv4 address on an access
                                interface.";
                } // END of ipv4-address definition.

                container config {
                    description
                        "Configuration data";
                    uses evpn-mpls-access-mac-ipv4-config;
                } // END of config-container definition.
                container state {
                    config false;
                    description
                        "Operational state data";
                    uses evpn-mpls-access-mac-ipv4-config;
                } // END of state-container definition.
            } // End of ipv4-host-mac-mapping-list
        } // END of ipv4-host-mac-mappings-container definition.
    } // END of evpn-mpls-access-interface-mac-ipv4-list-top definition.
    grouping evpn-mpls-access-interface-mac-ipv6-list-top {
        description
            "Grouping for mac-ipv6 configuration for access port";
        container ipv6-host-mac-mappings {
            description
                "Top level container for mac-ipv6 configuration for access port";

            list ipv6-host-mac-mapping {
                if-feature feature-list:HAVE_SUBINTERFACE;
                if-feature feature-list:HAVE_NVO;
                if-feature feature-list:HAVE_IPV6;
                key "mac-address ipv6-address";
                description
                    "access side host related configurations";
                leaf mac-address  {
                    type  leafref {
                        path  "../config/mac-address";
                    }
                    description "Use this attribute to configure static MAC address of the host";
                } // END of mac-address definition.

                leaf ipv6-address  {
                    type  leafref {
                        path  "../config/ipv6-address";
                    }
                    description "USe this attribute to associate a static IPv6 address on an access
                                interface.";
                } // END of ipv6-address definition.

                container config {
                    description
                        "Configuration data";
                    uses evpn-mpls-access-mac-ipv6-config;
                } // END of config-container definition.
                container state {
                    config false;
                    description
                        "Operational state data";
                    uses evpn-mpls-access-mac-ipv6-config;
                } // END of state-container definition.
            } // End of ipv6-host-mac-mapping-list
        } // END of ipv6-host-mac-mappings-container definition.
    } // END of evpn-mpls-access-interface-mac-ipv6-list-top definition.

    grouping  evpn-grouping {
    description
        "EVPN global level container";
    container evpn {
        if-feature feature-list:HAVE_BGP_EVPN;
        description
            "EVPN global level container";
        container multi-homing {
            description
                "Configuration data for multi-homing feature";
            container config {
                description
                    "Configuration data";
                uses evpn-multihoming-config;
            } // END of config-container definition.
            container state {
                config false;
                description
                    "Operational state data";
                uses evpn-multihoming-config;
            } // END of state-container definition.
        } // END of multi-homing-container definition.
        container global {
            description
                "Configuration data for EVPN global capability configuration";
            container config {
                description
                    "Configuration data";
                uses evpn-global-config;
            } // END of config-container definition.
            container state {
                config false;
                description
                    "Operational state data";
                uses evpn-global-config;
            } // END of state-container definition.
        } // END of global-container definition.
        container irb-forwarding {
            description
                "Configuration data for integrated routing and bridging feature";
            container config {
                description
                    "Configuration data";
                uses evpn-irb-anycast-config;
            } // END of config-container definition.
            container state {
                config false;
                description
                    "Operational state data";
                uses evpn-irb-anycast-config;
            } // END of state-container definition.
            uses irb-interface-anycast-top;
        } // END of irb-forwarding-container definition.
        container mac-move-count {
            description
                "EVPN MAC move count";
            container config {
                presence "yes";
                description
                    "Configuration data related to EVPN MAC move count";
                uses evpn-mac-move-config;
            } // END of config-container definition.
            container state {
                config false;
                description
                    "Operational state data related to EVPN MAC move count";
                uses evpn-mac-move-config;
            } // END of state-container definition.
        } // END of mac-move-count-container definition.
        uses evpn-interface-top;
        uses evpn-vlan-service-mapping-top;
    } // END of evpn-container definition.
    } // END of evpn-grouping definition.

    uses evpn-grouping;

}
