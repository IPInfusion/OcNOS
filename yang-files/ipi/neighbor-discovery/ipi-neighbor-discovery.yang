/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-neighbor-discovery.yang
*
*/

module ipi-neighbor-discovery {

    yang-version 1.1;

    namespace   "http://www.ipinfusion.com/yang/ocnos/ipi-neighbor-discovery";

    prefix "ipi-neighbor-discovery";

    import cml-data-types {
        prefix cml-data-types;
        revision-date 2026-05-15;
    }

    import ipi-nd-types {
        prefix ipi-nd-types;
        revision-date 2022-06-01;
    }

    import ipi-interface {
        prefix ipi-interface;
        revision-date 2026-03-10;
    }

    import ietf-inet-types {
        prefix inet;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Neighbor Discovery";


    revision "2025-05-14" {
        description "Increase nd age timeout and reachable time";
        reference " 0.12.0.";
    }

    revision "2025-01-07" {
        description "Fixed not to prompt for ifname for ipv6 neighbor command";
        reference " 0.13.0.";
    }

    revision "2024-06-10" {
        description "Implementaion of CLI no ipv6 unreachable";
        reference " 0.11.0.";
    }

    revision "2024-05-07" {
        description "Implementaion of CLI no ip unreachable";
        reference " 0.10.0.";
    }

    revision "2023-06-27" {
        description "Enclosed entry objectlist with entries container";
        reference " 0.9.0.";
    }

    revision "2023-04-17" {
        description "Fix for static nd entries not deleting after no form";
        reference " 0.8.0.";
    }

    revision "2023-01-05" {
        description "Leafref correction for config container";
        reference " 0.7.0.";
    }

    revision "2022-12-07" {
        description "Added the cliprependstr to the prependstr clear";
        reference " 0.6.0.";
    }

    revision "2022-08-10" {
        description "Debug hierarchy change";
        reference " 0.5.0.";
    }

    revision "2022-06-01" {
        description "Updated the yang file with feature";
        reference " 0.4.0.";
    }

    revision "2021-09-01" {
        description "Changed base interface module's switchport attribute name and the datatype from bool to empty";
        reference " 0.3.0.";
    }

    revision "2020-12-15" {
        description "Change to have data-types in lower case instead of camel case";
        reference " 0.2.0.";
    }

    revision "2020-07-10" {
        description "Initial Version";
        reference " 0.1.0.";
    }

    grouping global-ipv6-nd {
        description
            "Nd global level ipv6 neighbor information";
        container entries {
            description
                "Top level container for IPv6 Neighbor information";

            list entry {
            // when " ipi-neighbor-discovery:neighbor-discovery/entries/entry/config/mac-address ";
                key "ipv6-address interface-name";
                description
                    "A list for IPv6 neighbor information entry";
                leaf ipv6-address  {
                    type  leafref {
                        path  "../config/ipv6-address";
                    }
                    description "Use this attribute to add a static neighbor entry.";
                } // END of ipv6-address definition.

                leaf interface-name  {
                    type  leafref {
                        path  "../config/interface-name";
                    }
                    description "Use this attribute to add a static neighbor entry of the interface
                                name";
                } // END of interface-name definition.

                container config {
                    description
                        "Nd ipv6 neighbor information";
                    uses link-layer-ipv6-top;
                } // END of config-container definition.
                container state {
                    config false;
                    description
                        "Operational state data";
                    uses link-layer-ipv6-top;
                    uses common-state-nd;
                } // END of state-container definition.
            } // End of entry-list
        } // END of entries-container definition.
    } // END of global-ipv6-nd definition.
    grouping link-layer-ipv6-top {
        description
            "link-layer address information";
        leaf ipv6-address  {
            type  inet:ipv6-address;
            description "Use this attribute to add a static neighbor entry";
        } // END of ipv6-address definition.

        leaf interface-name  {
            type  leafref {
                path  "/ipi-interface:interfaces/ipi-interface:interface/ipi-interface:name";
            }
            description "Use this attribute to add a static neighbor entry of the interface
                        name";
        } // END of interface-name definition.

        leaf mac-address  {
            type  cml-data-types:cml_mac_addr_t {
                length "1..1965";
            }
            mandatory true;
            description "Use this attribute to add a static neighbor entry of  MAC hardware
                        address.";
        } // END of mac-address definition.

    } // END of link-layer-ipv6-top definition.
    grouping adj-summary-info {
        description
            "Summary information";
        leaf resolved-arp  {
            type  uint32;
            description "Count of working/known adjacencies";
        } // END of resolved-arp definition.

        leaf incomplete-arp  {
            type  uint32;
            description "Count of working/known adjacencies";
        } // END of incomplete-arp definition.

        leaf unknown-arp  {
            type  uint32;
            description "Count of adjacencies not currently in ARP table";
        } // END of unknown-arp definition.

        leaf total-arp  {
            type  uint32;
            description "Total count of all adjacencies";
        } // END of total-arp definition.

    } // END of adj-summary-info definition.
    grouping dynamic-nd {
        description
            "Dynamic Neighbor Discovery information";

        list dynamic-neighbor-discovery {
            key "vrf-name";
            config false;
            description
                "Dynamic Neighbor Discovery entry information";
            leaf vrf-name  {
                type  string {
                    length "1..1965";
                    pattern "[^?' =,>|]+";
                }
                description "neighbor information associated vrf name";
            } // END of vrf-name definition.


            list entry {
                key "ipv6-address";
                config false;
                description
                    "Dynamic Neighbor Discovery entry information";
                leaf ipv6-address  {
                    type  inet:ipv6-address;
                    description "ARP entry IP address in the device";
                } // END of ipv6-address definition.

                leaf mac-address  {
                    type  cml-data-types:cml_mac_addr_t {
                        length "1..1965";
                    }
                    description "Physical address of the host";
                } // END of mac-address definition.

                leaf interface-name  {
                    type  string {
                        length "1..1965";
                        pattern "[^?' =,>|]+";
                    }
                    description "Logical address to connect the device over network.";
                } // END of interface-name definition.

                uses common-state-nd;
            } // End of entry-list
            container adjacency-summary {
                config false;
                description
                    "Neighbor adjacency summary information";
                uses adj-summary-info;
            } // END of adjacency-summary-container definition.
        } // End of dynamic-neighbor-discovery-list
    } // END of dynamic-nd definition.
    grouping common-state-nd {
        description
            "Neigh discovery state information";
        leaf neighbor-age  {
            type  string {
                length "1..1965";
                pattern "[^?' =,>|]+";
            }
            description "The number of minutes before the ARP entry was refreshed. If this
                        value reaches the ARP aging period, the entry is removed from the
                        table. Static entries do not age out.";
        } // END of neighbor-age definition.

        leaf neighbor-source  {
            type  ipi-nd-types:ndd_nd_src_type_t;
            description "ARP request source in the interface";
        } // END of neighbor-source definition.

        leaf neighbor-state  {
            type  ipi-nd-types:ndd_nd_state_t;
            description "ARP request state that is being handled by the IPv6 neighbor session.";
        } // END of neighbor-state definition.

        leaf neighbor-if-state  {
            type  ipi-nd-types:ndd_nd_if_type_t;
            description "neighbor entry interface state";
        } // END of neighbor-if-state definition.

    } // END of common-state-nd definition.
    grouping nd-debug-config {
        description
            "Neighbor discovery debug level";
        leaf enable  {
            type  empty;
            description "Use this attribute to enable debugging for neighbor events.";
        } // END of enable definition.

    } // END of nd-debug-config definition.
    grouping nd-debug-terminal {
        description
            "nd-debug-terminal";
        leaf terminal-debug-status  {
            type  cml-data-types:cml_on_off_t;
            description "Enable/Disable ipv6 nd event debug";
        } // END of terminal-debug-status definition.

    } // END of nd-debug-terminal definition.
    grouping nd-interface-config {
        description
            "Configuration data for nd on each interface";
        leaf name  {
            type  leafref {
                path  "/ipi-interface:interfaces/ipi-interface:interface/ipi-interface:name";
            }
            description "The textual name of the interface. The value of this object should be
                        the name of the interface as assigned by the local device and should
                        be suitable for use in commands entered at the device's `console'.
                        This might be a text name, such as `le0' or a simple port number, such
                        as `1', depending on the interface naming syntax of the device. If
                        several entries in the ifTable together represent a single interface
                        as named by the device, then each will have the same value of name.
                        Note that for an agent which responds to SNMP queries concerning an
                        interface on some other (proxied) device, then the value of name for
                        such an interface is the proxied device's local name for it. If there
                        is no local name, or this object is otherwise not applicable, then
                        this object contains a zero-length string.";
        } // END of name definition.

        leaf nd-ageing-timeout  {
            type  uint16 {
                 range "60..36000"  {
                    description "60..36000: Supported range 60 - 36000";
                 }
            }
            default "1500";
            description "Use this attribute  to set the neighbor ageing timeout value.";
        } // END of nd-ageing-timeout definition.

        leaf nd-reachable-time  {
            type  uint32 {
                 range "10..36000"  {
                    description "10..36000: Supported range 10 - 36000";
                 }
            }
            default "60";
            description "Use this attribute to set neighbor reachable time value.";
        } // END of nd-reachable-time definition.

        leaf no-ip-unreachable  {
            type  empty;
            description "Use this attribute to set ip unreachable.";
        } // END of no-ip-unreachable definition.

        leaf no-ipv6-unreachable  {
            type  empty;
            description "Use this attribute to set ipv6 unreachable.";
        } // END of no-ipv6-unreachable definition.

    } // END of nd-interface-config definition.
    grouping nd-interface-top {
        description
            "Top level container for nd on each interface";
        container interfaces {
            description
                "Top level container for arp on each interface";

            list interface {
            // when " not(/ipi-interface:interfaces/ipi-interface:interface/ipi-interface:config/ipi-interface:enable-switchport) ";
                key "name";
                description
                    "List of interfaces on which arp is enabled/available";
                leaf name  {
                    type  leafref {
                        path  "../config/name";
                    }
                    description "The textual name of the interface. The value of this object should be
                                the name of the interface as assigned by the local device and should
                                be suitable for use in commands entered at the device's `console'.
                                This might be a text name, such as `le0' or a simple port number, such
                                as `1', depending on the interface naming syntax of the device. If
                                several entries in the ifTable together represent a single interface
                                as named by the device, then each will have the same value of name.
                                Note that for an agent which responds to SNMP queries concerning an
                                interface on some other (proxied) device, then the value of name for
                                such an interface is the proxied device's local name for it. If there
                                is no local name, or this object is otherwise not applicable, then
                                this object contains a zero-length string.";
                } // END of name definition.

                container config {
                    description
                        "Configuration data for nd on each interface";
                    uses nd-interface-config;
                } // END of config-container definition.
                container state {
                    config false;
                    description
                        "Operational state data";
                    uses nd-interface-config;
                } // END of state-container definition.
            } // End of interface-list
        } // END of interfaces-container definition.
    } // END of nd-interface-top definition.
    grouping nd-debug-top {
        description
            "Neighbor discovery debug grouping";
        container debug {
            description
                "Neighbor discovery debug information";
            container config {
                description
                    "Configuration for nd-debug";
                uses nd-debug-config;
            } // END of config-container definition.
            container state {
                config false;
                description
                    "Configuration for nd-ebug";
                uses nd-debug-config;
                uses nd-debug-terminal;
            } // END of state-container definition.
        } // END of debug-container definition.
    } // END of nd-debug-top definition.

    grouping  neighbor-discovery-grouping {
    description
        "neighbor discovery global level information";
    container neighbor-discovery {
        if-feature feature-list:HAVE_L3;
        if-feature feature-list:HAVE_IPV6;
        if-feature feature-list:HAVE_NDD;
        description
            "neighbor discovery global level information";
        uses global-ipv6-nd;
        uses nd-debug-top;
        uses nd-interface-top;
        uses dynamic-nd;
    } // END of neighbor-discovery-container definition.
    } // END of neighbor-discovery-grouping definition.

    uses neighbor-discovery-grouping;

    rpc nd-terminal-debug-on {
        if-feature feature-list:HAVE_L3;
        if-feature feature-list:HAVE_IPV6;
        if-feature feature-list:HAVE_NDD;
        description "Enable nd event debug";
    }

    rpc nd-terminal-debug-off {
        if-feature feature-list:HAVE_L3;
        if-feature feature-list:HAVE_IPV6;
        if-feature feature-list:HAVE_NDD;
        description "Disable nd event debug";
    }

    rpc clear-ipv6-nd-entry {
        if-feature feature-list:HAVE_L3;
        if-feature feature-list:HAVE_IPV6;
        if-feature feature-list:HAVE_NDD;
        description "clear ipv6 nd";
        input  {
            leaf ipv6-address  {
                type cml-data-types:cml_ipv6_prefix_t;
                description "Use this RPC to clear dynamic neighbor entries.";
            }
            leaf vrf-name  {
                type string;
                description "Use this RPC to clear dynamic neighbor entries.";
            }
        }
    }

    rpc clear-ipv6-nd-entry-per-interface {
        if-feature feature-list:HAVE_L3;
        if-feature feature-list:HAVE_IPV6;
        if-feature feature-list:HAVE_NDD;
        description "clear ipv6 nd interface";
        input  {
            leaf if-name  {
                type string;
                mandatory true;
                description "Use this RPC to clear dynamic neighbor entries.";
            }
            leaf vrf-name  {
                type string;
                description "Use this RPC to clear dynamic neighbor entries.";
            }
        }
    }

}
