/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ripng.yang
*
*/

module ipi-ripng {

    yang-version 1.1;

    namespace   "http://www.ipinfusion.com/yang/ocnos/ipi-ripng";

    prefix "ipi-ripng";

    import ipi-ripng-types {
        prefix ipi-ripng-types;
        revision-date 2024-09-05;
    }

    import ipi-interface {
        prefix ipi-interface;
        revision-date 2026-03-10;
    }

    import cml-data-types {
        prefix cml-data-types;
        revision-date 2026-05-15;
    }

    import feature-list {
        prefix feature-list;
        revision-date 2026-09-15;
    }

    include ipi-ripng-common { revision-date 2022-07-31;}
    include ipi-ripng-vrf { revision-date 2022-07-28;}
    organization
        "IP Infusion Inc.";

    contact
        "Address: 3965 Freedom Circle, Suite 200, Santa Clara, CA 95054
         Phone: +1 408-400-1900
         E-mail: support@ipinfusion.com
         Web: http://www.ipinfusion.com/";

    description
        "Data model for IPI RIPng Configuration and Operational state";


    revision "2024-09-05" {
        description "Updated if-feature for datatype RIPNG_ROUTE_TYPE_T";
        reference " 0.4.0.";
    }

    revision "2024-05-07" {
        description "Added HAVE_RIPNGD to dependentObject in 'config' container.";
        reference " 0.3.0.";
    }

    revision "2022-12-01" {
        description "Updated when expressions";
        reference " 0.1.4.";
    }

    revision "2022-08-04" {
        description "Stop using inet:ipv4-prefix and inet:ipv6-prefix due to Cisco NSO iterop";
        reference " 0.1.3.";
    }

    revision "2022-08-03" {
        description "Added proper import for ipi-if-aggregate";
        reference " 0.1.2.";
    }

    revision "2022-07-30" {
        description "Updated when expression";
        reference " 0.1.1.";
    }

    revision "2022-07-28" {
        description "Initial Version";
        reference " 0.1.0.";
    }

    revision "2022-02-09" {
        description "Added When tag constraints for 'debug' container";
        reference " 0.2.0.";
    }

    grouping ripng-redistribute-policies-config {
        description
            "Grouping for RIPng Redistribute Policies Configurations";
        leaf route-type  {
            type  ipi-ripng-types:ripng_redistribute_proto_t;
            description "Use this attribute to redistribute information from other routing
                        protocols";
        } // END of route-type definition.

    } // END of ripng-redistribute-policies-config definition.
    grouping ripng-redistribute-policies-top {
        description
            "Grouping for top level RIPng Redistribute Policies";
        container redistribute-policies {
            description
                "Container for RIPng Redistribute Policies";

            list redistribute-policy {
                key "route-type";
                description
                    "List of RIPng Redistribute Policies";
                leaf route-type  {
                    type  leafref {
                        path  "../config/route-type";
                    }
                    description "Use this attribute to redistribute information from other routing
                                protocols";
                } // END of route-type definition.

                container config {
                    description
                        "Configuration Data for RIPng Redistribute Policies";
                    uses ripng-redistribute-policies-config;
                    uses ripng-redistribute-policies-common-config;
                } // END of config-container definition.
                container state {
                    config false;
                    description
                        "Operational Data for RIPng Redistribute Policies";
                    uses ripng-redistribute-policies-config;
                    uses ripng-redistribute-policies-common-config;
                } // END of state-container definition.
            } // End of redistribute-policy-list
        } // END of redistribute-policies-container definition.
    } // END of ripng-redistribute-policies-top definition.
    grouping ripng-instance-config {
        description
            "Grouping for RIPng Instance configurations";
        leaf ripng-enabled  {
            type  empty;
            mandatory true;
            description "Use this attribute to enable the router instance";
        } // END of ripng-enabled definition.

    } // END of ripng-instance-config definition.
    grouping ripng-instance-top {
        description
            "Grouping for top level RIPng Instance configurations";
        container instance {
            description
                "Container for RIPng Instance";
            container config {
                presence "To enable RIPng Instance";
                description
                    "RIPng Instance Configuration Data";
                uses ripng-instance-config;
                uses ripng-instance-common-config;
            } // END of config-container definition.
            container state {
                config false;
                description
                    "RIPng Instance Operational Data";
                uses ripng-instance-config;
                uses ripng-instance-common-config;
            } // END of state-container definition.
            uses ripng-redistribute-policies-top;
            uses ripng-timers-top;
            uses ripng-neighbors-top;
            uses ripng-instance-interfaces-top;
            uses ripng-offset-lists-top;
            uses ripng-distribute-lists-top;
            uses ripng-distribute-prefixes-top;
            uses ripng-routes-top;
            uses vrfs-grouping;
        } // END of instance-container definition.
    } // END of ripng-instance-top definition.
    grouping ripng-interfaces-config {
        description
            "Grouping for interface RIPng configurations";
        leaf name  {
            type  leafref {
                path  "/ipi-interface:interfaces/ipi-interface:interface/ipi-interface:name";
            }
            description "The textual name of the interface";
        } // END of name definition.

        leaf enabled  {
            type  empty;
            description "Use this attribute to perform the router rip action on the interface";
        } // END of enabled definition.

        leaf split-horizon  {
            type  boolean;
            description "Use this attribute to perform the split-horizon action on the
                        interface.
                        Deleting this attribute would set the split-horizon to poisoned
                        reverse which is
                        the default value.";
        } // END of split-horizon definition.

        leaf metric-offset  {
            type  uint8 {
                 range "1..16"  {
                    description "1..16: Supported range 1 - 16";
                 }
            }
            description "Use this attribute to perform the metric-offset action on the
                        interface";
        } // END of metric-offset definition.

    } // END of ripng-interfaces-config definition.
    grouping ripng-interfaces-top {
        description
            "Grouping for top level interface RIPng configurations";
        container interfaces {
            description
                "Container for interface RIPng";

            list interface {
            // when " not(/ipi-interface:interfaces/ipi-interface:interface/ipi-interface:config/ipi-interface:enable-switchport) ";
                key "name";
                description
                    "List of interfaces";
                leaf name  {
                    type  leafref {
                        path  "../config/name";
                    }
                    description "The textual name of the interface";
                } // END of name definition.

                container config {
                    description
                        "Interface RIPng Configuration Data";
                    uses ripng-interfaces-config;
                } // END of config-container definition.
                container state {
                    config false;
                    description
                        "Interface RIPng Operational Data";
                    uses ripng-interfaces-config;
                } // END of state-container definition.
            } // End of interface-list
        } // END of interfaces-container definition.
    } // END of ripng-interfaces-top definition.
    grouping ripng-debug-config {
        description
            "Grouping for Global RIPng attributes";
        leaf options  {
            type  ipi-ripng-types:ripng_debug_t;
            description "This attribute enables debugging for RIPng";
        } // END of options definition.

    } // END of ripng-debug-config definition.
    grouping ripng-terminal-debug-state {
        description
            "Grouping for RIPng terminal Debug attributes";
        leaf terminal-debug-status  {
            type  ipi-ripng-types:ripng_debug_t;
            description "This attribute describes the RIPng terminal debug status";
        } // END of terminal-debug-status definition.

    } // END of ripng-terminal-debug-state definition.
    grouping ripng-debug-top {
        description
            "Grouping for global RIPng configurations";
        container debug {
            description
                "Container for RIPng Debug";
            container config {
                description
                    "RIPng Debug Configuration Data";
                uses ripng-debug-config;
            } // END of config-container definition.
            container state {
                config false;
                description
                    "RIPng Debug Operational Data";
                uses ripng-debug-config;
                uses ripng-terminal-debug-state;
            } // END of state-container definition.
        } // END of debug-container definition.
    } // END of ripng-debug-top definition.

    grouping  ripng-grouping {
    description
        "Top level container for RIPng Configuration";
    container ripng {
        if-feature feature-list:HAVE_RIPNGD;
        description
            "Top level container for RIPng Configuration";
        uses ripng-debug-top;
        uses ripng-interfaces-top;
        uses ripng-instance-top;
    } // END of ripng-container definition.
    } // END of ripng-grouping definition.

    uses ripng-grouping;

    rpc ripng-terminal-debug-on {
        if-feature feature-list:HAVE_RIPNGD;
        description "Enable RIPng debug categories";
        input  {
            leaf terminal-debug-options  {
                type ipi-ripng-types:ripng_debug_t;
                mandatory true;
                description "Bitmap representing RIPng debug categories";
            }
        }
    }

    rpc ripng-terminal-debug-off {
        if-feature feature-list:HAVE_RIPNGD;
        description "Disable RIPng debug categories";
        input  {
            leaf terminal-debug-options  {
                type ipi-ripng-types:ripng_debug_t;
                mandatory true;
                description "Bitmap representing RIPng debug categories";
            }
        }
    }

    rpc ripng-clear-route {
        if-feature feature-list:HAVE_RIPNGD;
        description "Use this RPC to clear the RIPng routes";
        input  {
            leaf type  {
                type ipi-ripng-types:ripng_clear_route_type_t;
                mandatory true;
                description "This attribute describes the type of the route";
            }
        }
    }

    rpc ripng-clear-route-prefix {
        if-feature feature-list:HAVE_RIPNGD;
        description "Use this RPC to clear the specified RIPng route prefixes";
        input  {
            leaf prefix  {
                type cml-data-types:cml_ipv6_prefix_t;
                mandatory true;
                description "This attribute describes the prefix that needs to be cleared";
            }
        }
    }

}
