/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ripng-common.yang
*
*/

submodule ipi-ripng-common {

    yang-version 1.1;

    belongs-to  ipi-ripng { prefix ipi-ripng; }

    import ipi-ripng-types {
        prefix ipi-ripng-types;
        revision-date 2024-09-05;
    }

    import ietf-inet-types {
        prefix inet;
        revision-date 2013-07-15;
    }

    import ipi-interface {
        prefix ipi-interface;
        revision-date 2026-03-10;
    }

    import cml-data-types {
        prefix cml-data-types;
        revision-date 2026-05-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for common configuration and operational state for default
                and VRF RIPng instances";


    revision "2022-07-31" {
        description "Stop using inet:ipv4-prefix and inet:ipv6-prefix due to Cisco NSO iterop";
        reference " 0.1.1.";
    }

    revision "2022-07-28" {
        description "Initial Version";
        reference " 0.1.0.";
    }

    grouping ripng-aggregate-route-state {
        description
            "Grouping for RIPng Aggregate Routes";
        leaf count  {
            type  uint32;
            description "This attribute describes the aggregate route count";
        } // END of count definition.

        leaf metric  {
            type  uint8;
            description "This attribute describes the metric of aggregate route";
        } // END of metric definition.

        leaf tag  {
            type  uint16;
            description "This attribute describes the tag field of aggregate route";
        } // END of tag definition.

    } // END of ripng-aggregate-route-state definition.
    grouping ripng-aggregate-route-top {
        description
            "Grouping for top level RIPng Aggregate Routes";
        container aggregate-route {
            config false;
            description
                "Container for RIPng Aggregate Routes";
            container state {
                config false;
                description
                    "Operational Data for RIPng Aggregate Routes";
                uses ripng-aggregate-route-state;
            } // END of state-container definition.
        } // END of aggregate-route-container definition.
    } // END of ripng-aggregate-route-top definition.
    grouping ripng-nexthop-state {
        description
            "Grouping for RIPng Routes' Next Hop";
        leaf address  {
            type  inet:ipv6-address;
            description "This attribute describes the nexthop address of the route";
        } // END of address definition.

        leaf if-name  {
            type  string {
                length "1..1965";
                pattern "[^?' =,>|]+";
            }
            description "This attribute describes the outgoing interface name for the nexthop
                        address of the route";
        } // END of if-name definition.

        leaf metric  {
            type  uint8;
            description "This attribute describes the metric of the nexthop address of the
                        route";
        } // END of metric definition.

        leaf up-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "This attribute describes the uptime of the nexthop address of the
                        route";
        } // END of up-time definition.

    } // END of ripng-nexthop-state definition.
    grouping ripng-nexthop-top {
        description
            "Grouping for top level RIPng Routes' Next Hops";
        container next-hops {
            config false;
            description
                "Container for RIPng Routes' Next Hops";

            list next-hop {
                key "address";
                config false;
                description
                    "List of RIPng Routes' Next Hops";
                leaf address  {
                    type  leafref {
                        path  "../state/address";
                    }
                    description "This attribute describes the nexthop address of the route";
                } // END of address definition.

                container state {
                    config false;
                    description
                        "Operational Data for RIPng Routes' Next Hops";
                    uses ripng-nexthop-state;
                } // END of state-container definition.
            } // End of next-hop-list
        } // END of next-hops-container definition.
    } // END of ripng-nexthop-top definition.
    grouping ripng-routes-state {
        description
            "Grouping for RIPng Routes";
        leaf prefix  {
            type  cml-data-types:cml_ipv6_prefix_t;
            description "This attribute describes the prefix of the route";
        } // END of prefix definition.

        leaf type  {
            type  ipi-ripng-types:ripng_route_type_t;
            description "This attribute describes the type of the route";
        } // END of type definition.

        leaf sub-type  {
            type  ipi-ripng-types:ripng_route_sub_type_t;
            description "This attribute describes the sub type of the route";
        } // END of sub-type definition.

        leaf tag  {
            type  uint16;
            description "This attribute describes the tag field of the route";
        } // END of tag definition.

    } // END of ripng-routes-state definition.
    grouping ripng-routes-top {
        description
            "Grouping for top level RIPng Routes";
        container routes {
            config false;
            description
                "Container for RIPng Routes";

            list route {
                key "prefix";
                config false;
                description
                    "List of RIPng Routes";
                leaf prefix  {
                    type  leafref {
                        path  "../state/prefix";
                    }
                    description "This attribute describes the prefix of the route";
                } // END of prefix definition.

                container state {
                    config false;
                    description
                        "Operational Data for RIPng Routes";
                    uses ripng-routes-state;
                } // END of state-container definition.
                uses ripng-nexthop-top;
                uses ripng-aggregate-route-top;
            } // End of route-list
        } // END of routes-container definition.
    } // END of ripng-routes-top definition.
    grouping ripng-distribute-prefixes-config {
        description
            "Grouping for RIPng Distribute Prefix Lists";
        leaf direction  {
            type  ipi-ripng-types:ripng_direction_t;
            description "Use this attribute to decide the type of packets to which the
                        distribute list prefix
                        is applied";
        } // END of direction definition.

        leaf list-name  {
            type  string {
                length "1..1965";
                pattern "[^?' =,>|]+";
            }
            mandatory true;
            description "Use this attribute to filter incoming or outgoing route updates
                        using an access list or a prefix list. You can filter out incoming or
                        outgoing route updates using an access list or a prefix list. If you
                        do
                        not specify the name of the interface, the filter will be applied to
                        all
                        the interfaces.";
        } // END of list-name definition.

    } // END of ripng-distribute-prefixes-config definition.
    grouping ripng-distribute-prefixes-top {
        description
            "Grouping for top level RIPng Distribute Prefix Lists";
        container distribute-prefix-lists {
            description
                "Container for RIPng Distribute Prefix Lists";

            list distribute-prefix-list {
                key "direction";
                description
                    "List of RIPng Distribute Prefix Lists";
                leaf direction  {
                    type  leafref {
                        path  "../config/direction";
                    }
                    description "Use this attribute to decide the type of packets to which the
                                distribute list prefix
                                is applied";
                } // END of direction definition.

                container config {
                    description
                        "Configuration Data for RIPng Distribute Prefix Lists";
                    uses ripng-distribute-prefixes-config;
                } // END of config-container definition.
                container state {
                    config false;
                    description
                        "Operational Data for RIPng Distribute Prefix Lists";
                    uses ripng-distribute-prefixes-config;
                } // END of state-container definition.
            } // End of distribute-prefix-list-list
        } // END of distribute-prefix-lists-container definition.
    } // END of ripng-distribute-prefixes-top definition.
    grouping ripng-distribute-lists-config {
        description
            "Grouping for RIPng Distribute Lists";
        leaf direction  {
            type  ipi-ripng-types:ripng_direction_t;
            description "Use this attribute to decide the type of packets to which the
                        distribute list
                        is applied";
        } // END of direction definition.

        leaf access-list-name  {
            type  string {
                length "1..1965";
                pattern "[^?' =,>|]+";
            }
            mandatory true;
            description "Use this attribute to filter incoming or outgoing route updates
                        using an access list or a prefix list. You can filter out incoming or
                        outgoing route updates using an access list or a prefix list. If you
                        do
                        not specify the name of the interface, the filter will be applied to
                        all
                        the interfaces.";
        } // END of access-list-name definition.

    } // END of ripng-distribute-lists-config definition.
    grouping ripng-distribute-lists-top {
        description
            "Grouping for top level RIPng Distribute Lists";
        container distribute-lists {
            description
                "Container for RIPng Distribute Lists";

            list distribute-list {
                key "direction";
                description
                    "List of RIPng Distribute Lists";
                leaf direction  {
                    type  leafref {
                        path  "../config/direction";
                    }
                    description "Use this attribute to decide the type of packets to which the
                                distribute list
                                is applied";
                } // END of direction definition.

                container config {
                    description
                        "Configuration Data for RIPng Distribute Lists";
                    uses ripng-distribute-lists-config;
                } // END of config-container definition.
                container state {
                    config false;
                    description
                        "Operational Data for RIPng Distribute Lists";
                    uses ripng-distribute-lists-config;
                } // END of state-container definition.
            } // End of distribute-list-list
        } // END of distribute-lists-container definition.
    } // END of ripng-distribute-lists-top definition.
    grouping ripng-offset-lists-config {
        description
            "Grouping for RIPng Offset Lists";
        leaf direction  {
            type  ipi-ripng-types:ripng_direction_t;
            description "Use this attribute to decide the type of packets to which the offset
                        list
                        is applied";
        } // END of direction definition.

        leaf access-list-name  {
            type  string {
                length "1..1965";
                pattern "[^?' =,>|]+";
            }
            mandatory true;
            description "Use this attribute to add an offset to in and out metrics to routes
                        learned through RIP. This command specifies the offset value that is
                        added to
                        the routing metric. When the networks match the access list the offset
                        is
                        applied to the metrics. No change occurs if the offset value is zero";
        } // END of access-list-name definition.

        leaf metric  {
            type  uint8 {
                 range "0..16"  {
                    description "0..16: Supported range 0 - 16";
                 }
            }
            mandatory true;
            description "This attribute describes the metric used for offset list";
        } // END of metric definition.

    } // END of ripng-offset-lists-config definition.
    grouping ripng-offset-lists-top {
        description
            "Grouping for top level RIPng Offset Lists";
        container offset-lists {
            description
                "Container for RIPng Offset Lists";

            list offset-list {
                key "direction";
                description
                    "List of RIPng Offset Lists";
                leaf direction  {
                    type  leafref {
                        path  "../config/direction";
                    }
                    description "Use this attribute to decide the type of packets to which the offset
                                list
                                is applied";
                } // END of direction definition.

                container config {
                    description
                        "Configuration Data for RIPng Offset Lists";
                    uses ripng-offset-lists-config;
                } // END of config-container definition.
                container state {
                    config false;
                    description
                        "Operational Data for RIPng Offset Lists";
                    uses ripng-offset-lists-config;
                } // END of state-container definition.
            } // End of offset-list-list
        } // END of offset-lists-container definition.
    } // END of ripng-offset-lists-top definition.
    grouping ripng-route-maps-config {
        description
            "Grouping for RIPng Filtering Route Maps";
        leaf type  {
            type  ipi-ripng-types:ripng_direction_t;
            description "Use this attribute to decide the type of packets to which the
                        filtering
                        is applied";
        } // END of type definition.

        leaf route-map-name  {
            type  string {
                length "1..63";
                pattern "[^?' =,>|]+";
            }
            mandatory true;
            description "Use this attribute to apply the route map to the type of filtering";
        } // END of route-map-name definition.

    } // END of ripng-route-maps-config definition.
    grouping ripng-route-maps-top {
        description
            "Grouping for top level RIPng Filtering Route Maps";
        container filtering-route-maps {
            description
                "Container for RIPng Filtering Route Maps";

            list filtering-route-map {
                key "type";
                description
                    "List of RIPng Filtering Route Maps";
                leaf type  {
                    type  leafref {
                        path  "../config/type";
                    }
                    description "Use this attribute to decide the type of packets to which the
                                filtering
                                is applied";
                } // END of type definition.

                container config {
                    description
                        "Configuration Data for RIPng Filtering Route Maps";
                    uses ripng-route-maps-config;
                } // END of config-container definition.
                container state {
                    config false;
                    description
                        "Operational Data for RIPng Filtering Route Maps";
                    uses ripng-route-maps-config;
                } // END of state-container definition.
            } // End of filtering-route-map-list
        } // END of filtering-route-maps-container definition.
    } // END of ripng-route-maps-top definition.
    grouping ripng-instance-interfaces-config {
        description
            "Grouping for RIPng Instance Interfaces";
        leaf name  {
            type  leafref {
                path  "/ipi-interface:interfaces/ipi-interface:interface/ipi-interface:name";
            }
            description "The textual name of the interface";
        } // END of name definition.

    } // END of ripng-instance-interfaces-config definition.
    grouping ripng-instance-interfaces-top {
        description
            "Grouping for top level RIPng Interface";
        container interfaces {
            description
                "Container for RIPng Interfaces";

            list interface {
                key "name";
                description
                    "List of RIPng Interfaces";
                leaf name  {
                    type  leafref {
                        path  "../config/name";
                    }
                    description "The textual name of the interface";
                } // END of name definition.

                container config {
                    description
                        "Configuration Data for RIPng Interfaces";
                    uses ripng-instance-interfaces-config;
                } // END of config-container definition.
                container state {
                    config false;
                    description
                        "Operational Data for RIPng Interfaces";
                    uses ripng-instance-interfaces-config;
                } // END of state-container definition.
                uses ripng-route-maps-top;
                uses ripng-offset-lists-top;
                uses ripng-distribute-lists-top;
                uses ripng-distribute-prefixes-top;
            } // End of interface-list
        } // END of interfaces-container definition.
    } // END of ripng-instance-interfaces-top definition.
    grouping ripng-neighbors-config {
        description
            "Grouping for RIPng Neighbors";
        leaf address  {
            type  inet:ipv6-address;
            description "Use this attribute to specify a link local address of neighbor router.
                        It is
                        used for each connected point-to-point link. This command exchanges
                        non-broadcast routing
                        information. It can be used multiple times for additional neighbors";
        } // END of address definition.

        leaf if-name  {
            type  leafref {
                path  "/ipi-interface:interfaces/ipi-interface:interface/ipi-interface:name";
            }
            mandatory true;
            description "The textual name of the interface";
        } // END of if-name definition.

    } // END of ripng-neighbors-config definition.
    grouping ripng-neighbors-top {
        description
            "Grouping for top level RIPng Neighbors";
        container neighbors {
            description
                "Container for RIPng Neighbors";

            list neighbor {
                key "address";
                description
                    "List of RIPng Neighbors";
                leaf address  {
                    type  leafref {
                        path  "../config/address";
                    }
                    description "Use this attribute to specify a link local address of neighbor router.
                                It is
                                used for each connected point-to-point link. This command exchanges
                                non-broadcast routing
                                information. It can be used multiple times for additional neighbors";
                } // END of address definition.

                container config {
                    description
                        "Configuration Data for RIPng Neighbors";
                    uses ripng-neighbors-config;
                } // END of config-container definition.
                container state {
                    config false;
                    description
                        "Operational Data for RIPng Neighbors";
                    uses ripng-neighbors-config;
                } // END of state-container definition.
            } // End of neighbor-list
        } // END of neighbors-container definition.
    } // END of ripng-neighbors-top definition.
    grouping ripng-timers-config {
        description
            "Grouping for RIPng Timers Configurations";
        leaf route-table-update-interval  {
            type  uint32 {
                 range "5..2147483647"  {
                    description "5..2147483647: Supported range 5 - 2147483647";
                 }
            }
            units "seconds";
            mandatory true;
            description "Use this attribute to adjust basic routing protocol update timer
                        interval";
        } // END of route-table-update-interval definition.

        leaf route-info-timeout-interval  {
            type  uint32 {
                 range "5..2147483647"  {
                    description "5..2147483647: Supported range 5 - 2147483647";
                 }
            }
            units "seconds";
            mandatory true;
            description "Use this attribute to adjust routing information timeout interval";
        } // END of route-info-timeout-interval definition.

        leaf garbage-collection-interval  {
            type  uint32 {
                 range "5..2147483647"  {
                    description "5..2147483647: Supported range 5 - 2147483647";
                 }
            }
            units "seconds";
            mandatory true;
            description "Use this attribute to adjust garbage collection interval";
        } // END of garbage-collection-interval definition.

    } // END of ripng-timers-config definition.
    grouping ripng-timers-top {
        description
            "Grouping for top level RIPng Timer Configuration";
        container timers {
            description
                "Container for RIPng Timers";
            container config {
                presence "To configure the update, timeout and garbage collection interval";
                description
                    "Configuration Data for RIPng Timers";
                uses ripng-timers-config;
            } // END of config-container definition.
            container state {
                config false;
                description
                    "Operational Data for RIPng Timers";
                uses ripng-timers-config;
            } // END of state-container definition.
        } // END of timers-container definition.
    } // END of ripng-timers-top definition.
    grouping ripng-redistribute-policies-common-config {
        description
            "Grouping for RIPng Redistribute Policies Common Configurations";
        leaf metric  {
            type  uint8 {
                 range "0..16"  {
                    description "0..16: Supported range 0 - 16";
                 }
            }
            description "Use this attribute to redistribute metric information from other
                        routing protocols";
        } // END of metric definition.

        leaf route-map  {
            type  string {
                length "1..1965";
                pattern "[^?' =,>|]+";
            }
            description "Use this attribute to redistribute route-map from other routing
                        protocols";
        } // END of route-map definition.

    } // END of ripng-redistribute-policies-common-config definition.
    grouping ripng-instance-common-config {
        description
            "Grouping for RIPng Instance common configurations";
        leaf-list passive-interfaces  {
            type  leafref {
                path  "/ipi-interface:interfaces/ipi-interface:interface/ipi-interface:name";
            }
            description "Use this attribute to block RIP broadcast on the interface";
        } // END of passive-interfaces definition.

        leaf distance  {
            type  uint8 {
                 range "1..255"  {
                    description "1..255: Supported range 1 - 255";
                 }
            }
            default "120";
            description "Use this attribute to set the administrative distance.
                        The administrative distance is a feature used by the routers to
                        select the path when there are two or more different routes to the
                        same destination from two different routing protocols. A smaller
                        administrative distance indicating a more reliable protocol";
        } // END of distance definition.

        leaf-list static-routes  {
            type  cml-data-types:cml_ipv6_prefix_t;
            description "Use this attribute to configure static RIP routes";
        } // END of static-routes definition.

        leaf-list aggregate-prefixes  {
            type  cml-data-types:cml_ipv6_prefix_t;
            description "Use this attribute to configure aggregate prefixes";
        } // END of aggregate-prefixes definition.

        leaf default-metric  {
            type  uint8 {
                 range "1..15"  {
                    description "1..15: Supported range 1 - 15";
                 }
            }
            default "1";
            description "Use this attribute to specify the metrics to be assigned to
                        redistributed routers";
        } // END of default-metric definition.

        leaf originate-default-route  {
            type  empty;
            description "Use this attribute to add default routes to the RIP updates";
        } // END of originate-default-route definition.

        leaf enable-cisco-metric-behavior  {
            type  boolean;
            description "Use this attribute to enable the metric update consistent with Cisco";
        } // END of enable-cisco-metric-behavior definition.

        leaf receive-buffer-size  {
            type  uint32 {
                 range "8192..2147483647"  {
                    description "8192..2147483647: Supported range 8192 - 2147483647";
                 }
            }
            units "bytes";
            default "8192";
            description "Use this attribute to run-time configure the RIP UDP receive-buffer
                        size";
        } // END of receive-buffer-size definition.

    } // END of ripng-instance-common-config definition.


}
