/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ripng-vrf.yang
*
*/

submodule ipi-ripng-vrf {

    yang-version 1.1;

    belongs-to  ipi-ripng { prefix ipi-ripng; }

    import feature-list {
        prefix feature-list;
        revision-date 2026-09-15;
    }

    import ipi-ripng-types {
        prefix ipi-ripng-types;
        revision-date 2024-09-05;
    }

    import ipi-network-instance {
        prefix ipi-network-instance;
        revision-date 2026-08-12;
    }

    import ipi-vrf {
        prefix ipi-vrf;
        revision-date 2026-08-12;
    }

    include ipi-ripng-common { revision-date 2022-07-31;}
    organization
        "IP Infusion Inc.";

    contact
        "Address: 3965 Freedom Circle, Suite 200, Santa Clara, CA 95054
         Phone: +1 408-400-1900
         E-mail: support@ipinfusion.com
         Web: http://www.ipinfusion.com/";

    description
        "Data model for IPI RIPng VRF Configuration and Operational state";


    revision "2022-07-28" {
        description "Initial Version";
        reference " 0.1.0.";
    }

    grouping ripng-vrf-redistribute-policies-config {
        description
            "Grouping for RIPng VRF Redistribute Policies Configurations";
        leaf route-type  {
            type  ipi-ripng-types:ripng_vrf_redistribute_proto_t;
            description "Use this attribute to redistribute information from other routing
                        protocols";
        } // END of route-type definition.

    } // END of ripng-vrf-redistribute-policies-config definition.
    grouping ripng-vrf-redistribute-policies-top {
        description
            "Grouping for top level RIPng Redistribute Policies";
        container redistribute-policies {
            description
                "Container for RIPng Redistribute Policies";

            list redistribute-policy {
                key "route-type";
                description
                    "List of RIPng Redistribute Policies";
                leaf route-type  {
                    type  leafref {
                        path  "../config/route-type";
                    }
                    description "Use this attribute to redistribute information from other routing
                                protocols";
                } // END of route-type definition.

                container config {
                    description
                        "Configuration Data for RIPng Redistribute Policies";
                    uses ripng-vrf-redistribute-policies-config;
                    uses ripng-redistribute-policies-common-config;
                } // END of config-container definition.
                container state {
                    config false;
                    description
                        "Operational Data for RIPng Redistribute Policies";
                    uses ripng-vrf-redistribute-policies-config;
                    uses ripng-redistribute-policies-common-config;
                } // END of state-container definition.
            } // End of redistribute-policy-list
        } // END of redistribute-policies-container definition.
    } // END of ripng-vrf-redistribute-policies-top definition.
    grouping ripng-vrfs-config {
        description
            "Grouping for VRF specific attributes";
        leaf vrf-name  {
            type  leafref {
                path  "/ipi-network-instance:network-instances/ipi-network-instance:network-instance/ipi-vrf:vrf/ipi-vrf:config/ipi-vrf:vrf-name";
            }
            description "VRF Name";
        } // END of vrf-name definition.

    } // END of ripng-vrfs-config definition.

    grouping  vrfs-grouping {
    description
        "Top level container for RIPng VRF Configuration";
    container vrfs {
        if-feature feature-list:HAVE_RIPNGD;
        if-feature feature-list:HAVE_VRF_RIPNG;
        description
            "Top level container for RIPng VRF Configuration";

        list vrf {
            key "vrf-name";
            description
                "List of RIPng VRF Configuration";
            leaf vrf-name  {
                type  leafref {
                    path  "../config/vrf-name";
                }
                description "VRF Name";
            } // END of vrf-name definition.

            container config {
                description
                    "Configuration Data for RIPng VRF";
                uses ripng-vrfs-config;
                uses ripng-instance-common-config;
            } // END of config-container definition.
            container state {
                config false;
                description
                    "Operational Data for RIPng VRF";
                uses ripng-vrfs-config;
                uses ripng-instance-common-config;
            } // END of state-container definition.
            uses ripng-vrf-redistribute-policies-top;
            uses ripng-timers-top;
            uses ripng-neighbors-top;
            uses ripng-instance-interfaces-top;
            uses ripng-offset-lists-top;
            uses ripng-distribute-lists-top;
            uses ripng-distribute-prefixes-top;
            uses ripng-routes-top;
        } // End of vrf-list
    } // END of vrfs-container definition.
    } // END of vrfs-grouping definition.


}
