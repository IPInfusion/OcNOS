/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ripng-types.yang
*
*/

module ipi-ripng-types {

    yang-version 1.1;

    namespace   "http://www.ipinfusion.com/yang/ocnos/ipi-ripng-types";

    prefix "ipi-ripng-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module defines data types related to the RIPng model";


    revision "2024-09-05" {
        description "Updated if-feature for datatype RIPNG_ROUTE_TYPE_T";
        reference " 0.2.0.";
    }

    revision "2022-07-28" {
        description "Initial version";
        reference " 0.1.0.";
    }



    typedef  ripng_redistribute_proto_t {
        type enumeration {
            enum kernel {
                value 0;
                if-feature feature-list:HAVE_SWFWDR;
                description "Kernel routes";
            }
            enum connected {
                value 1;
                description "Connected";
            }
            enum static {
                value 2;
                description "Static routes";
            }
            enum ospf6 {
                value 3;
                description "Open Shortest Path First (OSPF)";
            }
            enum isis {
                value 4;
                description "ISO IS-IS";
            }
            enum bgp {
                value 5;
                description "Border Gateway Protocol (BGP)";
            }
        }
        description "type definition for RIPNG_REDISTRIBUTE_PROTO_T";
    }

    typedef  ripng_vrf_redistribute_proto_t {
        type enumeration {
            enum connected {
                value 1;
                description "Connected";
            }
            enum static {
                value 2;
                description "Static routes";
            }
            enum ospf6 {
                value 3;
                description "Open Shortest Path First (OSPF)";
            }
            enum bgp {
                value 5;
                description "Border Gateway Protocol (BGP)";
            }
        }
        description "type definition for RIPNG_VRF_REDISTRIBUTE_PROTO_T";
    }

    typedef  ripng_clear_route_type_t {
        type enumeration {
            enum kernel {
                value 1;
                if-feature feature-list:HAVE_SWFWDR;
                description "Kernel routes";
            }
            enum connected {
                value 2;
                description "Connected";
            }
            enum static {
                value 3;
                description "Static routes";
            }
            enum isis {
                value 4;
                description "ISO IS-IS";
            }
            enum ospf6 {
                value 5;
                description "Open Shortest Path First (OSPF)";
            }
            enum bgp {
                value 6;
                description "Border Gateway Protocol (BGP)";
            }
            enum rip {
                value 7;
                description "Routing Information Protocol (RIP)";
            }
            enum all {
                value 8;
                description "All of the RIP routing table";
            }
        }
        description "type definition for RIPNG_CLEAR_ROUTE_TYPE_T";
    }

    typedef  ripng_route_type_t {
        type enumeration {
            enum system {
                value 0;
                description "System routes";
            }
            enum kernel {
                value 1;
                if-feature feature-list:HAVE_SWFWDR;
                description "Kernel routes";
            }
            enum connected {
                value 2;
                description "Connected";
            }
            enum static {
                value 3;
                description "Static routes";
            }
            enum rip {
                value 4;
                description "Routing Information Protocol (RIP)";
            }
            enum ripng {
                value 5;
                description "RIPng routes";
            }
            enum ospf {
                value 6;
                description "Open Shortest Path First (OSPF)";
            }
            enum ospf6 {
                value 7;
                description "Open Shortest Path First (OSPF) v6";
            }
            enum isis {
                value 8;
                description "ISO IS-IS";
            }
            enum bgp {
                value 9;
                description "Border Gateway Protocol (BGP)";
            }
        }
        description "type definition for RIPNG_ROUTE_TYPE_T";
    }

    typedef  ripng_route_sub_type_t {
        type enumeration {
            enum rip-other {
                value 0;
                description "RIP,Other";
            }
            enum rip-entry {
                value 1;
                description "RIP,Entry";
            }
            enum rip-connect {
                value 2;
                description "RIP,Connect";
            }
            enum rip-static {
                value 3;
                description "RIP,Static";
            }
            enum rip-aggregate {
                value 4;
                description "RIP,Aggregate";
            }
        }
        description "type definition for RIPNG_ROUTE_SUB_TYPE_T";
    }

    typedef  ripng_direction_t {
        type enumeration {
            enum in {
                value 0;
                description "For incoming updates";
            }
            enum out {
                value 1;
                description "For outgoing updates";
            }
        }
        description "type definition for RIPNG_DIRECTION_T";
    }

    typedef  ripng_debug_t {
        type bits {
            bit events {
                position 1;
                description "RIP events";
            }
            bit packet-send {
                position 2;
                description "RIP packets,RIP send packets";
            }
            bit packet-recv {
                position 3;
                description "RIP packets,RIP receive packets";
            }
            bit packet-detail {
                position 4;
                description "RIP packets,Detailed information display";
            }
            bit nsm {
                position 5;
                description "RIP NSM information";
            }
            bit rib {
                position 6;
                if-feature feature-list:HAVE_RIBD;
                description "RIP RIB information";
            }
        }
        description "type definition for RIPNG_DEBUG_T";
    }

}
