/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-isis-interface.yang
*
*/

submodule ipi-isis-interface {

    yang-version 1.1;

    belongs-to  ipi-isis { prefix ipi-isis; }

    import feature-list {
        prefix feature-list;
        revision-date 2026-09-15;
    }

    import cml-data-types {
        prefix cml-data-types;
        revision-date 2026-05-15;
    }

    import ipi-isis-types {
        prefix ipi-isis-types;
        revision-date 2025-12-05;
    }

    import ipi-interface {
        prefix ipi-interface;
        revision-date 2026-03-10;
    }

    import ietf-inet-types {
        prefix inet;
        revision-date 2013-07-15;
    }

    include ipi-isis-interface-flxalg { revision-date 2026-02-04;}
    organization
        "IP Infusion Inc.";

    contact
        "Address: 3965 Freedom Circle, Suite 200, Santa Clara, CA 95054
         Phone: +1 408-400-1900
         E-mail: support@ipinfusion.com
         Web: http://www.ipinfusion.com/";

    description
        "Model for managing IS-IS interfaces -- auguments the ISIS model for
                interface configurations and state";


    revision "2025-09-06" {
        description "Flex-Algo ASLA SRLG Min Value changes dependency";
        reference " 0.9.02.";
    }

    revision "2025-09-04" {
        description "Removed EVPN_IRB_IF_MODE while configuring IRB interface";
        reference " 0.9.1.";
    }

    revision "2025-06-09" {
        description "Flex-Algo ASLA TE-Metric Max Value changes dependency";
        reference " 0.9.00.";
    }

    revision "2025-05-28" {
        description "ISIS Interface ASLA params change";
        reference " 0.8.14.";
    }

    revision "2025-02-20" {
        description "ISIS authentication help string changed";
        reference " 0.8.13.";
    }

    revision "2025-02-04" {
        description "Changed Interface Flex-Algo ASLA SRLG params to hidden";
        reference " 0.8.12.";
    }

    revision "2024-12-22" {
        description "Updated revisions since included file ipi-isis-type was updated";
        reference " 0.8.11.";
    }

    revision "2024-10-22" {
        description "Added streaming telemetry support for ISIS";
        reference " 0.8.10.";
    }

    revision "2024-09-20" {
        description "Added flag for when tag with HAVE_SRLG";
        reference " 0.8.9.";
    }

    revision "2024-09-12" {
        description "Added dependency Skip for Flex-Algo ASLA TE Metric params";
        reference " 0.8.8.";
    }

    revision "2024-06-25" {
        description "Added interface delay normalization parameters";
        reference " 0.8.7.";
    }

    revision "2024-04-16" {
        description "Interface Flex-Algo bandwidth metric params added via included XML";
        reference " 0.8.6.";
    }

    revision "2024-04-10" {
        description "Removed unused imports from Interface Flex-Algo XML files";
        reference " 0.8.5.";
    }

    revision "2024-03-30" {
        description "Moved back Flex-Algo call backs to this file's callbacks Yaml files";
        reference " 0.8.4.";
    }

    revision "2024-03-09" {
        description "Moved all Flexible Algorithm related callbacks into a seperate yaml files";
        reference " 0.8.3.";
    }

    revision "2024-03-06" {
        description "Moved Flexible Algorithm related data models into a separate XML file";
        reference " 0.8.2.";
    }

    revision "2024-01-22" {
        description "Updated Flexible Algorithm specific ASLA Interface parameters";
        reference " 0.8.1.";
    }

    revision "2023-09-29" {
        description "Added Flexible Algorithm specific ASLA Interface parameters";
        reference " 0.8.0.";
    }

    revision "2023-08-10" {
        description "JIRA-61800:Added remaining enclosing containers";
        reference " 0.7.4.";
    }

    revision "2023-08-04" {
        description "Addition of missing cliprependstr";
        reference " 0.7.3.";
    }

    revision "2023-07-25" {
        description "ISIS CLI Commands for EVPN IRB Interface";
        reference " 0.7.2.";
    }

    revision "2023-07-11" {
        description "Added attributes for grouping adjacency-state";
        reference " 0.7.1.";
    }

    revision "2023-06-15" {
        description "JIRA-61800:Added enclosing containers";
        reference " 0.7.0.";
    }

    revision "2022-08-10" {
        description "Debug hierarchy change";
        reference " 0.6.1.";
    }

    revision "2022-07-30" {
        description "Updated when expressions in yang";
        reference " 0.6.0.";
    }

    revision "2022-06-01" {
        description "Updated the yang file with feature";
        reference " 0.5.0.";
    }

    revision "2022-04-04" {
        description "Added if-feature whereever needed";
        reference " 0.4.0.";
    }

    revision "2021-09-03" {
        description "Update descriptions of attribute";
        reference " 0.3.0.";
    }

    revision "2020-12-15" {
        description "Change to have data-types in lower case instead of camel case";
        reference " 0.2.0.";
    }

    revision "2020-05-06" {
        description "Datamodel restructuring";
        reference " 0.1.0.";
    }

    grouping isis-interface-config {
        description
            "Configuration items for ISIS interfaces";
        leaf name  {
            type  leafref {
                path  "/ipi-interface:interfaces/ipi-interface:interface/ipi-interface:name";
            }
            description "The interface name to configure the ISIS parameters.";
        } // END of name definition.

        leaf minimal  {
            type  ipi-isis-types:isis_auth_level_type_t;
            default "level-1-2";
            description "Use this attribute to set the minimal Hello interval in seconds.";
        } // END of minimal definition.

        leaf send-only  {
            type  ipi-isis-types:isis_auth_level_type_t;
            default "level-1-2";
            description "Use this attribute to set the send-only option to the
                        interface-related packets. Use this attribute before configuring the
                        ISIS authentication mode and ISIS authentication key-chain, so that
                        the implementation of authentication goes smoothly. That is, the
                        routers will have more time for the keys to be configured on each
                        router if authentication is inserted only on the packets being sent,
                        not checked on packets being received. After all routers that must
                        communicate are configured with this attribute, enable the
                        authentication mode and key chain on each router.";
        } // END of send-only definition.

    } // END of isis-interface-config definition.
    grouping isis-interface-state {
        description
            "State items for ISIS interfaces";
        leaf isis-tag  {
            type  string {
                length "1..1965";
                pattern "[^?' =,>|]+";
            }
            config false;
            description "ISIS instance attached to the Interface";
        } // END of isis-tag definition.

        leaf network-type  {
            type  string {
                length "1..1965";
                pattern "[^?' =,>|]+";
            }
            config false;
            description "ISIS network type (p2p, broadcast)";
        } // END of network-type definition.

        leaf circuit-type  {
            type  ipi-isis-types:isis_circuit_type_t;
            config false;
            description "ISIS circuit type (level-1, level-2, level-1-2)";
        } // END of circuit-type definition.

        leaf local-circuit-id  {
            type  string {
                length "1..1965";
                pattern "[^?' =,>|]+";
            }
            config false;
            description "Locally generated circuit ID for each ISIS interface per ISIS neighbor";
        } // END of local-circuit-id definition.

        leaf extended-circuit-id  {
            type  string {
                length "1..1965";
                pattern "[^?' =,>|]+";
            }
            config false;
            description "Extended Local circuit ID";
        } // END of extended-circuit-id definition.

        leaf local-snpa  {
            type  cml-data-types:cml_mac_addr_t {
                length "1..1965";
            }
            config false;
            description "local Snpa address.It is a MAC address on a LAN";
        } // END of local-snpa definition.

    } // END of isis-interface-state definition.
    grouping isis-interface-bandwidth-state {
        description
            "State items for ISIS Interface Bandwidth";
        leaf value  {
            if-feature feature-list:HAVE_ISIS_TE;
            type  string {
                length "1..1965";
                pattern "[^?' =,>|]+";
            }
            config false;
            description "Bandwidth configured for the ISIS interface";
        } // END of value definition.

        leaf maximum-resverable  {
            if-feature feature-list:HAVE_ISIS_TE;
            type  string {
                length "1..1965";
                pattern "[^?' =,>|]+";
            }
            config false;
            description "Maximum reservable bandwidth for the ISIS interface";
        } // END of maximum-resverable definition.

    } // END of isis-interface-bandwidth-state definition.
    grouping circuit-counters-structural-state {
        description
            "This grouping defines circuit counters.";
        container state {
            config false;
            description
                "The container defines a list of counters for IS circuit";
            uses isis-circuit-counters-state;
        } // END of state-container definition.
    } // END of circuit-counters-structural-state definition.
    grouping isis-circuit-counters-state {
        description
            "Operational state parameters relating to counters specific to one
                        interface or circuit.";
        leaf adjacency-changes  {
            type  uint32;
            config false;
            description "Number of times an adjacency state change has occurred on this circuit";
        } // END of adjacency-changes definition.

        leaf adjacency-number  {
            type  uint32;
            config false;
            description "Number of adjacencies on this circuit.";
        } // END of adjacency-number definition.

        leaf init-fails  {
            type  uint32;
            config false;
            description "Number of times initialization of this circuit has failed. This counts
                        events such as PPP NCP failures.";
        } // END of init-fails definition.

        leaf rejected-adjacency  {
            type  uint32;
            config false;
            description "Number of times an adjacency has been rejected on this circuit.";
        } // END of rejected-adjacency definition.

        leaf id-field-length-mismatches  {
            type  uint32;
            config false;
            description "Number of times an IS-IS control PDU with an ID field length different
                        from that for this system has been received.";
        } // END of id-field-length-mismatches definition.

        leaf max-area-address-mismatches  {
            type  uint32;
            config false;
            description "Number of times an IS-IS control PDU with a max area address field
                        different from that for this system has been received.";
        } // END of max-area-address-mismatches definition.

        leaf authentication-type-fails  {
            type  uint32;
            config false;
            description "Number of times an IS-IS control PDU with an auth type field different
                        Number of times an IS-IS control PDU with an auth type field different";
        } // END of authentication-type-fails definition.

        leaf authentication-fails  {
            type  uint32;
            config false;
            description "Number of times an IS-IS control PDU with the correct auth type has
                        failed to pass authentication validation.";
        } // END of authentication-fails definition.

        leaf lan-dis-changes  {
            type  uint32;
            config false;
            description "Number of times the Designated IS has changed on this circuit at this
                        level. If the circuit is point to point, this count is zero.";
        } // END of lan-dis-changes definition.

    } // END of isis-circuit-counters-state definition.
    grouping isis-interface-connected-ipv4-state {
        description
            "This grouping defines connected ipv4 addresses";
        leaf-list address  {
            type  cml-data-types:cml_ipv4_addr_prefix_t;
            description "IP interface addresses that are connected to particular interface";
        } // END of address definition.

    } // END of isis-interface-connected-ipv4-state definition.
    grouping isis-interface-connected-ipv6-state {
        description
            "This grouping defines connected ipv6 addresses";
        leaf-list address  {
            type  cml-data-types:cml_ipv6_prefix_t;
            description "IPv6 interface addresses that are connected to particular interface";
        } // END of address definition.

    } // END of isis-interface-connected-ipv6-state definition.
    grouping isis-interface-priority-bandwidth-state {
        description
            "This grouping defines badnwidth at particular priority value";
        leaf priority  {
            type  uint8;
            description "Priority value 0-7. Used as a synthetic key";
        } // END of priority definition.

        leaf available-bandwidth  {
            type  string {
                length "1..1965";
                pattern "[^?' =,>|]+";
            }
            description "Available bandwidth at particular priority value";
        } // END of available-bandwidth definition.

    } // END of isis-interface-priority-bandwidth-state definition.
    grouping isis-interface-lan-neighbor-state {
        description
            "This grouping defines state information for lan neighbors";
        leaf system-id  {
            type  string {
                length "1..1965";
                pattern "[^?' =,>|]+";
            }
            description "ISIS neighbor system-id.";
        } // END of system-id definition.

        leaf adjacency-type  {
            type  ipi-isis-types:isis_level_t;
            description "Formed ISIS adjacency type(level-1, level-2, level-1-2).";
        } // END of adjacency-type definition.

        uses isis-interface-adjacency-state;
    } // END of isis-interface-lan-neighbor-state definition.
    grouping isis-interface-adjacency-state {
        description
            "This grouping defines ISIS adjacency per interface.";
        leaf adjacency-advertisement  {
            type  ipi-isis-types:isis_nbr_adj_t;
            config false;
            description "Adjacency type Supress or Advertise";
        } // END of adjacency-advertisement definition.

        leaf neighbor-snpa  {
            type  string {
                length "1..1965";
                pattern "[^?' =,>|]+";
            }
            config false;
            description "ISIS neighbor SNPA.";
        } // END of neighbor-snpa definition.

        leaf-list level-1-nlp-id  {
            type  ipi-isis-types:isis_level_proto_t;
            config false;
            description "level 1 Supported Protocol. IPv4 is defined as (0xcc) and IPv6 -
                        (0x8e). ISIS reference is TLV 129.";
        } // END of level-1-nlp-id definition.

        leaf-list level-2-nlp-id  {
            type  ipi-isis-types:isis_level_proto_t;
            config false;
            description "level 2 Supported Protocol. IPv4 is defined as (0xcc) and IPv6 -
                        (0x8e). ISIS reference is TLV 129.";
        } // END of level-2-nlp-id definition.

        leaf multi-topology-type  {
            type  ipi-isis-types:isis_multi_topology_types_t;
            config false;
            description "ISIS topology type support(IPv4, IPv6)";
        } // END of multi-topology-type definition.

        leaf up-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            config false;
            description "Adjacency up time.";
        } // END of up-time definition.

        leaf adjacency-sid  {
            if-feature feature-list:HAVE_ISIS_SR;
            type  uint32;
            config false;
            description "Specify Adjacency state SID value.";
        } // END of adjacency-sid definition.

        leaf ilm-id  {
            if-feature feature-list:HAVE_ISIS_SR;
            type  uint32;
            config false;
            description "Specify ILM ID at adjacency state level";
        } // END of ilm-id definition.

        leaf bypass-trunk-id  {
            if-feature feature-list:HAVE_ISIS_SR;
            type  uint32;
            config false;
            description "This attr is used to specify Bypass Trunk ID";
        } // END of bypass-trunk-id definition.

        leaf backup-ilm-id  {
            if-feature feature-list:HAVE_ISIS_SR;
            if-feature feature-list:HAVE_ISIS_TI_LFA;
            type  uint32;
            config false;
            description "Specify backup ILM ID for adjacency state";
        } // END of backup-ilm-id definition.

        leaf backup-ilm-msg-id  {
            if-feature feature-list:HAVE_ISIS_SR;
            if-feature feature-list:HAVE_ISIS_TI_LFA;
            type  uint32;
            config false;
            description "Specify Backup ILM msg ID";
        } // END of backup-ilm-msg-id definition.

        leaf p-router-id  {
            if-feature feature-list:HAVE_ISIS_SR;
            if-feature feature-list:HAVE_ISIS_TI_LFA;
            type  inet:ipv4-address;
            config false;
            description "Specify P-router ID for adjacency state level";
        } // END of p-router-id definition.

        leaf q-router-id  {
            if-feature feature-list:HAVE_ISIS_SR;
            if-feature feature-list:HAVE_ISIS_TI_LFA;
            type  inet:ipv4-address;
            config false;
            description "Specify Q-router ID for adjacency state level";
        } // END of q-router-id definition.

        leaf pq-router-id  {
            if-feature feature-list:HAVE_ISIS_SR;
            if-feature feature-list:HAVE_ISIS_TI_LFA;
            type  inet:ipv4-address;
            config false;
            description "Specify PQ-router ID for adjacency state level";
        } // END of pq-router-id definition.

        leaf neighbor-protocol  {
            type  ipi-isis-types:isis_neighbour_protocol_t;
            config false;
            description "Neighbore protocol type M-ISIS or ISIS";
        } // END of neighbor-protocol definition.

        leaf-list area-address  {
            type  string {
                length "1..1965";
                pattern "[^?' =,>|]+";
            }
            description "List of ISIS area-address(es).";
        } // END of area-address definition.

    } // END of isis-interface-adjacency-state definition.
    grouping isis-interface-adjacency-ipv4-address-state {
        description
            "This grouping defines state information of neighbour IPv4 addresses.";
        leaf-list address  {
            type  inet:ipv4-address;
            description "Neighbor IP Address";
        } // END of address definition.

    } // END of isis-interface-adjacency-ipv4-address-state definition.
    grouping isis-interface-adjacency-ipv6-address-state {
        description
            "This grouping defines state information of neighbour IPv6 addresses.";
        leaf-list address  {
            type  inet:ipv6-address;
            description "Neighbor IPv6 Address";
        } // END of address definition.

    } // END of isis-interface-adjacency-ipv6-address-state definition.
    grouping isis-interface-lan-neighbor-level-state {
        description
            "This grouping defines state information of neighbour level.";
        leaf level  {
            type  ipi-isis-types:isis_level_t;
            description "Per level neighbour info";
        } // END of level definition.

        leaf adjacency-state  {
            type  ipi-isis-types:isis_state_t;
            description "3-way ISIS adjacency state(up, down, init).";
        } // END of adjacency-state definition.

        leaf adjacency-id  {
            type  uint32;
            description "Neighbor level adjacency ID";
        } // END of adjacency-id definition.

        leaf remaining-hold-time  {
            type  string {
                length "1..1965";
                pattern "[^?' =,>|]+";
            }
            description "Holding time in seconds for adjacency. This value is based on received
                        hello PDUs and the elapsed time since receipt.";
        } // END of remaining-hold-time definition.

        leaf priority  {
            type  uint8;
            description "Priority of the neighboring IS(LAN Hello only).";
        } // END of priority definition.

    } // END of isis-interface-lan-neighbor-level-state definition.
    grouping isis-interface-level-state {
        description
            "This grouping defines state information of level per interface.";
        leaf level-number  {
            type  ipi-isis-types:isis_iflevel_t;
            description "ISIS Level index";
        } // END of level-number definition.

        leaf next-hello-interval  {
            type  cml-data-types:cml_line_t {
                length "1..1965";
            }
            description "Next IS-IS Hello on this Interface";
        } // END of next-hello-interval definition.

        leaf mtu  {
            type  uint32;
            description "The maximum size in bytes of an IS-IS Link state PDU.";
        } // END of mtu definition.

        leaf circuit-id  {
            type  string {
                length "1..1965";
                pattern "[^?' =,>|]+";
            }
            description "DIS of this interface - Source ID";
        } // END of circuit-id definition.

        leaf active-adjancency-count  {
            type  int32;
            description "Number of active adjacencies in each level(AdjsUp)";
        } // END of active-adjancency-count definition.

        leaf csnp-interval  {
            type  cml-data-types:cml_line_t {
                length "1..1965";
            }
            description "The interval, specified in seconds, at which periodic CSNP packets
                        should be transmitted by the local IS.";
        } // END of csnp-interval definition.

        uses isis-circuit-counters-state;
    } // END of isis-interface-level-state definition.
    grouping packet-counters-generic-state {
        description
            "Operational state parameters relating to LSP packet counters.";
        leaf received  {
            type  uint32;
            description "The number of the specified type of PDU received on the interface.";
        } // END of received definition.

        leaf sent  {
            type  uint32;
            description "The number of the specified type of PDU that have been sent by the
                        local system on the interface.";
        } // END of sent definition.

    } // END of packet-counters-generic-state definition.
    grouping isis-interface-p2p-neighbor-state {
        description
            "This grouping defines state information for p2p neighbors";
        leaf system-id  {
            type  string {
                length "1..1965";
                pattern "[^?' =,>|]+";
            }
            description "ISIS neighbor system-id.";
        } // END of system-id definition.

        leaf circuit-id  {
            type  string {
                length "1..1965";
                pattern "[^?' =,>|]+";
            }
            description "Neighbor Local Circuit ID for P2P";
        } // END of circuit-id definition.

        leaf adjacency-state  {
            type  ipi-isis-types:isis_state_t;
            description "3-way ISIS adjacency state(up, down, init).";
        } // END of adjacency-state definition.

        leaf remaining-hold-time  {
            type  string {
                length "1..1965";
                pattern "[^?' =,>|]+";
            }
            description "Holding time in seconds for adjacency. This value is based on received
                        hello PDUs and the elapsed time since receipt.";
        } // END of remaining-hold-time definition.

        leaf adjacency-type  {
            type  string {
                length "1..1965";
                pattern "[^?' =,>|]+";
            }
            description "Neighbor level adjacency ID";
        } // END of adjacency-type definition.

        uses isis-interface-adjacency-state;
    } // END of isis-interface-p2p-neighbor-state definition.
    grouping isis-interface-params-config {
        description
            "This grouping           defines config information for isis interface.";
        leaf network-type  {
            type  ipi-isis-types:isis_network_t;
            description "Use this attribute to change a broadcast interface network type to a
                        point-to-point network type and vice-versa.";
        } // END of network-type definition.

        leaf circuit-type  {
            type  ipi-isis-types:isis_circuit_type_t;
            default "level-1-2";
            description "Use this attribute to set the circuit type for the interface. If
                        level-1 or level-2-only is specified in this attribute, ISIS sends
                        only the specified level of PDUs. On the point-to-point interface,
                        there is only one type of Hello packet, so in this case ISIS Hello
                        will be sent regardless of circuit-type. If istype is configured as
                        level-1 or level-2 only, routing for this instance is performed for
                        only the specified level. In this manner, only the particular level of
                        PDU is sent on the interface.";
        } // END of circuit-type definition.

        leaf ipv4-instance-tag  {
            type  string {
                length "1..1965";
                pattern "[^?' =,>|]+";
            }
            description "Use this attribute to enable ISIS IPv4 routing on the interface. This
                        attribute is mandatory to ISIS configuration. Match the ISIS instance
                        tag to one of existing instance.s tags, or a new instance with the tag
                        name should be initiated, otherwise routing will not run on this
                        interface. Configuring this attribute, the router sends ISIS Hello
                        with IP address TLV on this interface, and IP reachability information
                        TLV in the LSP will be updated.";
        } // END of ipv4-instance-tag definition.

        leaf ipv6-instance-tag  {
            if-feature feature-list:HAVE_IPV6;
            type  string {
                length "1..1965";
                pattern "[^?' =,>|]+";
            }
            description "Use this attribute to enable ISIS IPv6 routing on the interface. This
                        attribute is mandatory to IPv6 ISIS configuration. Match the ISIS
                        instance tag to one of existing instance.s tags, or a new instance
                        with the tag name should be initiated, otherwise routing will not run
                        on this interface.Configuring this attribute, the router sends ISIS
                        Hello with IPv6 address TLV on this interface, and IPv6 reachability
                        information TLV in the LSP will be updated.";
        } // END of ipv6-instance-tag definition.

        leaf lsp-interval  {
            type  uint32 {
                 range "1..4294967295"  {
                    description "1..4294967295: Supported range 1 - 4294967295";
                 }
            }
            default "33";
            description "Use this attribute to set the Link State Packet (LSP) transmission
                        interval. Configuring this attribute changes the minimum interval
                        between two consecutive LSP transmission. When flooding or some other
                        event triggers LSP to transmit, the LSP is put on the interface queue
                        and scheduled to transmit according to this interval. Two consecutive
                        LSP transmissions are scheduled to have at least this interval.";
        } // END of lsp-interval definition.

        leaf retransmit-interval  {
            type  uint16 {
                 range "1..65535"  {
                    description "1..65535: Supported range 1 - 65535";
                 }
            }
            default "5";
            description "Interval between retransmissions of the same LSP in seconds";
        } // END of retransmit-interval definition.

        leaf disable-padding  {
            type  empty;
            description "Use this attribute to configure/unconfigure the padding of the ISIS
                        Hello packet. ISIS pads the Hello packet by default to notify
                        neighbors of the supported MTU size.";
        } // END of disable-padding definition.

        leaf mesh-group-id  {
            type  ipi-isis-types:isis_mesh_type_t;
            description "Use this attribute to specify to block LSPs on the current interface.
                        If an interface is configured as mesh group blocked,. the standard LSP
                        database synchronization process is applied if the interface receives
                        CSNP or PSNP.";
        } // END of mesh-group-id definition.

        leaf delay-normalize-interval  {
            type  uint32 {
                 range "1..2147483"  {
                    description "1..2147483: Supported range 1 - 2147483";
                 }
            }
            description "The value of the normalization interval for measured delay";
        } // END of delay-normalize-interval definition.

        leaf delay-normalize-offset  {
            type  uint32 {
                 range "1..2147483"  {
                    description "1..2147483: Supported range 1 - 2147483";
                 }
            }
            description "The value of the normalization interval for measured delay";
        } // END of delay-normalize-offset definition.

    } // END of isis-interface-params-config definition.
    grouping isis-interface-params-bfd-config {
        description
            "Configuration items for ISIS BFD";
        leaf enable  {
            type  empty;
            description "Use this attribute to enable the BFD check on interface.";
        } // END of enable definition.

        leaf disable  {
            type  empty;
            description "Use this attribute to disable the BFD check on interface.";
        } // END of disable definition.

    } // END of isis-interface-params-bfd-config definition.
    grouping isis-interface-params-frr-config {
        description
            "Configuration items for ISIS FRR";
        leaf disable-level-1  {
            if-feature feature-list:HAVE_ISIS_LFA;
            type  empty;
            description "Use this attribute to disable frr on an interface for level-1.";
        } // END of disable-level-1 definition.

        leaf disable-level-2  {
            if-feature feature-list:HAVE_ISIS_LFA;
            type  empty;
            description "Use this attribute to disable frr on an interface for level-2.";
        } // END of disable-level-2 definition.

    } // END of isis-interface-params-frr-config definition.
    grouping isis-interface-level-params-info-config {
        description
            "Configuration items for ISIS interface level";
        leaf level  {
            type  ipi-isis-types:isis_level_t;
            default "level-1-2";
            description "ISIS level number (level-1, level-2, level-1-2).";
        } // END of level definition.

        leaf hello-interval  {
            type  uint16 {
                 range "1..65535"  {
                    description "1..65535: Supported range 1 - 65535";
                 }
            }
            default "10";
            description "Use this attribute to set the Hello interval in seconds. The
                        Hello-interval is set with the hello-multiplier. Configuring this
                        attribute changes the time interval between two consecutive Hello
                        transmissions. If a device receives its own LSP with a maximum
                        sequence number, then it suspends ISIS for the hold interval. DIS
                        sends Hello transmissions at three times the rate than non-DIS. If
                        ISIS is elected as DIS on this interface, ISIS sends Hello every 3.3
                        seconds. If minimal keyword is specified, Holding timer in Hello PDU
                        is set to 1 second and Hello interval is calculated by dividing by the
                        hello-multiplier.";
        } // END of hello-interval definition.

        leaf hello-multiplier  {
            type  uint8 {
                 range "2..100"  {
                    description "2..100: Supported range 2 - 100";
                 }
            }
            default "3";
            description "Use this attribute to set multiplier for Hello holding time. Changes
                        Holding Timer in Hello PDU. Holding timer is calculated by
                        .Hello-Interval. multiplied by this value. If minimal keyword is
                        specified with the Hello-Interval, the holding timer is set to 1
                        second and the hello-interval is calculated by dividing 1 by this
                        value.";
        } // END of hello-multiplier definition.

        leaf csnp-interval  {
            type  uint16 {
                 range "1..65535"  {
                    description "1..65535: Supported range 1 - 65535";
                 }
            }
            default "10";
            description "Use this attribute to set CSNP (Complete sequence number PDU) interval
                        in seconds.Configuring this attribute changes the interval between two
                        consecutive CSNP transmission. By default, CSNP is sent every 10
                        seconds only by LAN DIS. This parameter is only valid on broadcast
                        interface, since periodic CSNP is only sent on broadcast interface,
                        while CSNP on Point-to-Point interface is sent only when adjacency is
                        initiated.";
        } // END of csnp-interval definition.

        leaf priority  {
            type  uint8 {
                 range "0..127"  {
                    description "0..127: Supported range 0 - 127";
                 }
            }
            default "64";
            description "Use this attribute to set the priority for LAN DIS election. This
                        attribute changes the priority value in LAN ISIS Hello PDUs. A lower
                        priority value is less preferred in DIS election, and a higher
                        priority value is more preferred";
        } // END of priority definition.

        leaf metric  {
            type  uint8 {
                 range "1..63"  {
                    description "1..63: Supported range 1 - 63";
                 }
            }
            default "10";
            description "Use this attribute to set default metric for the interface. The
                        interface default metric is put into IP reachability information TLVs,
                        IS reachability information TLVs and IPv6 reachability TLVs in LSPs.
                        The value is used for SPF calculation, and is applied when the
                        metric-style is configured as .narrow.";
        } // END of metric definition.

        leaf password  {
            // when " !ipi-isis-interface:interfaces/interface/interface-parameters/level-infos/level-info/authentication/config/mode ";
            type  string {
                length "1..1965";
                pattern "[^?' =,>|]+";
            }
            description "Use this attribute to set the authentication password of Hello PDU on
                        the interface.";
        } // END of password definition.

        leaf tag  {
            type  uint32 {
                 range "1..4294967295"  {
                    description "1..4294967295: Supported range 1 - 4294967295";
                 }
            }
            description "Use this attribute to sets the tag for link-state packets (LSPs) sent
                        out advertising routes for networks directly connected to an
                        interface. If you do not specify a parameter, then the tag value is
                        set for level-1-2 boundary";
        } // END of tag definition.

        leaf wide-metric  {
            type  uint32 {
                 range "1..16777214"  {
                    description "1..16777214: Supported range 1 - 16777214";
                 }
            }
            default "10";
            description "Use this attribute to set wide metric for the interface. Interface
                        wide-metric is put into Extended IP reachability TLVs, Extended IS
                        reachability TLVs and IPv6 reachability TLVs in LSPs. The value is
                        used for SPF calculation. This value is applied when metric-style is
                        configured as 'wide'.";
        } // END of wide-metric definition.

        leaf te-metric  {
            if-feature feature-list:HAVE_ISIS_TE;
            type  uint32 {
                 range "1..16777215"  {
                    description "1..16777215: Supported range 1 - 16777215";
                 }
            }
            description "Use this attribute to set te  metric for the interface. Interface
                        te-metric is put into Extended IS reachability TLVs and IPv6
                        reachability TLVs in LSPs. The value is used for CSPF calculation";
        } // END of te-metric definition.

        leaf restart-hello-interval  {
            type  uint16 {
                 range "1..65535"  {
                    description "1..65535: Supported range 1 - 65535";
                 }
            }
            default "3";
            description "Use this attribute to configure the T1 timer, interval of ISIS Hello
                        packet with restart TLV.";
        } // END of restart-hello-interval definition.

    } // END of isis-interface-level-params-info-config definition.
    grouping isis-interface-authentication-config {
        description
            "This grouping defines ISIS authentication mode configuration";
        leaf mode  {
            type  ipi-isis-types:isis_auth_mode_t;
            mandatory true;
            description "Use this attribute to set the MD5 authentication mode.";
        } // END of mode definition.

        leaf key-chain  {
            type  string {
                length "1..1965";
                pattern "[^?' =,>|]+";
            }
            description "Use this attribute to set the key chain to be used for authentication
                        on the interface-related packets.Authentication mode must be set to
                        md5/text to configure the key chain.Only one authentication key-chain
                        is applied to an ISIS interface at a time. Authentication can be
                        specified for an entire instance of ISIS, instead of at the interface
                        level, by setting the authentication key-chain attribute at global
                        level.";
        } // END of key-chain definition.

    } // END of isis-interface-authentication-config definition.
    grouping isis-interface-ldp-sync-config {
        description
            "This grouping defines ISIS/LDP Synchronization configuration.";
        leaf level  {
            type  ipi-isis-types:isis_level_igp_sync_t;
            mandatory true;
            description "Use this attribute to enable LDP-ISIS synchronization. If you do not
                        specify a parameter, then synchronization is enabled for level-1-2";
        } // END of level definition.

        leaf hold-timer  {
            // when " ipi-isis-interface:interfaces/interface/igp-ldp-sync/config/level ";
            type  uint32 {
                 range "1..2147483"  {
                    description "1..2147483: Supported range 1 - 2147483";
                 }
            }
            mandatory true;
            description "It is the max time period for which IGP should advertise the max
                        metric for the interface in case of LDP session down on that
                        interface.";
        } // END of hold-timer definition.

    } // END of isis-interface-ldp-sync-config definition.
    grouping isis-interface-ldp-sync-state {
        description
            "State information for LDP/IGP sync";
        leaf interface-name  {
            type  string {
                length "1..1965";
                pattern "[^?' =,>|]+";
            }
            config false;
            description "Interface on which LDP-IGP sync is enabled";
        } // END of interface-name definition.

    } // END of isis-interface-ldp-sync-state definition.

    grouping  interfaces-grouping {
    description
        "Top level container for interfaces, including configuration and state
                data";
    container interfaces {
        if-feature feature-list:HAVE_ISISD;
        description
            "Top level container for interfaces, including configuration and state
                    data";

        list interface {
        // when " ipi-interface:interfaces/interface/config/enable-switchport != '1' ";
            key "name";
            description
                "This list defines global ISIS interface configuration and state
                            information.";
            leaf name  {
                type  leafref {
                    path  "../config/name";
                }
                description "Reference to interface name";
            } // END of name definition.


            list bandwidth-priority {
                key "priority";
                config false;
                description
                    "This objectlist defines runtime attributes for bandwidth at a
                                particular priority value";
                leaf priority  {
                    type  leafref {
                        path  "../state/priority";
                    }
                    description "Reference to bandwidth Priority";
                } // END of priority definition.

                container state {
                    config false;
                    description
                        "This container defines bandwidth at a particular priority value.";
                    uses isis-interface-priority-bandwidth-state;
                } // END of state-container definition.
            } // End of bandwidth-priority-list

            list neighbor-lan {
                key "system-id";
                config false;
                description
                    "This objectlist defines operational parameters for neighbor-lan";
                leaf system-id  {
                    type  leafref {
                        path  "../state/system-id";
                    }
                    description "Reference to ISIS neighbor System ID";
                } // END of system-id definition.


                list adjacency {
                    key "level";
                    config false;
                    description
                        "Neighbor level context";
                    leaf level  {
                        type  leafref {
                            path  "../state/level";
                        }
                        description "Reference to LAN Neighbor index";
                    } // END of level definition.

                    container state {
                        config false;
                        description
                            "This container defines state information for ISIS lan neighbor levels.";
                        uses isis-interface-lan-neighbor-level-state;
                    } // END of state-container definition.
                } // End of adjacency-list
                container state {
                    config false;
                    description
                        "This container defines state information for ISIS lan neighbors.";
                    uses isis-interface-lan-neighbor-state;
                } // END of state-container definition.
                container ipv4-addresses {
                    config false;
                    description
                        "Neighbor IP Address(es)";
                    container state {
                        config false;
                        description
                            "This container defines state information for ISIS lan neighbors
                                    IPv4-address.";
                        uses isis-interface-adjacency-ipv4-address-state;
                    } // END of state-container definition.
                } // END of ipv4-addresses-container definition.
                container ipv6-addresses {
                    config false;
                    description
                        "Neighbor IPv6 Address(es)";
                    container state {
                        config false;
                        description
                            "This container defines state information for ISIS lan neighbors
                                    IPv6-address.";
                        uses isis-interface-adjacency-ipv6-address-state;
                    } // END of state-container definition.
                } // END of ipv6-addresses-container definition.
            } // End of neighbor-lan-list

            list level {
                key "level-number";
                config false;
                description
                    "Level for interface";
                leaf level-number  {
                    type  leafref {
                        path  "../state/level-number";
                    }
                    description "Referene to ISIS Level index";
                } // END of level-number definition.

                container state {
                    config false;
                    description
                        "This container defines state information for ISIS level per interface.";
                    uses isis-interface-level-state;
                } // END of state-container definition.
                container isis-hellos {
                    config false;
                    description
                        "This container defines ISIS Hellos packet counters.";
                    container state {
                        config false;
                        description
                            "Operational counters relating to ISIS Hellos PDUs.";
                        uses packet-counters-generic-state;
                    } // END of state-container definition.
                } // END of isis-hellos-container definition.
                container link-state-pdu {
                    config false;
                    description
                        "This container defines LSP packet counters.";
                    container state {
                        config false;
                        description
                            "This container defines LSP PDU counters.";
                        uses packet-counters-generic-state;
                    } // END of state-container definition.
                } // END of link-state-pdu-container definition.
                container complete-sequence-number-pdu {
                    config false;
                    description
                        "Operational state parameters relating to CSNPs.";
                    container state {
                        config false;
                        description
                            "Packet counters relating to CSNPs.";
                        uses packet-counters-generic-state;
                    } // END of state-container definition.
                } // END of complete-sequence-number-pdu-container definition.
                container partial-sequence-number-pdu {
                    config false;
                    description
                        "This container defines ISIS psnp packet counters.";
                    container state {
                        config false;
                        description
                            "Packet counters relating to PSNPs.";
                        uses packet-counters-generic-state;
                    } // END of state-container definition.
                } // END of partial-sequence-number-pdu-container definition.
                container unknown {
                    config false;
                    description
                        "Operational state parameters relating to IS-IS PDUs that are not
                                otherwise classified - referred to as Unknown PDUs.";
                    container state {
                        config false;
                        description
                            "Packet counters relating to unknown PDUs.";
                        uses packet-counters-generic-state;
                    } // END of state-container definition.
                } // END of unknown-container definition.
            } // End of level-list
            container config {
                description
                    "This container defines ISIS interface configuration.";
                uses isis-interface-config;
                uses isis-interface-flexalgo-config;
            } // END of config-container definition.
            container state {
                config false;
                description
                    "This container defines ISIS interface Operational states.";
                uses isis-interface-config;
                uses isis-interface-flexalgo-config;
                uses isis-interface-state;
            } // END of state-container definition.
            container bandwidth {
                config false;
                description
                    "This container defines ISIS interface bandwidth information.";
                container state {
                    config false;
                    description
                        "This container defines ISIS interface bandwidth Operational state
                                information.";
                    uses isis-interface-bandwidth-state;
                } // END of state-container definition.
            } // END of bandwidth-container definition.
            container p2p-circuit-counters {
                config false;
                description
                    "This container defines p2p circuit counters";
                uses circuit-counters-structural-state;
            } // END of p2p-circuit-counters-container definition.
            container connected-ipv4 {
                description
                    "This list contains connected ipv4 addresses";
                container state {
                    config false;
                    description
                        "This container defines connected ipv4 address.";
                    uses isis-interface-connected-ipv4-state;
                } // END of state-container definition.
            } // END of connected-ipv4-container definition.
            container connected-ipv6 {
                description
                    "This list contains connected ipv6 addresses";
                container state {
                    config false;
                    description
                        "This container defines connected ipv6 address.";
                    uses isis-interface-connected-ipv6-state;
                } // END of state-container definition.
            } // END of connected-ipv6-container definition.
            container neighbor-P2P {
                config false;
                description
                    "This container defines operational parameters for point-to-point
                            neighbors";

                list ipv4-addresses {
                    key "address";
                    config false;
                    description
                        "Neighbor IP Address(es)";
                    leaf address  {
                        type  leafref {
                            path  "../state/address";
                        }
                        description "Neighbor IP Address";
                    } // END of address definition.

                    container state {
                        config false;
                        description
                            "This container defines state information for ISIS p2p neighbors
                                    IPv4-address.";
                        uses isis-interface-adjacency-ipv4-address-state;
                    } // END of state-container definition.
                } // End of ipv4-addresses-list

                list ipv6-addresses {
                    key "address";
                    config false;
                    description
                        "Neighbor IPv6 Address(es)";
                    leaf address  {
                        type  leafref {
                            path  "../state/address";
                        }
                        description "Neighbor IPv6 Address";
                    } // END of address definition.

                    container state {
                        config false;
                        description
                            "This container defines state information for ISIS p2p neighbors
                                    IPv6-address.";
                        uses isis-interface-adjacency-ipv6-address-state;
                    } // END of state-container definition.
                } // End of ipv6-addresses-list
                container state {
                    config false;
                    description
                        "This container defines state information for p2p neighbors";
                    uses isis-interface-p2p-neighbor-state;
                } // END of state-container definition.
            } // END of neighbor-P2P-container definition.
            container interface-parameters {
                description
                    "This container contains Configurable and state Interface parameters";
                container config {
                    description
                        "This container defines config information for isis interface";
                    uses isis-interface-params-config;
                } // END of config-container definition.
                container state {
                    config false;
                    description
                        "This container defines state information for isis interface";
                    uses isis-interface-params-config;
                } // END of state-container definition.
                container bfd {
                    if-feature feature-list:HAVE_BFD;
                    description
                        "This container contains configuration and state items for bfd";
                    container config {
                        description
                            "Configuration items for ISIS BFD";
                        uses isis-interface-params-bfd-config;
                    } // END of config-container definition.
                    container state {
                        config false;
                        description
                            "State items for ISIS BFD";
                        uses isis-interface-params-bfd-config;
                    } // END of state-container definition.
                } // END of bfd-container definition.
                container fast-re-route {
                    description
                        "Configuration and state items for FRR";
                    container config {
                        description
                            "Configuration items for ISIS FRR";
                        uses isis-interface-params-frr-config;
                    } // END of config-container definition.
                    container state {
                        config false;
                        description
                            "state items for ISIS FRR";
                        uses isis-interface-params-frr-config;
                    } // END of state-container definition.
                } // END of fast-re-route-container definition.
                container level-infos {
                    description
                        "Enclosing container for the list of per interface level-information";

                    list level-info {
                        key "level";
                        description
                            "Interface Level parameter";
                        leaf level  {
                            type  leafref {
                                path  "../config/level";
                            }
                            description "ISIS level number (level-1, level-2, level-1-2).";
                        } // END of level definition.

                        container config {
                            description
                                "Configutational and state parameters for ISIS interface level";
                            uses isis-interface-level-params-info-config;
                            uses isis-interface-level-params-flexalgo-config;
                        } // END of config-container definition.
                        container state {
                            config false;
                            description
                                "State parameters for ISIS interface level";
                            uses isis-interface-level-params-info-config;
                            uses isis-interface-level-params-flexalgo-config;
                        } // END of state-container definition.
                        container authentication {
                            description
                                "Configutational and state parameters for ISIS interface level
                                        authentication";
                            container config {
                                presence "authentication mode is needed for keychain";
                                description
                                    "Configutational and state parameters for ISIS authentication";
                                uses isis-interface-authentication-config;
                            } // END of config-container definition.
                            container state {
                                config false;
                                description
                                    "State parameters for ISIS interface level authentication";
                                uses isis-interface-authentication-config;
                            } // END of state-container definition.
                        } // END of authentication-container definition.
                    } // End of level-info-list
                } // END of level-infos-container definition.
            } // END of interface-parameters-container definition.
            container igp-ldp-sync {
                if-feature feature-list:HAVE_LDPD;
                description
                    "Configuration and operational state relating to synchronisation
                            between the LDP and IS-IS";
                container config {
                    presence "yes";
                    description
                        "This container defines ISIS/IGP configuration.";
                    uses isis-interface-ldp-sync-config;
                } // END of config-container definition.
                container state {
                    config false;
                    description
                        "This container defines ISIS/IGP state information.";
                    uses isis-interface-ldp-sync-config;
                    uses isis-interface-ldp-sync-state;
                } // END of state-container definition.
            } // END of igp-ldp-sync-container definition.
        } // End of interface-list
    } // END of interfaces-container definition.
    } // END of interfaces-grouping definition.


}
