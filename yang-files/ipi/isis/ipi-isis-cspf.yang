/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-isis-cspf.yang
*
*/

submodule ipi-isis-cspf {

    yang-version 1.1;

    belongs-to  ipi-isis { prefix ipi-isis; }

    import feature-list {
        prefix feature-list;
        revision-date 2026-09-15;
    }

    import ipi-isis-types {
        prefix ipi-isis-types;
        revision-date 2025-12-05;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Model for managing IS-IS CSPF Parameters";


    revision "2025-09-01" {
        description "Changed datatypes of next-reop-due-in and  lsp-reop-time";
        reference " 0.6.1.";
    }

    revision "2025-08-08" {
        description "Added new attributes lsp-name, include-all-mask, lsp-reoptimize, lsp-in-reop-list, lsp-reop-time and next-reop-due-in to isis-cspf-lsp-state group";
        reference " 0.6.0.";
    }

    revision "2024-12-22" {
        description "Updated revisions since included file ipi-isis-type was updated";
        reference " 0.5.2.";
    }

    revision "2023-08-10" {
        description "JIRA-61800:Added remaining enclosing containers";
        reference " 0.5.1.";
    }

    revision "2023-06-15" {
        description "JIRA-61800:Added enclosing containers";
        reference " 0.5.0.";
    }

    revision "2022-06-01" {
        description "Updated the yang file with feature";
        reference " 0.4.0.";
    }

    revision "2021-09-03" {
        description "Update descriptions of attribute";
        reference " 0.3.0.";
    }

    revision "2020-12-15" {
        description "Change to have data-types in lower case instead of camel case";
        reference " 0.2.0.";
    }

    revision "2020-05-06" {
        description "Datamodel restructuring";
        reference " 0.1.0.";
    }

    grouping isis-cspf-setup-priority-state {
        description
            "State items for ISIS CSPF Setup Priority";
        leaf setup-priority  {
            type  int8;
            description "Setup Priority";
        } // END of setup-priority definition.

    } // END of isis-cspf-setup-priority-state definition.
    grouping isis-cspf-lsp-state {
        description
            "State items for ISIS CSPF LSP";
        leaf lsp-id  {
            type  uint32;
            description "LSP ID";
        } // END of lsp-id definition.

        leaf metric  {
            type  uint32;
            description "ISIS CSPF LSP Metric Value";
        } // END of metric definition.

        leaf p2mp-id  {
            if-feature feature-list:HAVE_MPLS_P2MP;
            type  uint32;
            description "ISIS CSPF LSP P2MP-ID";
        } // END of p2mp-id definition.

        leaf sub-group-id  {
            if-feature feature-list:HAVE_MPLS_P2MP;
            type  uint16;
            description "ISIS CSPF LSP Sub-Group ID";
        } // END of sub-group-id definition.

        leaf retry-interval  {
            type  uint16;
            description "ISIS CSPF LSP Retry Interval";
        } // END of retry-interval definition.

        leaf retry-limit  {
            type  uint16;
            description "ISIS CSPF LSP Retry Limit";
        } // END of retry-limit definition.

        leaf tunnel-egress-ip  {
            type  inet:ipv4-address;
            description "ISIS CSPF LSP Egress Tunnel ID";
        } // END of tunnel-egress-ip definition.

        leaf tunnel-ingress-ip  {
            type  inet:ipv4-address;
            description "ISIS CSPF LSP Ingress Tunnel ID";
        } // END of tunnel-ingress-ip definition.

        leaf extended-tunnel-id  {
            type  inet:ipv4-address;
            description "ISIS CSPF LSP Extended Tunnel ID";
        } // END of extended-tunnel-id definition.

        leaf lsp-name  {
            type  string {
                length "1..1965";
                pattern "[^?' =,>|]+";
            }
            description "ISIS CSPF LSP Name";
        } // END of lsp-name definition.

        leaf status  {
            type  string {
                length "1..1965";
                pattern "[^?' =,>|]+";
            }
            description "ISIS CSPF LSP Status";
        } // END of status definition.

        leaf client-id  {
            type  uint8;
            description "ISIS CSPF LSP Client ID";
        } // END of client-id definition.

        leaf hop-limit  {
            type  int16;
            description "ISIS CSPF LSP Hop Limit";
        } // END of hop-limit definition.

        leaf include-mask  {
            type  int8;
            description "ISIS CSPF LSP Include Mask";
        } // END of include-mask definition.

        leaf include-all-mask  {
            type  int8;
            description "ISIS CSPF LSP Include All Mask";
        } // END of include-all-mask definition.

        leaf exclude-mask  {
            type  int8;
            description "ISIS CSPF LSP Exclude Mask";
        } // END of exclude-mask definition.

        leaf hold-priority  {
            type  uint8;
            description "ISIS CSPF LSP Hold Priority";
        } // END of hold-priority definition.

        leaf retry-count  {
            type  uint16;
            description "ISIS CSPF LSP Retry Count";
        } // END of retry-count definition.

        leaf bandwidth  {
            type  string {
                length "1..1965";
                pattern "[^?' =,>|]+";
            }
            description "ISIS CSPF LSP Bandwidth";
        } // END of bandwidth definition.

        leaf trunk-id  {
            type  uint32;
            description "ISIS CSPF LSP Trunk Id";
        } // END of trunk-id definition.

        leaf lsp-type  {
            type  ipi-isis-types:isis_cspf_lsp_type_t;
            description "ISIS CSPF LSP Primary/backup lsp";
        } // END of lsp-type definition.

        leaf lsp-reoptimize  {
            type  string {
                length "1..1965";
                pattern "[^?' =,>|]+";
            }
            description "ISIS CSPF LSP Reoptimize";
        } // END of lsp-reoptimize definition.

        leaf lsp-in-reop-list  {
            type  string {
                length "1..1965";
                pattern "[^?' =,>|]+";
            }
            description "ISIS CSPF LSP in Reop-List";
        } // END of lsp-in-reop-list definition.

        leaf lsp-reop-time  {
            type  string {
                length "1..1965";
            }
            description "ISIS CSPF LSP ReopTime";
        } // END of lsp-reop-time definition.

        leaf next-reop-due-in  {
            type  string {
                length "1..1965";
            }
            description "ISIS CSPF LSP Next Reop Due in";
        } // END of next-reop-due-in definition.

    } // END of isis-cspf-lsp-state definition.
    grouping isis-cspf-lsp-constraint-state {
        description
            "State items for ISIS CSPF LSP Constraint";
        leaf index  {
            type  uint32;
            description "CSPF LSP Constraint Index";
        } // END of index definition.

        leaf ip-address  {
            type  inet:ipv4-address;
            description "CSPF LSP Constraint IP Address";
        } // END of ip-address definition.

        leaf path-type  {
            type  ipi-isis-types:isis_cspf_path_type_t;
            description "CSPF LSP Constraint Type";
        } // END of path-type definition.

    } // END of isis-cspf-lsp-constraint-state definition.
    grouping isis-cspf-lsp-exclude-constraint-state {
        description
            "State items for ISIS CSPF LSP Exclude Constraint";
        leaf ip-address  {
            type  inet:ipv4-address;
            description "CSPF LSP Exclude Constraint State IP Address";
        } // END of ip-address definition.

        leaf interface-id  {
            if-feature feature-list:HAVE_GMPLS;
            type  uint32;
            description "CSPF LSP Exclude Constraint Interface ID";
        } // END of interface-id definition.

        leaf type  {
            type  ipi-isis-types:isis_cspf_constraint_type_t;
            description "CSPF LSP Exclude Constraint State Type";
        } // END of type definition.

    } // END of isis-cspf-lsp-exclude-constraint-state definition.
    grouping isis-cspf-lsp-computed-ero-state {
        description
            "State items for ISIS CSPF LSP Computed ERO";
        leaf local-ip-address  {
            type  inet:ipv4-address;
            description "CSPF Path LSP Computed ERO Local IP Address";
        } // END of local-ip-address definition.

        leaf remote-ip-address  {
            type  inet:ipv4-address;
            description "CSPF Path LSP Computed ERO Remote IP Address";
        } // END of remote-ip-address definition.

    } // END of isis-cspf-lsp-computed-ero-state definition.

    grouping  cspf-grouping {
    description
        "This container defines the ISIS CSPF Information";
    container cspf {
        if-feature feature-list:HAVE_ISIS_CSPF;
        if-feature feature-list:HAVE_ISISD;
        config false;
        description
            "This container defines the ISIS CSPF Information";

        list lsp {
            key "setup-priority";
            config false;
            description
                "This objectlist defines the ISIS CSPF Priority lists";
            leaf setup-priority  {
                type  leafref {
                    path  "../state/setup-priority";
                }
                description "Setup Priority";
            } // END of setup-priority definition.


            list lsp-status {
                key "lsp-id";
                config false;
                description
                    "This objectlist defines the ISIS CSPF LSP Status";
                leaf lsp-id  {
                    type  leafref {
                        path  "../state/lsp-id";
                    }
                    description "LSP ID";
                } // END of lsp-id definition.


                list path-constraint {
                    key "index";
                    config false;
                    description
                        "This objectlist defines the ISIS CSPF LSP Path Constraint";
                    leaf index  {
                        type  leafref {
                            path  "../state/index";
                        }
                        description "CSPF LSP Constraint Index";
                    } // END of index definition.

                    container state {
                        config false;
                        description
                            "This container defines the ISIS CSPF LSP Path Constraint State";
                        uses isis-cspf-lsp-constraint-state;
                    } // END of state-container definition.
                } // End of path-constraint-list

                list exclude-path-constraint {
                    key "ip-address";
                    config false;
                    description
                        "This objectlist defines the ISIS CSPF LSP Exclude Path Constraint";
                    leaf ip-address  {
                        type  leafref {
                            path  "../state/ip-address";
                        }
                        description "CSPF LSP Exclude Constraint State IP Address";
                    } // END of ip-address definition.

                    container state {
                        config false;
                        description
                            "This objectlist defines the ISIS CSPF LSP Exclude Path Constraint
                                    State";
                        uses isis-cspf-lsp-exclude-constraint-state;
                    } // END of state-container definition.
                } // End of exclude-path-constraint-list

                list path-computed-ero {
                    key "local-ip-address";
                    config false;
                    description
                        "This objectlist defines the ISIS CSPF LSP Path Computed ERO";
                    leaf local-ip-address  {
                        type  leafref {
                            path  "../state/local-ip-address";
                        }
                        description "CSPF Path LSP Computed ERO Local IP Address";
                    } // END of local-ip-address definition.

                    container state {
                        config false;
                        description
                            "This container defines the ISIS CSPF LSP Path Computed ERO State";
                        uses isis-cspf-lsp-computed-ero-state;
                    } // END of state-container definition.
                } // End of path-computed-ero-list
                container state {
                    config false;
                    description
                        "This container defines the ISIS CSPF LSP Status State";
                    uses isis-cspf-lsp-state;
                } // END of state-container definition.
            } // End of lsp-status-list
            container state {
                config false;
                description
                    "This container defines the ISIS LSP Priority Lists";
                uses isis-cspf-setup-priority-state;
            } // END of state-container definition.
        } // End of lsp-list
    } // END of cspf-container definition.
    } // END of cspf-grouping definition.


}
