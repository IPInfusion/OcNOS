/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-isis-fad.yang
*
*/

submodule ipi-isis-fad {

    yang-version 1.1;

    belongs-to  ipi-isis { prefix ipi-isis; }

    import feature-list {
        prefix feature-list;
        revision-date 2026-09-15;
    }

    import ipi-isis-types {
        prefix ipi-isis-types;
        revision-date 2025-12-05;
    }

    organization
        "IP Infusion Inc.";

    contact
        "Address: 3965 Freedom Circle, Suite 200, Santa Clara, CA 95054
         Phone: +1 408-400-1900
         E-mail: support@ipinfusion.com
         Web: http://www.ipinfusion.com/";

    description
        "Model for managing IS-IS FAD";


    revision "2025-09-17" {
        description "Corrected SRLG Minimum Value";
        reference " 0.2.1.";
    }

    revision "2025-09-06" {
        description "Added Flexible Algorithm SRLG-disjoint TI-LFA";
        reference " 0.2.0.";
    }

    revision "2025-03-17" {
        description "Changed display string for flexalgo clis";
        reference " 0.1.14.";
    }

    revision "2024-12-28" {
        description "Added cli command for advertise and particpate";
        reference " 0.1.13.";
    }

    revision "2024-12-26" {
        description "Unsupported commands of Flex-Algo made hidden";
        reference " 0.1.12.";
    }

    revision "2024-12-22" {
        description "Updated revisions since included file ipi-isis-type was updated";
        reference " 0.1.11.";
    }

    revision "2024-12-08" {
        description "Replaced Flex-Algo FAPM parameter by maximum-ecmp-paths parameter";
        reference " 0.1.10.";
    }

    revision "2024-09-03" {
        description "Corrected Default valus and Initialize attributes for Flex-Algo parameters";
        reference " 0.1.9.";
    }

    revision "2024-08-10" {
        description "Corrected validate API names of Bandwidth-Threshold and Microloop containers";
        reference " 0.1.7.";
    }

    revision "2024-07-05" {
        description "Corrected Bandwidth-Threshold and Microloop containers";
        reference " 0.1.6.";
    }

    revision "2024-05-07" {
        description "Added Microloop avoidance container objects";
        reference " 0.1.5.";
    }

    revision "2024-03-26" {
        description "Added bandwidth threshold/metric container objects";
        reference " 0.1.4.";
    }

    revision "2024-03-06" {
        description "Added reverse Extended Admin Group (EAG) objects";
        reference " 0.1.3.";
    }

    revision "2024-01-23" {
        description "Updated IGP Flexible Algorithm data-models";
        reference " 0.1.2.";
    }

    revision "2024-01-22" {
        description "Updated IGP Flexible Algorithm for ISIS Segment Routing";
        reference " 0.1.1.";
    }

    revision "2023-09-29" {
        description "Initial release of IGP Flexible Algorithm for ISIS Segment Routing";
        reference " 0.1.0.";
    }

    grouping isis-flexalgo-cfg-grp {
        description
            "Configuration items for ISIS Flexible Algorithm Mode";
        leaf algo-number  {
            type  uint8 {
                 range "128..255"  {
                    description "128..255: Supported range 128 - 255";
                 }
            }
            description "Use this attribute to configure Flexible Algorithm specific
                        configuration";
        } // END of algo-number definition.

        leaf metric-type  {
            type  ipi-isis-types:isis_fad_metric_type_t;
            default "igp-metric";
            description "ISIS Flexible Algorithm metric type";
        } // END of metric-type definition.

        leaf calculation-type  {
            type  ipi-isis-types:isis_fad_calculation_type_t;
            default "spf";
            description "ISIS Flexible Algorithm calculation type";
        } // END of calculation-type definition.

        leaf priority  {
            type  uint8 {
                 range "1..255"  {
                    description "1..255: Supported range 1 - 255";
                 }
            }
            default "5";
            description "Flexible Algorithm priority Value";
        } // END of priority definition.

        leaf exclude-minimum-bandwidth  {
            type  string {
                length "1..1965";
                pattern "(([1-9]{1}[0-9]{0,2}[m|M|k|K]{1})|([1-9]{1}.[0-9]{1}[g|G|m|M|k|K]{1})|([1-9]{1}[0-9]{0,1}[g|G]{1})|(100[g|G]{1}))+";
            }
            description "Minimum bandwidth value constraint for flexible algorithm. The
                        bandwidth input ranges are 1 to 999 Kbps, 1 to 999 Mbps and 1 to 100
                        Gbps.";
        } // END of exclude-minimum-bandwidth definition.

        leaf exclude-maximum-delay  {
            type  uint32 {
                 range "1..16777215"  {
                    description "1..16777215: Supported range 1 - 16777215";
                 }
            }
            units "microseconds";
            description "Use this attribute to specify maximum link delay value constraint for
                        flexible algorithm";
        } // END of exclude-maximum-delay definition.

        leaf enable-intf-group-mode-bw-calc  {
            type  empty;
            description "Enable interface group mode total bandwidth calculation for ISIS
                        Flexible algorithm";
        } // END of enable-intf-group-mode-bw-calc definition.

        leaf reference-bandwidth  {
            type  string {
                length "1..1965";
                pattern "(([1-9]{1}[0-9]{0,2}[m|M|k|K]{1})|([1-9]{1}.[0-9]{1}[g|G|m|M|k|K]{1})|([1-9]{1}[0-9]{0,1}[g|G]{1})|(100[g|G]{1}))+";
            }
            description "Reference bandwidth value constraint for flexible algorithm SPF's
                        automatic metric calculation. The bandwidth input ranges are 1 to 999
                        Kbps, 1 to 999 Mbps and 1 to 100 Gbps.";
        } // END of reference-bandwidth definition.

        leaf granularity-bandwidth  {
            type  string {
                length "1..1965";
                pattern "(([1-9]{1}[0-9]{0,2}[m|M|k|K]{1})|([1-9]{1}.[0-9]{1}[g|G|m|M|k|K]{1})|([1-9]{1}[0-9]{0,1}[g|G]{1})|(100[g|G]{1}))+";
            }
            description "Granularity bandwidth value constraint for flexible algorithm SPF's
                        automatic metric calculation. The bandwidth input ranges are 1 to 999
                        Kbps, 1 to 999 Mbps and 1 to 100 Gbps.";
        } // END of granularity-bandwidth definition.

        leaf disable-advertise-definition  {
            type  empty;
            description "Use this attribute to unconfigure the ISIS Flexible Algorithm
                        Advertisement";
        } // END of disable-advertise-definition definition.

        leaf disable-participate  {
            type  empty;
            description "Use this attribute to unconfigure the ISIS Flexible Algorithm
                        Participation";
        } // END of disable-participate definition.

        leaf enable-fast-reroute  {
            type  empty;
            description "Use this attribute to configure the ISIS Flexible Algorithm fast
                        rerouting";
        } // END of enable-fast-reroute definition.

        leaf enable-remote-lfa  {
            type  empty;
            description "Use this attribute to configure the ISIS Flexible Algorithm Remote-LFA";
        } // END of enable-remote-lfa definition.

        leaf enable-ti-lfa  {
            type  empty;
            description "Use this attribute to configure the ISIS Flexible Algorithm TI-LFA";
        } // END of enable-ti-lfa definition.

        leaf enable-backup-srlg-disjoint-path  {
            type  empty;
            description "Use this attribute to configure the ISIS Flexible Algorithm
                        SRLG-disjoint backup path";
        } // END of enable-backup-srlg-disjoint-path definition.

        leaf enable-backup-srlg-disjoint-forced  {
            type  empty;
            description "Use this attribute to configure the ISIS Flexible Algorithm forced
                        SRLG-disjoint backup path";
        } // END of enable-backup-srlg-disjoint-forced definition.

        leaf enable-prefix-metric-flag  {
            type  empty;
            description "Use this attribute to configure the ISIS Flexible Algorithm
                        prefix-metric flag sub-TLV advertisement";
        } // END of enable-prefix-metric-flag definition.

        leaf fapm-metric  {
            type  uint8 {
                 range "1..255"  {
                    description "1..255: Supported range 1 - 255";
                 }
            }
            default "24";
            description "Distance Value";
        } // END of fapm-metric definition.

        leaf maximum-ecmp-paths  {
            type  uint8 {
                 range "8..64"  {
                    description "8..64: Supported range 8 - 64";
                 }
            }
            default "8";
            description "Distance Value";
        } // END of maximum-ecmp-paths definition.

        leaf-list affinity-eag-exclude-any  {
            type  string {
                length "1..16";
                pattern "[^?' =,>|]+";
            }
            description "Flexible Algoithm Exclude Any Affinity-EAG Name";
        } // END of affinity-eag-exclude-any definition.

        leaf-list affinity-eag-include-any  {
            type  string {
                length "1..16";
                pattern "[^?' =,>|]+";
            }
            description "Flexible Algoithm Include Any Affinity-EAG Name";
        } // END of affinity-eag-include-any definition.

        leaf-list affinity-eag-include-all  {
            type  string {
                length "1..16";
                pattern "[^?' =,>|]+";
            }
            description "Flexible Algoithm Include All Affinity-EAG Name";
        } // END of affinity-eag-include-all definition.

        leaf-list affinity-eag-reverse-exclude-any  {
            type  string {
                length "1..16";
                pattern "[^?' =,>|]+";
            }
            description "Flexible Algoithm reverse Exclude Any Affinity-EAG Name";
        } // END of affinity-eag-reverse-exclude-any definition.

        leaf-list affinity-eag-reverse-include-any  {
            type  string {
                length "1..16";
                pattern "[^?' =,>|]+";
            }
            description "Flexible Algoithm reverse Include Any Affinity-EAG Name";
        } // END of affinity-eag-reverse-include-any definition.

        leaf-list affinity-eag-reverse-include-all  {
            type  string {
                length "1..16";
                pattern "[^?' =,>|]+";
            }
            description "Flexible Algoithm reverse Include All Affinity-EAG Name";
        } // END of affinity-eag-reverse-include-all definition.

        leaf-list affinity-ag-exclude-any  {
            type  string {
                length "1..16";
                pattern "[^?' =,>|]+";
            }
            description "Flexible Algoithm Exclude Any Affinity-AG Name";
        } // END of affinity-ag-exclude-any definition.

        leaf-list affinity-ag-include-any  {
            type  string {
                length "1..16";
                pattern "[^?' =,>|]+";
            }
            description "Flexible Algoithm Include Any Affinity-AG Name";
        } // END of affinity-ag-include-any definition.

        leaf-list affinity-ag-include-all  {
            type  string {
                length "1..16";
                pattern "[^?' =,>|]+";
            }
            description "Flexible Algoithm Include All Affinity-AG Name";
        } // END of affinity-ag-include-all definition.

        leaf-list affinity-ag-reverse-exclude-any  {
            type  string {
                length "1..16";
                pattern "[^?' =,>|]+";
            }
            description "Flexible Algoithm reverse Exclude Any Affinity-AG Name";
        } // END of affinity-ag-reverse-exclude-any definition.

        leaf-list affinity-ag-reverse-include-any  {
            type  string {
                length "1..16";
                pattern "[^?' =,>|]+";
            }
            description "Flexible Algoithm reverse Include Any Affinity-AG Name";
        } // END of affinity-ag-reverse-include-any definition.

        leaf-list affinity-ag-reverse-include-all  {
            type  string {
                length "1..16";
                pattern "[^?' =,>|]+";
            }
            description "Flexible Algoithm reverse Include All Affinity-AG Name";
        } // END of affinity-ag-reverse-include-all definition.

        leaf-list exclude-srlg  {
            if-feature feature-list:HAVE_SRLG;
            type  uint32 {
                 range "1..4294967295"  {
                    description "1..4294967295: Supported range 1 - 4294967295";
                 }
            }
            description "Flexible Algoithm Exclude Shared Risk Link Groups";
        } // END of exclude-srlg definition.

    } // END of isis-flexalgo-cfg-grp definition.
    grouping isis-flexalgo-bandwidth-threshold-metric-config {
        description
            "Bandwidth threshold metric Configurations";
        leaf bandwidth-threshold  {
            type  string {
                length "1..1965";
                pattern "(([1-9]{1}[0-9]{0,2}[m|M|k|K]{1})|([1-9]{1}.[0-9]{1}[g|G|m|M|k|K]{1})|([1-9]{1}[0-9]{0,1}[g|G]{1})|(100[g|G]{1}))+";
            }
            description "Staircase bandwidth threshold value constraint for flexible algorithm.
                        The bandwidth input ranges are 1 to 999 Kbps, 1 to 999 Mbps and 1 to
                        100 Gbps.";
        } // END of bandwidth-threshold definition.

        leaf threshold-metric  {
            type  uint32 {
                 range "1..4261412"  {
                    description "1..4261412: Supported range 1 - 4261412";
                 }
            }
            description "Link metric value for the bandwidth threshold";
        } // END of threshold-metric definition.

    } // END of isis-flexalgo-bandwidth-threshold-metric-config definition.
    grouping isis-flexalgo-bandwidth-threshold-metric-top {
        description
            "Bandwidth threshold metric configurations";
        container flexalgo-bandwidth-thresholds {
            description
                "YANG data model for Flexible-Algorithm bandwidth threshold
                        configuration and operation.";

            list flexalgo-bandwidth-threshold {
                key "bandwidth-threshold";
                description
                    "Bandwidth threshold metric configurations";
                leaf bandwidth-threshold  {
                    type  leafref {
                        path  "../config/bandwidth-threshold";
                    }
                    description "Staircase bandwidth threshold value constraint for flexible algorithm.
                                The bandwidth input ranges are 1 to 999 Kbps, 1 to 999 Mbps and 1 to
                                100 Gbps.";
                } // END of bandwidth-threshold definition.

                container config {
                    description
                        "Config container for flexible algorithm staircase bandwidth threshold";
                    uses isis-flexalgo-bandwidth-threshold-metric-config;
                } // END of config-container definition.
                container state {
                    config false;
                    description
                        "State Contatiner for flexible algorithm staircase bandwidth threshold";
                    uses isis-flexalgo-bandwidth-threshold-metric-config;
                } // END of state-container definition.
            } // End of flexalgo-bandwidth-threshold-list
        } // END of flexalgo-bandwidth-thresholds-container definition.
    } // END of isis-flexalgo-bandwidth-threshold-metric-top definition.
    grouping isis-flexalgo-microloop-avoidance-params-config {
        description
            "configuration items for microloop-avoidance";
        leaf level-type  {
            type  ipi-isis-types:isis_level2_t;
            description "IS-IS instance level,(1|2)";
        } // END of level-type definition.

        leaf enable  {
            type  empty;
            description "Microloop avoidance";
        } // END of enable definition.

    } // END of isis-flexalgo-microloop-avoidance-params-config definition.
    grouping isis-flexalgo-microloop-avoidance-top {
        description
            "Grouping for ISIS Microloop Avoidance";
        container flexalgo-microloop-avoidances {
            if-feature feature-list:HAVE_ISIS_LFA_OR_HAVE_ISIS_TI_LFA;
            description
                "This container defines the ISIS Microloop Avoidance";

            list flexalgo-microloop-avoidance {
            // when " ipi-isis:isis/isis-instances/isis-instance/flexalgos/flexalgo/flexalgo-microloop-avoidances/flexalgo-microloop-avoidance/config/enable ";
                key "level-type";
                description
                    "This objectlist defines the ISIS Microloop Avoidance";
                leaf level-type  {
                    type  leafref {
                        path  "../config/level-type";
                    }
                    description "IS-IS instance level,(1|2)";
                } // END of level-type definition.

                container config {
                    description
                        "This container defines the ISIS Microloop Avoidance configurations";
                    uses isis-flexalgo-microloop-avoidance-params-config;
                } // END of config-container definition.
                container state {
                    config false;
                    description
                        "This container defines the ISIS Microloop Avoidance State";
                    uses isis-flexalgo-microloop-avoidance-params-config;
                } // END of state-container definition.
            } // End of flexalgo-microloop-avoidance-list
        } // END of flexalgo-microloop-avoidances-container definition.
    } // END of isis-flexalgo-microloop-avoidance-top definition.
    grouping isis-flexalgo-top-grp {
        description
            "ISIS Flexible Algorithm Top Level group";
        container flexalgos {
            description
                "This container defines the ISIS Flexible Algorithm parameters";

            list flexalgo {
                key "algo-number";
                description
                    "This objectlist defines the ISIS FAD Metric Type Configurations and
                                state information";
                leaf algo-number  {
                    type  leafref {
                        path  "../config/algo-number";
                    }
                    description "Use this attribute to configure Flexible Algorithm specific
                                configuration";
                } // END of algo-number definition.

                container config {
                    presence "yes";
                    description
                        "config parameters for ISIS Flexible Algorithm configurations";
                    uses isis-flexalgo-cfg-grp;
                } // END of config-container definition.
                container state {
                    config false;
                    description
                        "This container defines the ISIS Flexible Algorithm operational
                                information";
                    uses isis-flexalgo-cfg-grp;
                } // END of state-container definition.
                uses isis-flexalgo-bandwidth-threshold-metric-top;
                uses isis-flexalgo-microloop-avoidance-top;
            } // End of flexalgo-list
        } // END of flexalgos-container definition.
    } // END of isis-flexalgo-top-grp definition.
    grouping isis-extended-admin-group-show {
        description
            "ISIS Extended Administrative Group (EAG) Display";
        leaf name  {
            type  string {
                length "1..1965";
                pattern "[^?' =,>|]+";
            }
            description "Use this attribute for name-to-value binding for an extended
                        administrative group";
        } // END of name definition.

        leaf id  {
            type  uint16 {
                 range "32..1055"  {
                    description "32..1055: Supported range 32 - 1055";
                 }
            }
            description "identifier value for the extended administrative group";
        } // END of id definition.

    } // END of isis-extended-admin-group-show definition.
    grouping isis-extended-admin-group-top {
        description
            "ISIS Flexible Algorithm Top Level group";
        container extended-admin-groups {
            config false;
            description
                "Container for ISIS Extended Administrative Groups (EAG) Table";

            list extended-admin-group {
                key "name id";
                config false;
                description
                    "ISIS Extended Administrative Group (EAG) entry";
                leaf name  {
                    type  leafref {
                        path  "../state/name";
                    }
                    description "Use this attribute for name-to-value binding for an extended
                                administrative group";
                } // END of name definition.

                leaf id  {
                    type  leafref {
                        path  "../state/id";
                    }
                    description "identifier value for the extended administrative group";
                } // END of id definition.

                container state {
                    config false;
                    description
                        "State Contatiner for ISIS Extended Administrative Groups (EAG)";
                    uses isis-extended-admin-group-show;
                } // END of state-container definition.
            } // End of extended-admin-group-list
        } // END of extended-admin-groups-container definition.
    } // END of isis-extended-admin-group-top definition.


}
