/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-isis-lsp.yang
*
*/

submodule ipi-isis-lsp {

    yang-version 1.1;

    belongs-to  ipi-isis { prefix ipi-isis; }

    import feature-list {
        prefix feature-list;
        revision-date 2026-09-15;
    }

    import cml-data-types {
        prefix cml-data-types;
        revision-date 2026-05-15;
    }

    import ipi-isis-types {
        prefix ipi-isis-types;
        revision-date 2025-12-05;
    }

    import ietf-inet-types {
        prefix inet;
        revision-date 2013-07-15;
    }

    include ipi-isis-lsp-flxalg { revision-date 2024-04-22;}
    organization
        "IP Infusion Inc.";

    contact
        "Address: 3965 Freedom Circle, Suite 200, Santa Clara, CA 95054
         Phone: +1 408-400-1900
         E-mail: support@ipinfusion.com
         Web: http://www.ipinfusion.com/";

    description
        "Model for managing IS-IS LSP";


    revision "2025-10-24" {
        description "Updated attr name from protocol-distance to protocol-metric";
        reference " 0.11.1.";
    }

    revision "2025-08-11" {
        description "Updated the range for metric";
        reference " 0.11.0.";
    }

    revision "2024-12-22" {
        description "Updated revisions since included file ipi-isis-type was updated";
        reference " 0.10.6.";
    }

    revision "2024-10-22" {
        description "Added support for streaming telemetry";
        reference " 0.10.5.";
    }

    revision "2024-04-22" {
        description "Commented out all Flex-Algo state container group uses for now";
        reference " 0.10.3.";
    }

    revision "2024-04-17" {
        description "Added Get API header file name for generation";
        reference " 0.10.2.";
    }

    revision "2024-02-13" {
        description "MT IPv6 reachability tlv";
        reference " 0.10.4.";
    }

    revision "2024-02-09" {
        description "Updated MT IS Reachability with SRV6 attributes";
        reference " 0.10.1.";
    }

    revision "2023-09-29" {
        description "Flexible Algorithm related Get API in ISIS LSP";
        reference " 0.10.0.";
    }

    revision "2023-08-10" {
        description "JIRA-61800:Added remaining enclosing containers";
        reference " 0.9.3.";
    }

    revision "2023-08-04" {
        description "Added cliprependstr for authentication";
        reference " 0.9.2.";
    }

    revision "2023-06-29" {
        description "JIRA-61800:Added enclosing containers";
        reference " 0.9.1.";
    }

    revision "2023-06-16" {
        description "ISIS-LSP-MAX-WAIT-DEFAULT-VALUE-CHANGE";
        reference " 0.9.0.";
    }

    revision "2022-11-25" {
        description "ISIS-LSP-MTU-RANGE-CHANGE-FIX";
        reference " 0.8.0.";
    }

    revision "2022-06-01" {
        description "Updated the yang file with feature";
        reference " 0.7.0.";
    }

    revision "2022-04-20" {
        description "SID Label Binding TLV attribute changed as per RFC 8667";
        reference " 0.6.0.";
    }

    revision "2022-02-14" {
        description "SRv6 GET API related Changes in ISIS LSP";
        reference " 0.5.0.";
    }

    revision "2021-09-03" {
        description "Update descriptions of attribute";
        reference " 0.4.0.";
    }

    revision "2021-08-16" {
        description "ISIS-TE Metric Extension's GET API support";
        reference " 0.3.0.";
    }

    revision "2020-12-15" {
        description "Change to have data-types in lower case instead of camel case";
        reference " 0.2.0.";
    }

    revision "2020-05-06" {
        description "Datamodel restructuring";
        reference " 0.1.0.";
    }



    grouping level-runtime-grouping {
    description
        "Run time Level information";
        list level-runtime {
            if-feature feature-list:HAVE_ISISD;
            key "type";
            config false;
            description
                "Run time Level information";
            leaf type  {
                type  leafref {
                    path  "../state/type";
                }
                description "IS-IS instance level,(1|2)";
            } // END of type definition.


            list lspdb {
                key "lsp-identifier";
                config false;
                description
                    "This objectlist defines the ISIS Level LSP DB List";
                leaf lsp-identifier  {
                    type  leafref {
                        path  "../state/lsp-identifier";
                    }
                    description "LSP ID";
                } // END of lsp-identifier definition.


                list tlvs {
                    key "index";
                    config false;
                    description
                        "This objectlist defines the ISIS Level LSP DB TLVs";
                    leaf index  {
                        type  leafref {
                            path  "../state/index";
                        }
                        description "Index";
                    } // END of index definition.


                    list is-neighbors {
                        key "system-id";
                        config false;
                        description
                            "This objectlist defines the ISIS Level LSP DB TLV IS Neighbor List";
                        leaf system-id  {
                            type  leafref {
                                path  "../state/system-id";
                            }
                            description "System ID";
                        } // END of system-id definition.

                        container state {
                            config false;
                            description
                                "This container defines the ISIS Level LSP DB TLV IS Neighbor List
                                        State";
                            uses isis-level-lspdb-tlv-is-neighbor-state;
                        } // END of state-container definition.
                    } // End of is-neighbors-list

                    list es-neighbors {
                        key "system-id";
                        config false;
                        description
                            "This objectlist defines the ISIS Level LSP DB TLV ES Neighbor List";
                        leaf system-id  {
                            type  leafref {
                                path  "../state/system-id";
                            }
                            description "System ID";
                        } // END of system-id definition.

                        container state {
                            config false;
                            description
                                "This container defines the ISIS Level LSP DB TLV ES Neighbor List
                                        State";
                            uses isis-level-lspdb-tlv-es-neighbor-state;
                        } // END of state-container definition.
                    } // End of es-neighbors-list

                    list ip-internal-reachability-information {
                        key "prefix";
                        config false;
                        description
                            "This objectlist defines the ISIS Level LSP DB TLV Ip Internal
                                        reachability TLV";
                        leaf prefix  {
                            type  leafref {
                                path  "../state/prefix";
                            }
                            description "Prefix";
                        } // END of prefix definition.

                        container state {
                            config false;
                            description
                                "This objectlist defines the ISIS Level LSP DB TLV Ip Internal
                                        reachability TLV State";
                            uses isis-level-lspdb-tlv-ip-internal-reach-state;
                        } // END of state-container definition.
                    } // End of ip-internal-reachability-information-list

                    list ip-external-reachability-information {
                        key "prefix";
                        config false;
                        description
                            "This objectlist defines the ISIS Level LSP DB TLV Ip External
                                        reachability TLV";
                        leaf prefix  {
                            type  leafref {
                                path  "../state/prefix";
                            }
                            description "Prefix";
                        } // END of prefix definition.

                        container state {
                            config false;
                            description
                                "This container defines the ISIS Level LSP DB TLV Ip External
                                        reachability TLV State";
                            uses isis-level-lspdb-tlv-ip-external-reach-state;
                        } // END of state-container definition.
                    } // End of ip-external-reachability-information-list

                    list extended-is-reachability {
                        if-feature feature-list:HAVE_WIDE_METRIC;
                        key "extended-is-index";
                        config false;
                        description
                            "This objectlist defines the ISIS Level LSP DB Extended IS reachability
                                        TLV";
                        leaf extended-is-index  {
                            type  leafref {
                                path  "../state/extended-is-index";
                            }
                            description "Index";
                        } // END of extended-is-index definition.


                        list subtlv {
                            key "subtlv-index";
                            config false;
                            description
                                "This objectlist defines the ISIS Level LSP DB Stlv List";
                            leaf subtlv-index  {
                                type  leafref {
                                    path  "../state/subtlv-index";
                                }
                                description "Index";
                            } // END of subtlv-index definition.

                            container state {
                                config false;
                                description
                                    "This container defines the ISIS Level LSP DB Stlv List";
                                uses isis-level-lspdb-stlv-state;
                            } // END of state-container definition.
                            container protocols-supported {
                                if-feature feature-list:HAVE_PROTOCOL_TOPOLOGY;
                                config false;
                                description
                                    "This container defines the ISIS Level LSP DB Protocols supported STLV";
                                container state {
                                    config false;
                                    description
                                        "This container defines the ISIS Level LSP DB Protocols supported STLV
                                                State";
                                    uses isis-level-lspdb-supported-proto-state;
                                } // END of state-container definition.
                            } // END of protocols-supported-container definition.
                            container admin-group-info {
                                if-feature feature-list:HAVE_ISIS_TE;
                                config false;
                                description
                                    "This container defines the ISIS Level LSP DB Admin Group STLV";
                                container state {
                                    config false;
                                    description
                                        "This container defines the ISIS Level LSP DB Admin Group STLV State";
                                    uses isis-level-lspdb-admin-group-stlv-state;
                                    uses isis-level-lspdb-mismatch-state;
                                } // END of state-container definition.
                            } // END of admin-group-info-container definition.
                            container ipv4-interface-address {
                                if-feature feature-list:HAVE_ISIS_TE;
                                config false;
                                description
                                    "This container defines the ISIS Level LSP DB TLV Interface IPv4
                                            address";
                                container state {
                                    config false;
                                    description
                                        "This container defines the ISIS Level LSP DB TLV Interface IPv4
                                                address State";
                                    uses isis-level-lspdb-local-ipv4-addr-state;
                                    uses isis-level-lspdb-mismatch-state;
                                } // END of state-container definition.
                            } // END of ipv4-interface-address-container definition.
                            container ipv4-neighbor-address {
                                if-feature feature-list:HAVE_ISIS_TE;
                                config false;
                                description
                                    "This container defines the ISIS Level LSP DB TLV Neighbor IPv4 address";
                                container state {
                                    config false;
                                    description
                                        "This container defines the ISIS Level LSP DB TLV Neighbor IPv4 address
                                                State";
                                    uses isis-level-lspdb-neighbor-ipv4-addr-state;
                                    uses isis-level-lspdb-mismatch-state;
                                } // END of state-container definition.
                            } // END of ipv4-neighbor-address-container definition.
                            container ipv6-interface-address {
                                if-feature feature-list:HAVE_ISIS_TE;
                                if-feature feature-list:HAVE_IPV6;
                                config false;
                                description
                                    "This container defines the ISIS Level LSP DB TLV Interface IPv6
                                            address";
                                container state {
                                    config false;
                                    description
                                        "This container defines the ISIS Level LSP DB TLV Interface IPv6
                                                address State";
                                    uses isis-level-lspdb-local-ipv6-addr-state;
                                    uses isis-level-lspdb-mismatch-state;
                                } // END of state-container definition.
                            } // END of ipv6-interface-address-container definition.
                            container ipv6-neighbor-address {
                                if-feature feature-list:HAVE_ISIS_TE;
                                if-feature feature-list:HAVE_IPV6;
                                config false;
                                description
                                    "This container defines the ISIS Level LSP DB TLV Neighbor IPv6 address";
                                container state {
                                    config false;
                                    description
                                        "This container defines the ISIS Level LSP DB TLV Neighbor IPv6 address
                                                State";
                                    uses isis-level-lspdb-neighbor-ipv6-addr-state;
                                    uses isis-level-lspdb-mismatch-state;
                                } // END of state-container definition.
                            } // END of ipv6-neighbor-address-container definition.
                            container max-link-bandwidth {
                                if-feature feature-list:HAVE_ISIS_TE;
                                config false;
                                description
                                    "This container defines the ISIS Level LSP DB Stlv Max-Link Bandwidth";
                                container state {
                                    config false;
                                    description
                                        "This container defines the ISIS Level LSP DB Stlv Max-Link Bandwidth
                                                State";
                                    uses isis-level-lspdb-max-link-bw-state;
                                    uses isis-level-lspdb-mismatch-state;
                                } // END of state-container definition.
                            } // END of max-link-bandwidth-container definition.
                            container max-reserve-link-bandwidth {
                                if-feature feature-list:HAVE_ISIS_TE;
                                config false;
                                description
                                    "This container defines the ISIS Level LSP DB Stlv Max-Link Bandwidth";
                                container state {
                                    config false;
                                    description
                                        "This container defines the ISIS Level LSP DB Stlv Max-Link Bandwidth
                                                State";
                                    uses isis-level-lspdb-max-reserve-bw-state;
                                    uses isis-level-lspdb-mismatch-state;
                                } // END of state-container definition.
                            } // END of max-reserve-link-bandwidth-container definition.
                            container unreserved-bandwidth {
                                if-feature feature-list:HAVE_ISIS_TE;
                                config false;
                                description
                                    "This container defines the ISIS Level LSP DB Stlv LSPDB Unreserve
                                            Bandwidth";
                                container state {
                                    config false;
                                    description
                                        "This container defines the ISIS Level LSP DB Stlv LSPDB Unreserve
                                                Bandwidth State";
                                    uses isis-level-lspdb-unreserve-bw-state;
                                    uses isis-level-lspdb-mismatch-state;
                                } // END of state-container definition.
                            } // END of unreserved-bandwidth-container definition.
                            container te-default-metric {
                                if-feature feature-list:HAVE_ISIS_TE;
                                config false;
                                description
                                    "This container defines the ISIS Level LSP DB Stlv TE Default Metric";
                                container state {
                                    config false;
                                    description
                                        "This container defines the ISIS Level LSP DB Stlv TE Default Metric
                                                State";
                                    uses isis-level-lspdb-te-default-metric-state;
                                    uses isis-level-lspdb-mismatch-state;
                                } // END of state-container definition.
                            } // END of te-default-metric-container definition.
                            container uni-link-delay {
                                if-feature feature-list:HAVE_ISIS_TE;
                                config false;
                                description
                                    "This container defines the ISIS Level LSP DB Stlv Unidirectional Link
                                            Delay";
                                container state {
                                    config false;
                                    description
                                        "This container defines the ISIS Level LSP DB Stlv Unidirectional Link
                                                Delay";
                                    uses isis-level-lspdb-uni-link-delay-state;
                                    uses isis-level-lspdb-mismatch-state;
                                } // END of state-container definition.
                            } // END of uni-link-delay-container definition.
                            container min-max-uni-link-delay {
                                if-feature feature-list:HAVE_ISIS_TE;
                                config false;
                                description
                                    "This container defines the ISIS Level LSP DB Stlv Min/Max
                                            Unidirectional Link Delay";
                                container state {
                                    config false;
                                    description
                                        "This container defines the ISIS Level LSP DB Stlv Min/Max
                                                Unidirectional Link Delay";
                                    uses isis-level-lspdb-min-max-uni-link-delay-state;
                                    uses isis-level-lspdb-mismatch-state;
                                } // END of state-container definition.
                            } // END of min-max-uni-link-delay-container definition.
                            container uni-delay-variation {
                                if-feature feature-list:HAVE_ISIS_TE;
                                config false;
                                description
                                    "This container defines the ISIS Level LSP DB Stlv Unidirectional Delay
                                            variation";
                                container state {
                                    config false;
                                    description
                                        "This container defines the ISIS Level LSP DB Stlv Unidirectional Delay
                                                Variotaion";
                                    uses isis-level-lspdb-uni-delay-variation-state;
                                    uses isis-level-lspdb-mismatch-state;
                                } // END of state-container definition.
                            } // END of uni-delay-variation-container definition.
                            container uni-link-loss {
                                if-feature feature-list:HAVE_ISIS_TE;
                                config false;
                                description
                                    "This container defines the ISIS Level LSP DB Stlv Unidirectional Link
                                            Loss";
                                container state {
                                    config false;
                                    description
                                        "This container defines the ISIS Level LSP DB Stlv Unidirectional Link
                                                Loss";
                                    uses isis-level-lspdb-uni-link-loss-state;
                                    uses isis-level-lspdb-mismatch-state;
                                } // END of state-container definition.
                            } // END of uni-link-loss-container definition.
                            container uni-residual-bw {
                                if-feature feature-list:HAVE_ISIS_TE;
                                config false;
                                description
                                    "This container defines the ISIS Level LSP DB Stlv Unidirectional
                                            Residual Bandwidth";
                                container state {
                                    config false;
                                    description
                                        "This container defines the ISIS Level LSP DB Stlv Unidirectional
                                                Residual Bandwidth";
                                    uses isis-level-lspdb-uni-residual-bw-state;
                                    uses isis-level-lspdb-mismatch-state;
                                } // END of state-container definition.
                            } // END of uni-residual-bw-container definition.
                            container uni-available-bw {
                                if-feature feature-list:HAVE_ISIS_TE;
                                config false;
                                description
                                    "This container defines the ISIS Level LSP DB Stlv Unidirectional
                                            Available Bandwidth";
                                container state {
                                    config false;
                                    description
                                        "This container defines the ISIS Level LSP DB Stlv Unidirectional
                                                Available Bandwidth";
                                    uses isis-level-lspdb-uni-available-bw-state;
                                    uses isis-level-lspdb-mismatch-state;
                                } // END of state-container definition.
                            } // END of uni-available-bw-container definition.
                            container uni-utilized-bw {
                                if-feature feature-list:HAVE_ISIS_TE;
                                config false;
                                description
                                    "This container defines the ISIS Level LSP DB Stlv Unidirectional
                                            Utilized Bandwidth";
                                container state {
                                    config false;
                                    description
                                        "This container defines the ISIS Level LSP DB Stlv Unidirectional Link
                                                Loss";
                                    uses isis-level-lspdb-uni-utilized-bw-state;
                                    uses isis-level-lspdb-mismatch-state;
                                } // END of state-container definition.
                            } // END of uni-utilized-bw-container definition.
                            container sr-te-adjacency-sid {
                                if-feature feature-list:HAVE_ISIS_TE;
                                if-feature feature-list:HAVE_ISIS_SR;
                                config false;
                                description
                                    "This container defines the ISIS Level LSP DB Stlv ISIS-SR TE Adj SID";
                                container state {
                                    config false;
                                    description
                                        "This container defines the ISIS Level LSP DB Stlv ISIS-SR TE Adj SID
                                                State";
                                    uses isis-level-lspdb-sr-te-adj-sid-state;
                                    uses isis-level-lspdb-mismatch-state;
                                } // END of state-container definition.
                            } // END of sr-te-adjacency-sid-container definition.
                            container sr-te-lan-adjacency-sid {
                                if-feature feature-list:HAVE_ISIS_TE;
                                if-feature feature-list:HAVE_ISIS_SR;
                                config false;
                                description
                                    "This container defines the ISIS Level LSP DB Stlv ISIS-SR TE Adj SID";
                                container state {
                                    config false;
                                    description
                                        "This container defines the ISIS Level LSP DB Stlv ISIS-SR TE Adj SID
                                                State";
                                    uses isis-level-lspdb-sr-te-lan-adj-sid-state;
                                    uses isis-level-lspdb-mismatch-state;
                                } // END of state-container definition.
                            } // END of sr-te-lan-adjacency-sid-container definition.
                            container link-ids {
                                if-feature feature-list:HAVE_GMPLS;
                                config false;
                                description
                                    "This container defines the ISIS Level LSP DB Stlv GMPLS link id";
                                container state {
                                    config false;
                                    description
                                        "This container defines the ISIS Level LSP DB Stlv GMPLS link id State";
                                    uses isis-level-lspdb-link-id-state;
                                    uses isis-level-lspdb-mismatch-state;
                                } // END of state-container definition.
                            } // END of link-ids-container definition.
                            container link-protection-type {
                                if-feature feature-list:HAVE_GMPLS;
                                config false;
                                description
                                    "This container defines the ISIS Level LSP DB Stlv GMPLS link
                                            protection Type";
                                container state {
                                    config false;
                                    description
                                        "This container defines the ISIS Level LSP DB Stlv GMPLS link
                                                protection Type State";
                                    uses isis-level-lspdb-link-protection-type-state;
                                    uses isis-level-lspdb-mismatch-state;
                                } // END of state-container definition.
                            } // END of link-protection-type-container definition.
                            container link-switch-capability {
                                if-feature feature-list:HAVE_GMPLS;
                                config false;
                                description
                                    "This container defines the ISIS Level LSP DB Stlv GMPLS link Swithch
                                            Capability";
                                container state {
                                    config false;
                                    description
                                        "This container defines the ISIS Level LSP DB Stlv GMPLS link Swithch
                                                Capability State";
                                    uses isis-level-lspdb-link-switch-capability-state;
                                    uses isis-level-lspdb-mismatch-state;
                                } // END of state-container definition.
                            } // END of link-switch-capability-container definition.
                            container endx-sid {
                                if-feature feature-list:HAVE_SRV6;
                                config false;
                                description
                                    "This container defines the ISIS Level LSP DB Stlv EndX SID";
                                container state {
                                    config false;
                                    description
                                        "This container defines the ISIS Level LSP DB Stlv EndX SID";
                                    uses isis-level-lspdb-endx-sid-state;
                                    uses isis-level-lspdb-mismatch-state;
                                } // END of state-container definition.
                            } // END of endx-sid-container definition.
                            container lan-endx-sid {
                                if-feature feature-list:HAVE_SRV6;
                                config false;
                                description
                                    "This container defines the ISIS Level LSP DB Stlv LAN EndX SID";
                                container state {
                                    config false;
                                    description
                                        "This container defines the ISIS Level LSP DB Stlv LAN EndX SID";
                                    uses isis-level-lspdb-lan-endx-sid-state;
                                    uses isis-level-lspdb-mismatch-state;
                                } // END of state-container definition.
                            } // END of lan-endx-sid-container definition.
                        } // End of subtlv-list
                        container state {
                            config false;
                            description
                                "This container defines the ISIS Level LSP DB Extended IS reachability
                                        TLV State";
                            uses isis-level-lspdb-tlv-extend-is-reach-state;
                        } // END of state-container definition.
                    } // End of extended-is-reachability-list

                    list extended-ipv4-reachability {
                        if-feature feature-list:HAVE_WIDE_METRIC;
                        key "ipv4-reach-index";
                        config false;
                        description
                            "This objectlist defines the ISIS Level LSP DB Extended Ip reachability
                                        TLV";
                        leaf ipv4-reach-index  {
                            type  leafref {
                                path  "../state/ipv4-reach-index";
                            }
                            description "Index";
                        } // END of ipv4-reach-index definition.


                        list subtlv {
                            key "stlv-reach-index";
                            config false;
                            description
                                "This objectlist defines the ISIS Level LSP DB Stlv Reach List";
                            leaf stlv-reach-index  {
                                type  leafref {
                                    path  "../state/stlv-reach-index";
                                }
                                description "Index";
                            } // END of stlv-reach-index definition.

                            container state {
                                config false;
                                description
                                    "This container defines the ISIS Level LSP DB Stlv List Reach State";
                                uses isis-level-lspdb-stlv-reach-state;
                            } // END of state-container definition.
                            container admin-tag-info {
                                config false;
                                description
                                    "This container defines the ISIS Level LSP DB Stlv Admin tag STLV";
                                container state {
                                    config false;
                                    description
                                        "This container defines the ISIS Level LSP DB Stlv State";
                                    uses isis-level-lspdb-admin-tag-info;
                                    uses isis-level-lspdb-mismatch-state;
                                } // END of state-container definition.
                            } // END of admin-tag-info-container definition.
                            container prefix-sid {
                                if-feature feature-list:HAVE_ISIS_SR;
                                config false;
                                description
                                    "Admin tag STLV";
                                container state {
                                    config false;
                                    description
                                        "State items for ISIS Level LSPDB Prefix SID";
                                    uses isis-level-lspdb-prefix-sid-state;
                                    uses isis-level-lspdb-mismatch-state;
                                } // END of state-container definition.
                            } // END of prefix-sid-container definition.
                        } // End of subtlv-list
                        container state {
                            config false;
                            description
                                "This objectlist defines the ISIS Level LSP DB Extended Ip reachability
                                        TLV State";
                            uses isis-level-lspdb-tlv-extended-ipv4-reach-state;
                        } // END of state-container definition.
                    } // End of extended-ipv4-reachability-list

                    list ipv6-reachability {
                        if-feature feature-list:HAVE_IPV6;
                        key "ipv6-reach-index";
                        config false;
                        description
                            "This objectlist defines the ISIS Level LSP DB Ipv6 reachability TLV";
                        leaf ipv6-reach-index  {
                            type  leafref {
                                path  "../state/ipv6-reach-index";
                            }
                            description "Index Value";
                        } // END of ipv6-reach-index definition.


                        list subtlv {
                            key "stlv-reach-index";
                            config false;
                            description
                                "This objectlist defines the ISIS Level LSP DB Stlv Reach List";
                            leaf stlv-reach-index  {
                                type  leafref {
                                    path  "../state/stlv-reach-index";
                                }
                                description "Index";
                            } // END of stlv-reach-index definition.

                            container state {
                                config false;
                                description
                                    "This container defines the ISIS Level LSP DB Stlv List Reach State";
                                uses isis-level-lspdb-stlv-reach-state;
                            } // END of state-container definition.
                            container admin-tag-info {
                                config false;
                                description
                                    "This container defines the ISIS Level LSP DB Stlv Admin tag STLV";
                                container state {
                                    config false;
                                    description
                                        "This container defines the ISIS Level LSP DB Stlv State";
                                    uses isis-level-lspdb-admin-tag-info;
                                    uses isis-level-lspdb-mismatch-state;
                                } // END of state-container definition.
                            } // END of admin-tag-info-container definition.
                            container prefix-sid {
                                if-feature feature-list:HAVE_ISIS_SR;
                                config false;
                                description
                                    "Admin tag STLV";
                                container state {
                                    config false;
                                    description
                                        "State items for ISIS Level LSPDB Prefix SID";
                                    uses isis-level-lspdb-prefix-sid-state;
                                    uses isis-level-lspdb-mismatch-state;
                                } // END of state-container definition.
                            } // END of prefix-sid-container definition.
                        } // End of subtlv-list
                        container state {
                            config false;
                            description
                                "This objectlist defines the ISIS Level LSP DB Ipv6 reachability TLV
                                        State";
                            uses isis-level-lspdb-tlv-ipv6-reach-state;
                        } // END of state-container definition.
                    } // End of ipv6-reachability-list

                    list multi-topology {
                        if-feature feature-list:HAVE_MULTI_TOPOLOGY;
                        key "id";
                        config false;
                        description
                            "This objectlist defines the ISIS Level LSP DB Multitopology ID TLV";
                        leaf id  {
                            type  leafref {
                                path  "../state/id";
                            }
                            description "MT ID";
                        } // END of id definition.

                        container state {
                            config false;
                            description
                                "This objectlist defines the ISIS Level LSP DB Multitopology ID TLV
                                        State";
                            uses isis-level-lspdb-tlv-ipv4-multi-topo-state;
                        } // END of state-container definition.
                    } // End of multi-topology-list

                    list multi-topology-is-reachability {
                        if-feature feature-list:HAVE_MULTI_TOPOLOGY;
                        key "multi-is-index";
                        config false;
                        description
                            "This objectlist defines the ISIS Level LSP DB MultiTopology IS
                                        reachability TLV";
                        leaf multi-is-index  {
                            type  leafref {
                                path  "../state/multi-is-index";
                            }
                            description "Index";
                        } // END of multi-is-index definition.


                        list subtlv {
                            key "subtlv-index";
                            config false;
                            description
                                "This objectlist defines the ISIS Level LSP DB Stlv List";
                            leaf subtlv-index  {
                                type  leafref {
                                    path  "../state/subtlv-index";
                                }
                                description "Index";
                            } // END of subtlv-index definition.

                            container state {
                                config false;
                                description
                                    "This container defines the ISIS Level LSP DB Stlv List";
                                uses isis-level-lspdb-stlv-state;
                            } // END of state-container definition.
                            container protocols-supported {
                                if-feature feature-list:HAVE_PROTOCOL_TOPOLOGY;
                                config false;
                                description
                                    "This container defines the ISIS Level LSP DB Protocols supported STLV";
                                container state {
                                    config false;
                                    description
                                        "This container defines the ISIS Level LSP DB Protocols supported STLV
                                                State";
                                    uses isis-level-lspdb-supported-proto-state;
                                } // END of state-container definition.
                            } // END of protocols-supported-container definition.
                            container admin-group-info {
                                if-feature feature-list:HAVE_ISIS_TE;
                                config false;
                                description
                                    "This container defines the ISIS Level LSP DB Admin Group STLV";
                                container state {
                                    config false;
                                    description
                                        "This container defines the ISIS Level LSP DB Admin Group STLV State";
                                    uses isis-level-lspdb-admin-group-stlv-state;
                                    uses isis-level-lspdb-mismatch-state;
                                } // END of state-container definition.
                            } // END of admin-group-info-container definition.
                            container ipv4-interface-address {
                                if-feature feature-list:HAVE_ISIS_TE;
                                config false;
                                description
                                    "This container defines the ISIS Level LSP DB TLV Interface IPv4
                                            address";
                                container state {
                                    config false;
                                    description
                                        "This container defines the ISIS Level LSP DB TLV Interface IPv4
                                                address State";
                                    uses isis-level-lspdb-local-ipv4-addr-state;
                                    uses isis-level-lspdb-mismatch-state;
                                } // END of state-container definition.
                            } // END of ipv4-interface-address-container definition.
                            container ipv4-neighbor-address {
                                if-feature feature-list:HAVE_ISIS_TE;
                                config false;
                                description
                                    "This container defines the ISIS Level LSP DB TLV Neighbor IPv4 address";
                                container state {
                                    config false;
                                    description
                                        "This container defines the ISIS Level LSP DB TLV Neighbor IPv4 address
                                                State";
                                    uses isis-level-lspdb-neighbor-ipv4-addr-state;
                                    uses isis-level-lspdb-mismatch-state;
                                } // END of state-container definition.
                            } // END of ipv4-neighbor-address-container definition.
                            container ipv6-interface-address {
                                if-feature feature-list:HAVE_ISIS_TE;
                                if-feature feature-list:HAVE_IPV6;
                                config false;
                                description
                                    "This container defines the ISIS Level LSP DB TLV Interface IPv6
                                            address";
                                container state {
                                    config false;
                                    description
                                        "This container defines the ISIS Level LSP DB TLV Interface IPv6
                                                address State";
                                    uses isis-level-lspdb-local-ipv6-addr-state;
                                    uses isis-level-lspdb-mismatch-state;
                                } // END of state-container definition.
                            } // END of ipv6-interface-address-container definition.
                            container ipv6-neighbor-address {
                                if-feature feature-list:HAVE_ISIS_TE;
                                if-feature feature-list:HAVE_IPV6;
                                config false;
                                description
                                    "This container defines the ISIS Level LSP DB TLV Neighbor IPv6 address";
                                container state {
                                    config false;
                                    description
                                        "This container defines the ISIS Level LSP DB TLV Neighbor IPv6 address
                                                State";
                                    uses isis-level-lspdb-neighbor-ipv6-addr-state;
                                    uses isis-level-lspdb-mismatch-state;
                                } // END of state-container definition.
                            } // END of ipv6-neighbor-address-container definition.
                            container max-link-bandwidth {
                                if-feature feature-list:HAVE_ISIS_TE;
                                config false;
                                description
                                    "This container defines the ISIS Level LSP DB Stlv Max-Link Bandwidth";
                                container state {
                                    config false;
                                    description
                                        "This container defines the ISIS Level LSP DB Stlv Max-Link Bandwidth
                                                State";
                                    uses isis-level-lspdb-max-link-bw-state;
                                    uses isis-level-lspdb-mismatch-state;
                                } // END of state-container definition.
                            } // END of max-link-bandwidth-container definition.
                            container max-reserve-link-bandwidth {
                                if-feature feature-list:HAVE_ISIS_TE;
                                config false;
                                description
                                    "This container defines the ISIS Level LSP DB Stlv Max-Link Bandwidth";
                                container state {
                                    config false;
                                    description
                                        "This container defines the ISIS Level LSP DB Stlv Max-Link Bandwidth
                                                State";
                                    uses isis-level-lspdb-max-reserve-bw-state;
                                    uses isis-level-lspdb-mismatch-state;
                                } // END of state-container definition.
                            } // END of max-reserve-link-bandwidth-container definition.
                            container unreserved-bandwidth {
                                if-feature feature-list:HAVE_ISIS_TE;
                                config false;
                                description
                                    "This container defines the ISIS Level LSP DB Stlv LSPDB Unreserve
                                            Bandwidth";
                                container state {
                                    config false;
                                    description
                                        "This container defines the ISIS Level LSP DB Stlv LSPDB Unreserve
                                                Bandwidth State";
                                    uses isis-level-lspdb-unreserve-bw-state;
                                    uses isis-level-lspdb-mismatch-state;
                                } // END of state-container definition.
                            } // END of unreserved-bandwidth-container definition.
                            container te-default-metric {
                                if-feature feature-list:HAVE_ISIS_TE;
                                config false;
                                description
                                    "This container defines the ISIS Level LSP DB Stlv LSPD TE Default
                                            Metric";
                                container state {
                                    config false;
                                    description
                                        "This container defines the ISIS Level LSP DB Stlv LSPD TE Default
                                                Metric State";
                                    uses isis-level-lspdb-te-default-metric-state;
                                    uses isis-level-lspdb-mismatch-state;
                                } // END of state-container definition.
                            } // END of te-default-metric-container definition.
                            container uni-link-delay {
                                if-feature feature-list:HAVE_ISIS_TE;
                                config false;
                                description
                                    "This container defines the ISIS Level LSP DB Stlv Unidirectional Link
                                            Delay";
                                container state {
                                    config false;
                                    description
                                        "This container defines the ISIS Level LSP DB Stlv Unidirectional Link
                                                Delay";
                                    uses isis-level-lspdb-uni-link-delay-state;
                                    uses isis-level-lspdb-mismatch-state;
                                } // END of state-container definition.
                            } // END of uni-link-delay-container definition.
                            container min-max-uni-link-delay {
                                if-feature feature-list:HAVE_ISIS_TE;
                                config false;
                                description
                                    "This container defines the ISIS Level LSP DB Stlv Min/Max
                                            Unidirectional Link Delay";
                                container state {
                                    config false;
                                    description
                                        "This container defines the ISIS Level LSP DB Stlv Min/Max
                                                Unidirectional Link Delay";
                                    uses isis-level-lspdb-min-max-uni-link-delay-state;
                                    uses isis-level-lspdb-mismatch-state;
                                } // END of state-container definition.
                            } // END of min-max-uni-link-delay-container definition.
                            container uni-delay-variation {
                                if-feature feature-list:HAVE_ISIS_TE;
                                config false;
                                description
                                    "This container defines the ISIS Level LSP DB Stlv Unidirectional Delay
                                            variation";
                                container state {
                                    config false;
                                    description
                                        "This container defines the ISIS Level LSP DB Stlv Unidirectional Delay
                                                Variotaion";
                                    uses isis-level-lspdb-uni-delay-variation-state;
                                    uses isis-level-lspdb-mismatch-state;
                                } // END of state-container definition.
                            } // END of uni-delay-variation-container definition.
                            container uni-link-loss {
                                if-feature feature-list:HAVE_ISIS_TE;
                                config false;
                                description
                                    "This container defines the ISIS Level LSP DB Stlv Unidirectional Link
                                            Loss";
                                container state {
                                    config false;
                                    description
                                        "This container defines the ISIS Level LSP DB Stlv Unidirectional Link
                                                Loss";
                                    uses isis-level-lspdb-uni-link-loss-state;
                                    uses isis-level-lspdb-mismatch-state;
                                } // END of state-container definition.
                            } // END of uni-link-loss-container definition.
                            container uni-residual-bw {
                                if-feature feature-list:HAVE_ISIS_TE;
                                config false;
                                description
                                    "This container defines the ISIS Level LSP DB Stlv Unidirectional
                                            Residual Bandwidth";
                                container state {
                                    config false;
                                    description
                                        "This container defines the ISIS Level LSP DB Stlv Unidirectional
                                                Residual Bandwidth";
                                    uses isis-level-lspdb-uni-residual-bw-state;
                                    uses isis-level-lspdb-mismatch-state;
                                } // END of state-container definition.
                            } // END of uni-residual-bw-container definition.
                            container uni-available-bw {
                                if-feature feature-list:HAVE_ISIS_TE;
                                config false;
                                description
                                    "This container defines the ISIS Level LSP DB Stlv Unidirectional
                                            Available Bandwidth";
                                container state {
                                    config false;
                                    description
                                        "This container defines the ISIS Level LSP DB Stlv Unidirectional
                                                Available Bandwidth";
                                    uses isis-level-lspdb-uni-available-bw-state;
                                    uses isis-level-lspdb-mismatch-state;
                                } // END of state-container definition.
                            } // END of uni-available-bw-container definition.
                            container uni-utilized-bw {
                                if-feature feature-list:HAVE_ISIS_TE;
                                config false;
                                description
                                    "This container defines the ISIS Level LSP DB Stlv Unidirectional
                                            Utilized Bandwidth";
                                container state {
                                    config false;
                                    description
                                        "This container defines the ISIS Level LSP DB Stlv Unidirectional Link
                                                Loss";
                                    uses isis-level-lspdb-uni-utilized-bw-state;
                                    uses isis-level-lspdb-mismatch-state;
                                } // END of state-container definition.
                            } // END of uni-utilized-bw-container definition.
                            container sr-te-adjacency-sid {
                                if-feature feature-list:HAVE_ISIS_TE;
                                if-feature feature-list:HAVE_ISIS_SR;
                                config false;
                                description
                                    "This container defines the ISIS Level LSP DB Stlv ISIS-SR TE Adj SID";
                                container state {
                                    config false;
                                    description
                                        "This container defines the ISIS Level LSP DB Stlv ISIS-SR TE Adj SID
                                                State";
                                    uses isis-level-lspdb-sr-te-adj-sid-state;
                                    uses isis-level-lspdb-mismatch-state;
                                } // END of state-container definition.
                            } // END of sr-te-adjacency-sid-container definition.
                            container sr-te-lan-adjacency-sid {
                                if-feature feature-list:HAVE_ISIS_TE;
                                if-feature feature-list:HAVE_ISIS_SR;
                                config false;
                                description
                                    "This container defines the ISIS Level LSP DB Stlv ISIS-SR TE Adj SID";
                                container state {
                                    config false;
                                    description
                                        "This container defines the ISIS Level LSP DB Stlv ISIS-SR TE Adj SID
                                                State";
                                    uses isis-level-lspdb-sr-te-lan-adj-sid-state;
                                    uses isis-level-lspdb-mismatch-state;
                                } // END of state-container definition.
                            } // END of sr-te-lan-adjacency-sid-container definition.
                            container link-ids {
                                if-feature feature-list:HAVE_GMPLS;
                                config false;
                                description
                                    "This container defines the ISIS Level LSP DB Stlv GMPLS link id";
                                container state {
                                    config false;
                                    description
                                        "This container defines the ISIS Level LSP DB Stlv GMPLS link id State";
                                    uses isis-level-lspdb-link-id-state;
                                    uses isis-level-lspdb-mismatch-state;
                                } // END of state-container definition.
                            } // END of link-ids-container definition.
                            container link-protection-type {
                                if-feature feature-list:HAVE_GMPLS;
                                config false;
                                description
                                    "This container defines the ISIS Level LSP DB Stlv GMPLS link
                                            protection Type";
                                container state {
                                    config false;
                                    description
                                        "This container defines the ISIS Level LSP DB Stlv GMPLS link
                                                protection Type State";
                                    uses isis-level-lspdb-link-protection-type-state;
                                    uses isis-level-lspdb-mismatch-state;
                                } // END of state-container definition.
                            } // END of link-protection-type-container definition.
                            container link-switch-capability {
                                if-feature feature-list:HAVE_GMPLS;
                                config false;
                                description
                                    "This container defines the ISIS Level LSP DB Stlv GMPLS link Swithch
                                            Capability";
                                container state {
                                    config false;
                                    description
                                        "This container defines the ISIS Level LSP DB Stlv GMPLS link Swithch
                                                Capability State";
                                    uses isis-level-lspdb-link-switch-capability-state;
                                    uses isis-level-lspdb-mismatch-state;
                                } // END of state-container definition.
                            } // END of link-switch-capability-container definition.
                            container endx-sid {
                                if-feature feature-list:HAVE_SRV6;
                                config false;
                                description
                                    "This container defines the ISIS Level LSP DB Stlv EndX SID";
                                container state {
                                    config false;
                                    description
                                        "This container defines the ISIS Level LSP DB Stlv EndX SID";
                                    uses isis-level-lspdb-endx-sid-state;
                                    uses isis-level-lspdb-mismatch-state;
                                } // END of state-container definition.
                            } // END of endx-sid-container definition.
                            container lan-endx-sid {
                                if-feature feature-list:HAVE_SRV6;
                                config false;
                                description
                                    "This container defines the ISIS Level LSP DB Stlv LAN EndX SID";
                                container state {
                                    config false;
                                    description
                                        "This container defines the ISIS Level LSP DB Stlv LAN EndX SID";
                                    uses isis-level-lspdb-lan-endx-sid-state;
                                    uses isis-level-lspdb-mismatch-state;
                                } // END of state-container definition.
                            } // END of lan-endx-sid-container definition.
                        } // End of subtlv-list
                        container state {
                            config false;
                            description
                                "This objectlist defines the ISIS Level LSP DB MultiTopology IS
                                        reachability TLV State";
                            uses isis-level-lspdb-tlv-multi-is-reach-state;
                        } // END of state-container definition.
                    } // End of multi-topology-is-reachability-list

                    list multi-topology-ipv6-reachability {
                        if-feature feature-list:HAVE_MULTI_TOPOLOGY;
                        if-feature feature-list:HAVE_IPV6;
                        key "multi-ipv6-reach-index";
                        config false;
                        description
                            "This objectlist defines the ISIS Level LSP DB MultiTopology Ipv6
                                        reachability TLV";
                        leaf multi-ipv6-reach-index  {
                            type  leafref {
                                path  "../state/multi-ipv6-reach-index";
                            }
                            description "MT Index";
                        } // END of multi-ipv6-reach-index definition.


                        list subtlv {
                            key "stlv-reach-index";
                            config false;
                            description
                                "This objectlist defines the ISIS Level LSP DB Stlv Reach List";
                            leaf stlv-reach-index  {
                                type  leafref {
                                    path  "../state/stlv-reach-index";
                                }
                                description "Index";
                            } // END of stlv-reach-index definition.

                            container state {
                                config false;
                                description
                                    "This container defines the ISIS Level LSP DB Stlv List Reach State";
                                uses isis-level-lspdb-stlv-reach-state;
                            } // END of state-container definition.
                            container admin-tag-info {
                                config false;
                                description
                                    "This container defines the ISIS Level LSP DB Stlv Admin tag STLV";
                                container state {
                                    config false;
                                    description
                                        "This container defines the ISIS Level LSP DB Stlv State";
                                    uses isis-level-lspdb-admin-tag-info;
                                    uses isis-level-lspdb-mismatch-state;
                                } // END of state-container definition.
                            } // END of admin-tag-info-container definition.
                            container prefix-sid {
                                if-feature feature-list:HAVE_ISIS_SR;
                                config false;
                                description
                                    "Prefix segment Identifier STLV";
                                container state {
                                    config false;
                                    description
                                        "State items for ISIS Level LSPDB Prefix SID";
                                    uses isis-level-lspdb-prefix-sid-state;
                                    uses isis-level-lspdb-mismatch-state;
                                } // END of state-container definition.
                            } // END of prefix-sid-container definition.
                        } // End of subtlv-list
                        container state {
                            config false;
                            description
                                "This container defines the ISIS Level LSP DB MultiTopology Ipv6
                                        reachability TLV State";
                            uses isis-level-lspdb-tlv-ipv6-multi-reach-state;
                        } // END of state-container definition.
                    } // End of multi-topology-ipv6-reachability-list

                    list multi-topology-ipv4-reachability {
                        if-feature feature-list:HAVE_MULTI_TOPOLOGY;
                        key "id";
                        config false;
                        description
                            "This objectlist defines the ISIS Level LSP DB MultiTopology Ipv4
                                        reachability TLV";
                        leaf id  {
                            type  leafref {
                                path  "../state/id";
                            }
                            description "MT Index";
                        } // END of id definition.


                        list subtlv {
                            key "stlv-reach-index";
                            config false;
                            description
                                "This objectlist defines the ISIS Level LSP DB Stlv Reach List";
                            leaf stlv-reach-index  {
                                type  leafref {
                                    path  "../state/stlv-reach-index";
                                }
                                description "Index";
                            } // END of stlv-reach-index definition.

                            container state {
                                config false;
                                description
                                    "This container defines the ISIS Level LSP DB Stlv List Reach State";
                                uses isis-level-lspdb-stlv-reach-state;
                            } // END of state-container definition.
                            container admin-tag-info {
                                config false;
                                description
                                    "This container defines the ISIS Level LSP DB Stlv Admin tag STLV";
                                container state {
                                    config false;
                                    description
                                        "This container defines the ISIS Level LSP DB Stlv State";
                                    uses isis-level-lspdb-admin-tag-info;
                                    uses isis-level-lspdb-mismatch-state;
                                } // END of state-container definition.
                            } // END of admin-tag-info-container definition.
                            container prefix-sid {
                                if-feature feature-list:HAVE_ISIS_SR;
                                config false;
                                description
                                    "Admin tag STLV";
                                container state {
                                    config false;
                                    description
                                        "State items for ISIS Level LSPDB Prefix SID";
                                    uses isis-level-lspdb-prefix-sid-state;
                                    uses isis-level-lspdb-mismatch-state;
                                } // END of state-container definition.
                            } // END of prefix-sid-container definition.
                        } // End of subtlv-list
                        container state {
                            config false;
                            description
                                "This container defines the ISIS Level LSP DB MultiTopology Ipv4
                                        reachability TLV State";
                            uses isis-level-lspdb-tlv-ipv4-multi-reach-state;
                        } // END of state-container definition.
                    } // End of multi-topology-ipv4-reachability-list
                    container state {
                        config false;
                        description
                            "This container defines the ISIS Level LSP DB TLV State";
                        uses isis-level-lspdb-tlv-state;
                    } // END of state-container definition.
                    container area-addresses {
                        config false;
                        description
                            "This objectlist defines the ISIS Level LSP DB Area Address";
                        container state {
                            config false;
                            description
                                "State items for ISIS Level LSPDB TLV Area Address State";
                            uses isis-level-lspdb-tlv-area-address-state;
                        } // END of state-container definition.
                    } // END of area-addresses-container definition.
                    container supported-protocol {
                        config false;
                        description
                            "This container defines the ISIS Level LSP DB TLV for protocol
                                    supported";
                        container state {
                            config false;
                            description
                                "This container defines the ISIS Level LSP DB TLV for protocol
                                        supported State";
                            uses isis-level-lspdb-supported-proto-state;
                        } // END of state-container definition.
                    } // END of supported-protocol-container definition.
                    container host-name {
                        config false;
                        description
                            "This container defines the host name TLV";
                        container state {
                            config false;
                            description
                                "This container state information for hostname TLV";
                            uses isis-level-lspdb-host-name-state;
                        } // END of state-container definition.
                    } // END of host-name-container definition.
                    container ipv4-interface-addresses {
                        config false;
                        description
                            "This container defines the ISIS Level LSP DB TLV interface IP addr";
                        container state {
                            config false;
                            description
                                "This container defines the ISIS Level LSP DB TLV interface IP addr
                                        State";
                            uses isis-level-lspdb-tlv-ip-address-state;
                        } // END of state-container definition.
                    } // END of ipv4-interface-addresses-container definition.
                    container sid-label-binding {
                        if-feature feature-list:HAVE_ISIS_SR;
                        config false;
                        description
                            "This container defines the ISIS Level LSP DB TLV SID label binding";
                        container state {
                            config false;
                            description
                                "This container defines the ISIS Level LSP DB TLV SID label binding
                                        State";
                            uses isis-level-lspdb-tlv-sid-label-binding-state;
                        } // END of state-container definition.
                    } // END of sid-label-binding-container definition.
                    container ipv4-te-router-id {
                        if-feature feature-list:HAVE_ISIS_TE;
                        config false;
                        description
                            "This container defines the ISIS Level LSP DB TLV IPv4 TE router-id";
                        container state {
                            config false;
                            description
                                "This container defines the ISIS Level LSP DB TLV IPv4 TE router-id
                                        State";
                            uses isis-level-lspdb-tlv-ipv4-te-router-id-state;
                        } // END of state-container definition.
                    } // END of ipv4-te-router-id-container definition.
                    container ipv4-shared-risk-link-group {
                        if-feature feature-list:HAVE_WIDE_METRIC;
                        if-feature feature-list:HAVE_GMPLS;
                        config false;
                        description
                            "This container defines the ISIS Level LSP DB TLV Shared Like Risk
                                    Group";
                        container state {
                            config false;
                            description
                                "This container defines the ISIS Level LSP DB TLV Shared Like Risk
                                        Group State";
                            uses isis-level-lspdb-tlv-ipv4-srlg-state;
                        } // END of state-container definition.
                    } // END of ipv4-shared-risk-link-group-container definition.
                    container ipv6-te-router-id {
                        if-feature feature-list:HAVE_ISIS_TE;
                        if-feature feature-list:HAVE_IPV6;
                        config false;
                        description
                            "This container defines the ISIS Level LSP DB TLV Te Ipv6 Router-id";
                        container state {
                            config false;
                            description
                                "This container defines the ISIS Level LSP DB TLV Te Ipv6 Router-id
                                        State";
                            uses isis-level-lspdb-tlv-ipv6-te-router-id-state;
                        } // END of state-container definition.
                    } // END of ipv6-te-router-id-container definition.
                    container ipv6-interface-address {
                        if-feature feature-list:HAVE_IPV6;
                        config false;
                        description
                            "This container defines the ISIS Level LSP DB TLV interface IPv6 addr";
                        container state {
                            config false;
                            description
                                "This container defines the ISIS Level LSP DB TLV interface IPv6 addr
                                        State";
                            uses isis-level-lspdb-tlv-ipv6-interface-address-state;
                        } // END of state-container definition.
                    } // END of ipv6-interface-address-container definition.
                    container router-capability {
                        if-feature feature-list:HAVE_ISIS_SR_OR_HAVE_SRV6;
                        config false;
                        description
                            "This container defines the ISIS Level LSP DB Router Capability TLV";

                        list subtlv {
                            key "stlv-index";
                            config false;
                            description
                                "This objectlist defines the ISIS Level LSP DB Router Capability STLVs";
                            leaf stlv-index  {
                                type  leafref {
                                    path  "../state/stlv-index";
                                }
                                description "Index";
                            } // END of stlv-index definition.

                            container state {
                                config false;
                                description
                                    "This container defines the ISIS Level LSP DB Router Capability STLV
                                            State";
                                uses isis-level-lspdb-tlv-router-cap-stlv-state;
                            } // END of state-container definition.
                            container segment-routing {
                                if-feature feature-list:HAVE_ISIS_SR;
                                config false;
                                description
                                    "This container defines the ISIS Level LSP DB Router Capabilit STLV SR
                                            Capability";
                                container state {
                                    config false;
                                    description
                                        "This container defines the ISIS Level LSP DB Router Capabilit STLV SR
                                                Capability State";
                                    uses isis-level-lspdb-tlv-router-cap-stlv-sr-cap-state;
                                    uses isis-level-lspdb-mismatch-state;
                                } // END of state-container definition.
                            } // END of segment-routing-container definition.
                            container segment-routing-algorithm {
                                if-feature feature-list:HAVE_ISIS_SR;
                                config false;
                                description
                                    "This container defines the ISIS Level LSP DB Router Capabilit STLV SR
                                            Algorithm";
                                container state {
                                    config false;
                                    description
                                        "This container defines the ISIS Level LSP DB Router Capabilit STLV SR
                                                Algorithm State";
                                    uses isis-level-lspdb-tlv-router-cap-stlv-sr-algo-state;
                                    uses isis-level-lspdb-mismatch-state;
                                } // END of state-container definition.
                            } // END of segment-routing-algorithm-container definition.
                            container segment-routing-mapping-server-preference {
                                if-feature feature-list:HAVE_ISIS_SR;
                                config false;
                                description
                                    "This container defines the ISIS Level LSP DB Router Capabilit STLV SR
                                            Preference";
                                container state {
                                    config false;
                                    description
                                        "This container defines the ISIS Level LSP DB Router Capabilit STLV SR
                                                Preference State";
                                    uses isis-level-lspdb-tlv-router-cap-stlv-srms-preference-state;
                                    uses isis-level-lspdb-mismatch-state;
                                } // END of state-container definition.
                            } // END of segment-routing-mapping-server-preference-container definition.
                            container segment-routing-v6 {
                                if-feature feature-list:HAVE_SRV6;
                                config false;
                                description
                                    "This container defines the ISIS Level LSP DB Router Capability STLV
                                            SRv6 Capability";
                                container state {
                                    config false;
                                    description
                                        "This container defines the ISIS Level LSP DB Router Capability STLV
                                                SRv6 Capability State";
                                    uses isis-level-lspdb-tlv-router-cap-stlv-srv6-cap-state;
                                    uses isis-level-lspdb-mismatch-state;
                                } // END of state-container definition.
                            } // END of segment-routing-v6-container definition.
                            container max-sid-depth {
                                if-feature feature-list:HAVE_SRV6;
                                config false;
                                description
                                    "This container defines the ISIS Level LSP DB Router Capability STLV
                                            MAX SID Depth";
                                container state {
                                    config false;
                                    description
                                        "This container defines the ISIS Level LSP DB Router Capability STLV
                                                MAX SID Depth";
                                    uses isis-level-lspdb-tlv-router-cap-stlv-max-sid-depth;
                                    uses isis-level-lspdb-mismatch-state;
                                } // END of state-container definition.
                            } // END of max-sid-depth-container definition.
                        } // End of subtlv-list
                        container state {
                            config false;
                            description
                                "This container defines the ISIS Level LSP DB Router Capability TLV
                                        State";
                            uses isis-level-lspdb-tlv-router-cap-state;
                        } // END of state-container definition.
                    } // END of router-capability-container definition.
                    container srv6-locator {
                        if-feature feature-list:HAVE_SRV6;
                        config false;
                        description
                            "This container defines the ISIS Level LSP DB SRv6 Locator TLV";

                        list subtlv {
                            key "stlv-index stlv-endpoint-function";
                            config false;
                            description
                                "This objectlist defines the ISIS Level LSP DB Router Capability STLVs";
                            leaf stlv-index  {
                                type  leafref {
                                    path  "../state/stlv-index";
                                }
                                description "Index";
                            } // END of stlv-index definition.

                            leaf stlv-endpoint-function  {
                                type  leafref {
                                    path  "../state/stlv-endpoint-function";
                                }
                                description "End-Point Function";
                            } // END of stlv-endpoint-function definition.

                            container state {
                                config false;
                                description
                                    "This container defines the ISIS Level LSP DB SRv6 Locator STLV State";
                                uses isis-level-lspdb-tlv-srv6-locator-stlv-state;
                            } // END of state-container definition.
                            container srv6-end-sid {
                                if-feature feature-list:HAVE_SRV6;
                                config false;
                                description
                                    "This container defines the ISIS Level LSP DB SRv6 Locator STLV SRv6
                                            END-SID";
                                container state {
                                    config false;
                                    description
                                        "This container defines the ISIS Level LSP DB SRv6 Locator STLV SRv6
                                                END-SID State";
                                    uses isis-level-lspdb-tlv-srv6-locator-sid-entries;
                                    uses isis-level-lspdb-mismatch-state;
                                } // END of state-container definition.
                            } // END of srv6-end-sid-container definition.
                        } // End of subtlv-list
                        container state {
                            config false;
                            description
                                "This container defines the ISIS Level LSP DB SRV6 Locator TLV State";
                            uses isis-level-lspdb-tlv-srv6-locator-state;
                        } // END of state-container definition.
                    } // END of srv6-locator-container definition.
                } // End of tlvs-list
                container state {
                    config false;
                    description
                        "This container defines the ISIS Level LSP DB State";
                    uses isis-level-lspdb-state;
                } // END of state-container definition.
            } // End of lspdb-list

            list protocol-data {
                key "index";
                config false;
                description
                    "This objectlist defines the ISIS Level IPv4/IPv6 protocol data";
                leaf index  {
                    type  uint8;
                    description "Index of protocol";
                } // END of index definition.


                list vertex {
                    key "destination-system-id";
                    config false;
                    description
                        "This objectlist defines the ISIS Level SPF Tree Vertex";
                    leaf destination-system-id  {
                        type  leafref {
                            path  "../state/destination-system-id";
                        }
                        description "Nexthop neighbor source ID";
                    } // END of destination-system-id definition.


                    list vertex-nexthop {
                        key "nexthop-interface nexthop-system-id";
                        config false;
                        description
                            "This objectlist defines the Vertex nexthop data";
                        leaf nexthop-interface  {
                            type  leafref {
                                path  "../state/nexthop-interface";
                            }
                            description "Nexthop interface index";
                        } // END of nexthop-interface definition.

                        leaf nexthop-system-id  {
                            type  leafref {
                                path  "../state/nexthop-system-id";
                            }
                            description "Nexthop neighbor source ID";
                        } // END of nexthop-system-id definition.

                        container state {
                            config false;
                            description
                                "This container defines the Vertex Nexthop State data";
                            uses isis-level-proto-vertex-nexthop-state;
                        } // END of state-container definition.
                    } // End of vertex-nexthop-list
                    container state {
                        config false;
                        description
                            "This container defines the ISIS Level SPF Tree Vertex State";
                        uses isis-level-proto-vertex-state;
                    } // END of state-container definition.
                } // End of vertex-list
            } // End of protocol-data-list
            container state {
                config false;
                description
                    "This container defines the ISIS Level State information";
                container counters {
                    config false;
                    description
                        "This container defines the ISIS LSP Counters";
                    uses isis-lsp-counter-state;
                } // END of counters-container definition.
                uses isis-level-state;
            } // END of state-container definition.
        } // End of level-runtime-list
    } // END of level-runtime-grouping definition.
    grouping isis-spf-level-config {
        description
            "Configuration items for ISIS SPF Level";
        leaf level  {
            type  ipi-isis-types:isis_level3_t;
            default "level-1-2";
            description "IS-IS instance level,(1|2|3)";
        } // END of level definition.

    } // END of isis-spf-level-config definition.
    grouping isis-level-config {
        description
            "Configuration items for ISIS Level";
        leaf type  {
            type  ipi-isis-types:isis_level3_t;
            default "level-1-2";
            description "IS-IS instance level,(1|2|3)";
        } // END of type definition.

        leaf wait-timer  {
            type  uint16 {
                 range "1..65535"  {
                    description "1..65535: Supported range 1 - 65535";
                 }
            }
            description "Number of seconds to delay in waiting state before on state";
        } // END of wait-timer definition.

        leaf restart-timer  {
            type  uint16 {
                 range "5..65535"  {
                    description "5..65535: Supported range 5 - 65535";
                 }
            }
            description "Use this attribute to restart the ISIS timer";
        } // END of restart-timer definition.

        leaf lsp-max-wait-interval  {
            type  uint32 {
                 range "1..120"  {
                    description "1..120: Supported range 1 - 120";
                 }
            }
            default "5";
            description "Use this attribute to set minimum interval before regenerating the
                        same LSP. The smaller the interval, the faster the convergence.
                        However, this setting might cause more frequent flooding";
        } // END of lsp-max-wait-interval definition.

        leaf lsp-mtu-size  {
            type  uint16 {
                 range "512..4352"  {
                    description "512..4352: Supported range 512 - 4352";
                 }
            }
            default "1492";
            description "Use this attribute to set minimum interval before regenerating the
                        same LSP";
        } // END of lsp-mtu-size definition.

    } // END of isis-level-config definition.
    grouping isis-authentication-config {
        description
            "This grouping defines ISIS authentication mode configuration";
        leaf key-chain  {
            type  string {
                length "1..1965";
                pattern "[^?' =,>|]+";
            }
            description "Use this attribute to set the key chain to be used for authentication
                        at the instance level. Authentication mode must be set to md5/text to
                        configure the key chain.";
        } // END of key-chain definition.

        leaf mode  {
            type  ipi-isis-types:isis_auth_mode_t;
            mandatory true;
            description "Use this attribute to set the authentication mode at the instance
                        level.";
        } // END of mode definition.

    } // END of isis-authentication-config definition.
    grouping isis-spf-config {
        description
            "Config items for ISIS SPF";
        leaf spf-min-delay  {
            type  uint32 {
                 range "0..2147483647"  {
                    description "0..2147483647: Supported range 0 - 2147483647";
                 }
            }
            description "Minimum delay between receiving a change to SPF calculation in
                        milliseconds.The default value is 500";
        } // END of spf-min-delay definition.

        leaf spf-max-delay  {
            type  uint32 {
                 range "0..2147483647"  {
                    description "0..2147483647: Supported range 0 - 2147483647";
                 }
            }
            description "Maximum delay between receiving a change to SPF calculation in
                        milliseconds.The default value is 5000";
        } // END of spf-max-delay definition.

    } // END of isis-spf-config definition.
    grouping isis-level-state {
        description
            "State items for ISIS Level";
        leaf type  {
            type  ipi-isis-types:isis_level2_t;
            description "IS-IS instance level,(1|2)";
        } // END of type definition.

        leaf topology-type  {
            type  uint8;
            description "Topology type";
        } // END of topology-type definition.

    } // END of isis-level-state definition.
    grouping isis-lsp-counter-state {
        description
            "State items for ISIS Adjacency Counters";
        leaf authentication-type-fails  {
            type  uint32;
            description "The number of authentication type mismatches recognized by this
                        Intermediate System";
        } // END of authentication-type-fails definition.

        leaf authentication-fails  {
            type  uint32;
            description "The number of authentication key failures recognized by this
                        Intermediate System.";
        } // END of authentication-fails definition.

        leaf corrupted-lsps  {
            type  uint32;
            description "Number of corrupted LSPs detected.";
        } // END of corrupted-lsps definition.

        leaf database-overloads  {
            type  uint32;
            description "Number of times the LSP database has become overloaded.";
        } // END of database-overloads definition.

        leaf manual-address-drop-from-areas  {
            type  uint32;
            description "Number of times a manual address has been dropped from the area.";
        } // END of manual-address-drop-from-areas definition.

        leaf attempt-to-exceed-maximum-sequence-numbers  {
            type  uint32;
            description "Number of times the IS has attempted to exceed the maximum sequence
                        number.";
        } // END of attempt-to-exceed-maximum-sequence-numbers definition.

        leaf sequence-number-skips  {
            type  uint32;
            description "Number of times a sequence number skip has occurred.";
        } // END of sequence-number-skips definition.

        leaf own-lsp-purges  {
            type  uint32;
            description "Number of times a zero-aged copy of the system's own LSP is received
                        from some other node.";
        } // END of own-lsp-purges definition.

        leaf lsp-sourced  {
            type  uint32;
            description "Number of times a lsp is sourced";
        } // END of lsp-sourced definition.

        leaf maximum-area-address-mismatches  {
            type  uint32;
            description "Number of times there is a mismatch between area-address";
        } // END of maximum-area-address-mismatches definition.

        leaf id-length-mismatch  {
            type  uint32;
            description "Number of times a PDU is received with a different value for ID field
                        length from that of the receiving system.";
        } // END of id-length-mismatch definition.

        leaf partition-changes  {
            type  uint32;
            description "Partition changes.";
        } // END of partition-changes definition.

        leaf spf-runs  {
            type  uint32;
            description "Number of times we ran SPF.";
        } // END of spf-runs definition.

        leaf partial-route-calculation-count  {
            type  uint32;
            description "Number of times we ran PRC.";
        } // END of partial-route-calculation-count definition.

        leaf lan-designated-is-changes  {
            type  uint32;
            description "Number of times DIS has changed.";
        } // END of lan-designated-is-changes definition.

    } // END of isis-lsp-counter-state definition.
    grouping isis-level-lspdb-state {
        description
            "State items for ISIS Level LSPDB";
        leaf lsp-identifier  {
            type  string {
                length "1..1965";
                pattern "[^?' =,>|]+";
            }
            description "LSP ID";
        } // END of lsp-identifier definition.

        leaf is-self-lsp  {
            type  string {
                length "1..1965";
                pattern "[^?' =,>|]+";
            }
            description "Self Lsp";
        } // END of is-self-lsp definition.

        leaf checksum  {
            type  string {
                length "1..1965";
                pattern "[^?' =,>|]+";
            }
            description "LSP Check-Sum";
        } // END of checksum definition.

        leaf remaining-lifetime  {
            type  uint16;
            description "LSP hold time";
        } // END of remaining-lifetime definition.

        leaf flags  {
            type  uint8;
            description "LSP Att flag";
        } // END of flags definition.

        leaf partition-repair  {
            type  boolean;
            description "LSP Partition-flag";
        } // END of partition-repair definition.

        leaf over-loaded  {
            type  boolean;
            description "LSP OverLoad flag";
        } // END of over-loaded definition.

        leaf sequence-number  {
            type  string {
                length "1..1965";
                pattern "[^?' =,>|]+";
            }
            description "Initial Sequence Number with host byte order";
        } // END of sequence-number definition.

        leaf pdu-length  {
            type  uint32;
            description "Length of the PDU";
        } // END of pdu-length definition.

    } // END of isis-level-lspdb-state definition.
    grouping isis-level-lspdb-tlv-state {
        description
            "State items for ISIS Level LSPDB TLV";
        leaf index  {
            type  uint32;
            description "Index";
        } // END of index definition.

    } // END of isis-level-lspdb-tlv-state definition.
    grouping isis-level-lspdb-tlv-area-address-state {
        description
            "State items for ISIS Level LSPDB TLV Area Address";
        leaf-list address  {
            type  string {
                length "1..1965";
                pattern "[^?' =,>|]+";
            }
            description "Address";
        } // END of address definition.

    } // END of isis-level-lspdb-tlv-area-address-state definition.
    grouping isis-level-lspdb-tlv-is-neighbor-state {
        description
            "State items for ISIS Level LSPDB TLV IS Neighbor";
        leaf system-id  {
            type  string {
                length "1..1965";
                pattern "[^?' =,>|]+";
            }
            description "System ID";
        } // END of system-id definition.

        leaf metric  {
            type  uint32;
            description "Metric";
        } // END of metric definition.

    } // END of isis-level-lspdb-tlv-is-neighbor-state definition.
    grouping isis-level-lspdb-tlv-es-neighbor-state {
        description
            "State items for ISIS Level LSPDB TLV ES Neighbor";
        leaf system-id  {
            type  string {
                length "1..1965";
                pattern "[^?' =,>|]+";
            }
            description "System ID";
        } // END of system-id definition.

        leaf metric  {
            type  uint32;
            description "Metric Value";
        } // END of metric definition.

    } // END of isis-level-lspdb-tlv-es-neighbor-state definition.
    grouping isis-level-lspdb-tlv-ip-internal-reach-state {
        description
            "State items for ISIS Level LSPDB IP Internal Reach";
        leaf prefix  {
            type  cml-data-types:cml_line_t {
                length "1..1965";
            }
            description "IPv4 prefix contained within reachability TLVs.";
        } // END of prefix definition.

        leaf metric  {
            type  string {
                length "1..1965";
                pattern "[^?' =,>|]+";
            }
            description "Metric Value";
        } // END of metric definition.

    } // END of isis-level-lspdb-tlv-ip-internal-reach-state definition.
    grouping isis-level-lspdb-tlv-ip-external-reach-state {
        description
            "State items for ISIS Level LSPDB IP External Reach";
        leaf prefix  {
            type  cml-data-types:cml_line_t {
                length "1..1965";
            }
            description "Prefix";
        } // END of prefix definition.

        leaf metric  {
            type  string {
                length "1..63";
                pattern "[^?' =,>|]+";
            }
            description "Metric Value";
        } // END of metric definition.

    } // END of isis-level-lspdb-tlv-ip-external-reach-state definition.
    grouping isis-level-lspdb-supported-proto-state {
        description
            "State items for ISIS Level LSPDB Supported Protocol";
        leaf-list nlp-id  {
            type  ipi-isis-types:isis_level_proto_t;
            description "NLP ID";
        } // END of nlp-id definition.

    } // END of isis-level-lspdb-supported-proto-state definition.
    grouping isis-level-lspdb-host-name-state {
        description
            "State items for ISIS host name tlv";
        leaf host-name  {
            type  string {
                length "1..1965";
                pattern "[^?' =,>|]+";
            }
            description "Host name assigned to the node";
        } // END of host-name definition.

    } // END of isis-level-lspdb-host-name-state definition.
    grouping isis-level-lspdb-tlv-ip-address-state {
        description
            "State items for ISIS Level LSPDB TLV IP Address";
        leaf address  {
            type  inet:ipv4-address;
            description "Address";
        } // END of address definition.

    } // END of isis-level-lspdb-tlv-ip-address-state definition.
    grouping isis-level-lspdb-tlv-sid-label-binding-state {
        description
            "State items for ISIS Level LSPDB TLV SID Label Binding";
        leaf ipv4-address  {
            type  string {
                length "1..1965";
                pattern "[^?' =,>|]+";
            }
            description "IPv4 Address";
        } // END of ipv4-address definition.

        leaf ipv6-address  {
            if-feature feature-list:HAVE_IPV6;
            type  string {
                length "1..1965";
                pattern "[^?' =,>|]+";
            }
            description "IPv6 Address";
        } // END of ipv6-address definition.

        leaf fmsda-flags  {
            type  cml-data-types:cml_line_t {
                length "1..1965";
            }
            description "FMSDA Flags";
        } // END of fmsda-flags definition.

        leaf rnpev-flags  {
            type  cml-data-types:cml_line_t {
                length "1..1965";
            }
            description "RNPEV Flags";
        } // END of rnpev-flags definition.

        leaf start-identifier  {
            type  uint32;
            description "Start Identifier";
        } // END of start-identifier definition.

        leaf algorithm  {
            type  uint32;
            description "Algorithm";
        } // END of algorithm definition.

        leaf range  {
            type  uint32;
            description "Range";
        } // END of range definition.

    } // END of isis-level-lspdb-tlv-sid-label-binding-state definition.
    grouping isis-level-lspdb-tlv-ipv4-te-router-id-state {
        description
            "State items for ISIS Level LSPDB TLV IPv4 TE Router ID";
        leaf unknown-tlv-type  {
            type  uint8;
            description "Unknown TLV Type";
        } // END of unknown-tlv-type definition.

        leaf length  {
            type  uint8;
            description "Length";
        } // END of length definition.

        leaf router-id  {
            type  string {
                length "1..1965";
                pattern "[^?' =,>|]+";
            }
            description "Router ID";
        } // END of router-id definition.

    } // END of isis-level-lspdb-tlv-ipv4-te-router-id-state definition.
    grouping isis-level-lspdb-tlv-extend-is-reach-state {
        description
            "State items for ISIS Level LSPDB TLV IS Reach";
        leaf extended-is-index  {
            type  uint32;
            description "Index";
        } // END of extended-is-index definition.

        leaf system-id  {
            type  string {
                length "1..1965";
                pattern "[^?' =,>|]+";
            }
            description "System ID";
        } // END of system-id definition.

        leaf metric  {
            type  uint32 {
                 range "0..16777215"  {
                    description "0..16777215: Supported range 0 - 16777215";
                 }
            }
            description "Metric Value";
        } // END of metric definition.

    } // END of isis-level-lspdb-tlv-extend-is-reach-state definition.
    grouping isis-level-lspdb-stlv-state {
        description
            "State items for ISIS Level LSPDB STLV";
        leaf subtlv-index  {
            type  uint16;
            description "Index";
        } // END of subtlv-index definition.

    } // END of isis-level-lspdb-stlv-state definition.
    grouping isis-level-lspdb-admin-group-stlv-state {
        description
            "State items for ISIS Level LSPDB Admin Group STLV";
        leaf admin-group  {
            type  string {
                length "1..1965";
                pattern "[^?' =,>|]+";
            }
            description "Admin Group";
        } // END of admin-group definition.

    } // END of isis-level-lspdb-admin-group-stlv-state definition.
    grouping isis-level-lspdb-local-ipv4-addr-state {
        description
            "State items for ISIS Level LSPDB Local IPv4 Address";
        leaf address  {
            type  inet:ipv4-address;
            description "IPv4 Address";
        } // END of address definition.

    } // END of isis-level-lspdb-local-ipv4-addr-state definition.
    grouping isis-level-lspdb-neighbor-ipv4-addr-state {
        description
            "State items for ISIS Level LSPDB Neighbor IPv4 Address";
        leaf address  {
            type  inet:ipv4-address;
            description "Neighbour IP Address";
        } // END of address definition.

    } // END of isis-level-lspdb-neighbor-ipv4-addr-state definition.
    grouping isis-level-lspdb-local-ipv6-addr-state {
        description
            "State items for ISIS Level LSPDB Local IPv6 Address";
        leaf address  {
            type  inet:ipv6-address;
            description "IPv6 Address";
        } // END of address definition.

    } // END of isis-level-lspdb-local-ipv6-addr-state definition.
    grouping isis-level-lspdb-neighbor-ipv6-addr-state {
        description
            "State items for ISIS Level LSPDB Neighbor IPv6 Address";
        leaf address  {
            type  inet:ipv6-address;
            description "Neighbour IP Address";
        } // END of address definition.

    } // END of isis-level-lspdb-neighbor-ipv6-addr-state definition.
    grouping isis-level-lspdb-max-link-bw-state {
        description
            "State items for ISIS Level LSPDB Max Link Bandwidth";
        leaf bandwidth  {
            type  string {
                length "1..1965";
                pattern "[^?' =,>|]+";
            }
            description "Bandwidth";
        } // END of bandwidth definition.

    } // END of isis-level-lspdb-max-link-bw-state definition.
    grouping isis-level-lspdb-max-reserve-bw-state {
        description
            "State items for ISIS Level LSPDB Max Reserve Bandwidth";
        leaf bandwidth  {
            type  ipi-isis-types:isis_ieee_float32_t {
                length "1..1965";
            }
            description "Max Resereved Bandwidth";
        } // END of bandwidth definition.

    } // END of isis-level-lspdb-max-reserve-bw-state definition.
    grouping isis-level-lspdb-unreserve-bw-state {
        description
            "State items for ISIS Level LSPDB Unreserve Bandwidth";
        leaf bandwidth  {
            type  ipi-isis-types:isis_ieee_float32_t {
                length "1..1965";
            }
            description "Unreserved Bandwidth";
        } // END of bandwidth definition.

    } // END of isis-level-lspdb-unreserve-bw-state definition.
    grouping isis-level-lspdb-te-default-metric-state {
        description
            "State items for ISIS Level LSPDB TE Default Metric";
        leaf metric  {
            type  uint32;
            description "Metric Value";
        } // END of metric definition.

    } // END of isis-level-lspdb-te-default-metric-state definition.
    grouping isis-level-lspdb-uni-link-delay-state {
        description
            "State items for ISIS Level LSPDB Unidirectional Link Delay";
        leaf a-bit  {
            type  uint8;
            description "Abit Delay Value";
        } // END of a-bit definition.

        leaf value  {
            type  uint32;
            description "Delay Value";
        } // END of value definition.

    } // END of isis-level-lspdb-uni-link-delay-state definition.
    grouping isis-level-lspdb-min-max-uni-link-delay-state {
        description
            "State items for ISIS Level LSPDB Min/Max Unidirectional link delay";
        leaf a-bit  {
            type  uint8;
            description "Abit Delay Value";
        } // END of a-bit definition.

        leaf min-value  {
            type  uint32;
            description "Minimum Delay Value";
        } // END of min-value definition.

        leaf max-value  {
            type  uint32;
            description "Maximum Delay Value";
        } // END of max-value definition.

    } // END of isis-level-lspdb-min-max-uni-link-delay-state definition.
    grouping isis-level-lspdb-uni-delay-variation-state {
        description
            "State items for ISIS Level LSPDB Unidirectional Delay Variation";
        leaf variation  {
            type  uint32;
            description "Delay Variation Value";
        } // END of variation definition.

    } // END of isis-level-lspdb-uni-delay-variation-state definition.
    grouping isis-level-lspdb-uni-link-loss-state {
        description
            "State items for ISIS Level LSPDB Unidirectional Link Loss";
        leaf a-bit  {
            type  uint8;
            description "abit loss Value";
        } // END of a-bit definition.

        leaf loss  {
            type  decimal64 {
                 fraction-digits 6;            }
            description "loss Value";
        } // END of loss definition.

    } // END of isis-level-lspdb-uni-link-loss-state definition.
    grouping isis-level-lspdb-uni-residual-bw-state {
        description
            "State items for ISIS Level LSPDB Unidirectional Residual Bandwidth";
        leaf residual-bw  {
            type  ipi-isis-types:isis_ieee_float32_t {
                length "1..1965";
            }
            description "Residual BW Value";
        } // END of residual-bw definition.

    } // END of isis-level-lspdb-uni-residual-bw-state definition.
    grouping isis-level-lspdb-uni-available-bw-state {
        description
            "State items for ISIS Level LSPDB Unidirectional Available Bandwidth";
        leaf available-bw  {
            type  ipi-isis-types:isis_ieee_float32_t {
                length "1..1965";
            }
            description "Available BW Value";
        } // END of available-bw definition.

    } // END of isis-level-lspdb-uni-available-bw-state definition.
    grouping isis-level-lspdb-uni-utilized-bw-state {
        description
            "State items for ISIS Level LSPDB Unidirectional Utilized Bandwidth";
        leaf utilized-bw  {
            type  ipi-isis-types:isis_ieee_float32_t {
                length "1..1965";
            }
            description "Utilized BW Value";
        } // END of utilized-bw definition.

    } // END of isis-level-lspdb-uni-utilized-bw-state definition.
    grouping isis-level-lspdb-sr-te-adj-sid-state {
        description
            "State items for ISIS Level LSPDB SR TE Adjacent SID";
        leaf value  {
            type  uint32;
            description "Value";
        } // END of value definition.

        leaf flag  {
            type  cml-data-types:cml_line_t {
                length "1..1965";
            }
            description "Flag";
        } // END of flag definition.

    } // END of isis-level-lspdb-sr-te-adj-sid-state definition.
    grouping isis-level-lspdb-sr-te-lan-adj-sid-state {
        description
            "State items for ISIS Level LSPDB SR TE LAN Adjacent SID";
        leaf system-id  {
            type  string {
                length "1..1965";
                pattern "[^?' =,>|]+";
            }
            description "System ID";
        } // END of system-id definition.

        leaf value  {
            type  uint32;
            description "Value";
        } // END of value definition.

        leaf flag  {
            type  cml-data-types:cml_line_t {
                length "1..1965";
            }
            description "Flags";
        } // END of flag definition.

    } // END of isis-level-lspdb-sr-te-lan-adj-sid-state definition.
    grouping isis-level-lspdb-link-id-state {
        description
            "State items for ISIS Level LSPDB Link ID";
        leaf local  {
            type  uint32;
            description "Local";
        } // END of local definition.

        leaf remote  {
            type  uint32;
            description "Remote";
        } // END of remote definition.

    } // END of isis-level-lspdb-link-id-state definition.
    grouping isis-level-lspdb-link-protection-type-state {
        description
            "State items for ISIS Level LSPDB Link Protection Type";
        leaf type  {
            type  string {
                length "1..1965";
                pattern "[^?' =,>|]+";
            }
            description "Type";
        } // END of type definition.

    } // END of isis-level-lspdb-link-protection-type-state definition.
    grouping isis-level-lspdb-endx-sid-state {
        description
            "State items for ISIS Level LSPDB SRv6 END X SID";
        leaf endx-sid  {
            type  inet:ipv6-address;
            description "SRv6 End-X Segment Identifier";
        } // END of endx-sid definition.

        leaf endx-algo  {
            type  uint32;
            description "Algorithm - As defined in IGP Algorithm Types registry RFC-8665";
        } // END of endx-algo definition.

        leaf endx-flags  {
            type  uint32;
            description "End X Flags containing info about B,S and P bit and reserved info";
        } // END of endx-flags definition.

        leaf endx-behavior  {
            type  string {
                length "1..1965";
                pattern "[^?' =,>|]+";
            }
            description "End X Behavior for the corresponding SID";
        } // END of endx-behavior definition.

        leaf endx-flavor  {
            type  uint32;
            description "End X Flavor for the corresponding SID";
        } // END of endx-flavor definition.

        leaf endx-weight  {
            type  uint32;
            description "The value represents the weight of the SID for the purpose of load
                        balancing.";
        } // END of endx-weight definition.

    } // END of isis-level-lspdb-endx-sid-state definition.
    grouping isis-level-lspdb-lan-endx-sid-state {
        description
            "State items for ISIS Level LSPDB SRv6 END X SID";
        leaf lan-endx-sid  {
            type  inet:ipv6-address;
            description "SRv6 LAN End-X Segment Identifier";
        } // END of lan-endx-sid definition.

        leaf lan-endx-behavior  {
            type  string {
                length "1..1965";
                pattern "[^?' =,>|]+";
            }
            description "LAN End X Behavior for the corresponding SID";
        } // END of lan-endx-behavior definition.

        leaf lan-endx-flavor  {
            type  uint32;
            description "LAN End X Flavor for the corresponding SID";
        } // END of lan-endx-flavor definition.

        leaf lan-endx-sysid  {
            type  string {
                length "1..1965";
                pattern "[^?' =,>|]+";
            }
            description "System ID of the neighbor on the LAN";
        } // END of lan-endx-sysid definition.

        leaf lan-endx-algo  {
            type  uint32;
            description "Algorithm - As defined in IGP Algorithm Types registry RFC-8665";
        } // END of lan-endx-algo definition.

        leaf lan-endx-weight  {
            type  uint32;
            description "The value represents the weight of the SID for the purpose of load
                        balancing.";
        } // END of lan-endx-weight definition.

    } // END of isis-level-lspdb-lan-endx-sid-state definition.
    grouping isis-level-lspdb-link-switch-capability-state {
        description
            "State items for ISIS Level LSPDB Link Switch Capability";
        leaf type  {
            type  string {
                length "1..1965";
                pattern "[^?' =,>|]+";
            }
            description "Type";
        } // END of type definition.

        leaf encoding-type  {
            type  string {
                length "1..1965";
                pattern "[^?' =,>|]+";
            }
            description "Encoding Type";
        } // END of encoding-type definition.

        leaf max-lsp-bandwidth-at-priority  {
            type  ipi-isis-types:isis_ieee_float32_t {
                length "1..1965";
            }
            description "Maximum Bandwidth At Priority";
        } // END of max-lsp-bandwidth-at-priority definition.

        leaf min-lsp-bandwidth  {
            type  ipi-isis-types:isis_ieee_float32_t {
                length "1..1965";
            }
            description "Minimum LSP Bandwidth";
        } // END of min-lsp-bandwidth definition.

        leaf interface-mtu  {
            type  string {
                length "1..1965";
                pattern "[^?' =,>|]+";
            }
            description "Interface MTU";
        } // END of interface-mtu definition.

        leaf sonet-sdh-indication  {
            type  string {
                length "1..1965";
                pattern "[^?' =,>|]+";
            }
            description "Sonet SDH Indication";
        } // END of sonet-sdh-indication definition.

    } // END of isis-level-lspdb-link-switch-capability-state definition.
    grouping isis-level-lspdb-tlv-extended-ipv4-reach-state {
        description
            "State items for ISIS Level LSPDB TLV Extended IPv4 Reach";
        leaf ipv4-reach-index  {
            type  uint32;
            description "Index";
        } // END of ipv4-reach-index definition.

        leaf prefix  {
            type  cml-data-types:cml_ipv4_addr_prefix_t;
            description "Prefix";
        } // END of prefix definition.

        leaf metric  {
            type  uint32 {
                 range "0..16777215"  {
                    description "0..16777215: Supported range 0 - 16777215";
                 }
            }
            description "Metric Value";
        } // END of metric definition.

    } // END of isis-level-lspdb-tlv-extended-ipv4-reach-state definition.
    grouping isis-level-lspdb-stlv-reach-state {
        description
            "State items for ISIS Level LSPDB STLV Reach";
        leaf stlv-reach-index  {
            type  uint16;
            description "Index";
        } // END of stlv-reach-index definition.

    } // END of isis-level-lspdb-stlv-reach-state definition.
    grouping isis-level-lspdb-admin-tag-info {
        description
            "State items for ISIS Level LSPDB Admin Tag";
        leaf admin-tag  {
            type  uint32;
            description "Admin Tag";
        } // END of admin-tag definition.

    } // END of isis-level-lspdb-admin-tag-info definition.
    grouping isis-level-lspdb-prefix-sid-state {
        description
            "State items for ISIS Level LSPDB Prefix SID";
        leaf value  {
            type  uint32;
            description "Value";
        } // END of value definition.

        leaf rnpev-flags  {
            type  cml-data-types:cml_line_t {
                length "1..1965";
            }
            description "RNPEV Flags";
        } // END of rnpev-flags definition.

    } // END of isis-level-lspdb-prefix-sid-state definition.
    grouping isis-level-lspdb-tlv-ipv4-srlg-state {
        description
            "State items for ISIS Level LSPDB TLV IPv4 SRLG";
        leaf value  {
            type  string {
                length "1..1965";
                pattern "[^?' =,>|]+";
            }
            description "Value";
        } // END of value definition.

        leaf neighbor-address  {
            type  inet:ipv4-address;
            description "Neighbour Address";
        } // END of neighbor-address definition.

        leaf local-address  {
            type  inet:ipv4-address;
            description "Local Address";
        } // END of local-address definition.

        leaf system-id  {
            type  string {
                length "1..1965";
                pattern "[^?' =,>|]+";
            }
            description "System ID";
        } // END of system-id definition.

    } // END of isis-level-lspdb-tlv-ipv4-srlg-state definition.
    grouping isis-level-lspdb-tlv-ipv6-te-router-id-state {
        description
            "State items for ISIS Level LSPDB TLV IPv6 TE Router ID";
        leaf unknown-tlv-type  {
            type  uint8;
            description "Unknown TLV Type";
        } // END of unknown-tlv-type definition.

        leaf unknown-tlv-length  {
            type  uint8;
            description "Unknown TLV Length";
        } // END of unknown-tlv-length definition.

        leaf router-id  {
            type  inet:ipv6-address;
            description "Router ID";
        } // END of router-id definition.

    } // END of isis-level-lspdb-tlv-ipv6-te-router-id-state definition.
    grouping isis-level-lspdb-tlv-ipv6-interface-address-state {
        description
            "State items for ISIS Level LSPDB TLV IPv6 Interface Address";
        leaf address  {
            type  inet:ipv6-address;
            description "IPv6 Address";
        } // END of address definition.

    } // END of isis-level-lspdb-tlv-ipv6-interface-address-state definition.
    grouping isis-level-lspdb-tlv-ipv6-reach-state {
        description
            "State items for ISIS Level LSPDB TLV IPv6 Reach";
        leaf ipv6-reach-index  {
            type  uint32;
            description "Index Value";
        } // END of ipv6-reach-index definition.

        leaf prefix  {
            type  cml-data-types:cml_ipv6_prefix_t;
            description "Prefix";
        } // END of prefix definition.

        leaf metric  {
            type  cml-data-types:cml_line_t {
                length "1..1965";
            }
            description "Metric Value";
        } // END of metric definition.

        leaf up-down  {
            type  boolean;
            description "Up/Down Value";
        } // END of up-down definition.

    } // END of isis-level-lspdb-tlv-ipv6-reach-state definition.
    grouping isis-level-lspdb-tlv-ipv4-multi-topo-state {
        description
            "State items for ISIS Level LSPDB TLV IPv4 Multi Topology";
        leaf id  {
            type  string {
                length "1..1965";
            }
            description "MT ID";
        } // END of id definition.

    } // END of isis-level-lspdb-tlv-ipv4-multi-topo-state definition.
    grouping isis-level-lspdb-tlv-multi-is-reach-state {
        description
            "State items for ISIS Level LSPDB TLV Multi IS Reach";
        leaf multi-is-index  {
            type  uint32;
            description "Index";
        } // END of multi-is-index definition.

        leaf system-id  {
            type  string {
                length "1..1965";
            }
            description "System ID";
        } // END of system-id definition.

        leaf metric  {
            type  uint32 {
                 range "1..16777215"  {
                    description "1..16777215: Supported range 1 - 16777215";
                 }
            }
            description "Metric Value";
        } // END of metric definition.

    } // END of isis-level-lspdb-tlv-multi-is-reach-state definition.
    grouping isis-level-lspdb-tlv-ipv6-multi-reach-state {
        description
            "State items for ISIS Level LSPDB TLV IPv6 Multi Reach";
        leaf prefix  {
            type  string {
                length "1..1965";
            }
            description "Prefix";
        } // END of prefix definition.

        leaf metric  {
            type  string {
                length "1..1965";
                pattern "[^?' =,>|]+";
            }
            description "Metric Value";
        } // END of metric definition.

        leaf up-down  {
            type  boolean;
            description "Up/Down Status";
        } // END of up-down definition.

        leaf multi-ipv6-reach-index  {
            type  uint16;
            description "MT Index";
        } // END of multi-ipv6-reach-index definition.

        leaf id  {
            type  uint16;
            description "MT Index";
        } // END of id definition.

    } // END of isis-level-lspdb-tlv-ipv6-multi-reach-state definition.
    grouping isis-level-lspdb-tlv-ipv4-multi-reach-state {
        description
            "State items for ISIS Level LSPDB TLV IPv4 Multi Reach";
        leaf prefix  {
            type  inet:ipv4-address;
            description "Prefix";
        } // END of prefix definition.

        leaf metric  {
            type  uint32 {
                 range "1..16777215"  {
                    description "1..16777215: Supported range 1 - 16777215";
                 }
            }
            description "Metric Value";
        } // END of metric definition.

        leaf id  {
            type  uint16;
            description "MT Index";
        } // END of id definition.

    } // END of isis-level-lspdb-tlv-ipv4-multi-reach-state definition.
    grouping isis-level-lspdb-tlv-router-cap-state {
        description
            "State items for ISIS Level LSPDB TLV Router Capability";
        leaf router-id  {
            type  inet:ipv4-address;
            description "Router ID";
        } // END of router-id definition.

    } // END of isis-level-lspdb-tlv-router-cap-state definition.
    grouping isis-level-lspdb-tlv-router-cap-stlv-state {
        description
            "State items for ISIS Level LSPDB TLV Router Capability STLV";
        leaf stlv-index  {
            type  uint16;
            description "Index";
        } // END of stlv-index definition.

    } // END of isis-level-lspdb-tlv-router-cap-stlv-state definition.
    grouping isis-level-lspdb-tlv-router-cap-stlv-sr-cap-state {
        description
            "State items for ISIS Level LSPDB TLV Router Capability STLV SR
                        Capability";
        leaf range  {
            type  uint32;
            description "Range";
        } // END of range definition.

        leaf sid  {
            type  uint32;
            description "System ID";
        } // END of sid definition.

    } // END of isis-level-lspdb-tlv-router-cap-stlv-sr-cap-state definition.
    grouping isis-level-lspdb-tlv-router-cap-stlv-srv6-cap-state {
        description
            "State items for ISIS Level LSPDB TLV Router Capability STLV SRv6
                        Capability";
        leaf srv6-flags  {
            type  uint32;
            description "srv6 flags to denote SRv6 capability of the node";
        } // END of srv6-flags definition.

    } // END of isis-level-lspdb-tlv-router-cap-stlv-srv6-cap-state definition.
    grouping isis-level-lspdb-tlv-router-cap-stlv-max-sid-depth {
        description
            "State items for ISIS Level LSPDB TLV Router Capability STLV Max SID
                        Depth";
        leaf segments-left  {
            type  uint32;
            description "The Maximum Segments Left MSD Type specifies the maximum value of the
                        SL field [I-D.ietf-6man-segment-routing-header] in the SRH of a
                        received packet before applying the Endpoint behavior associated with
                        a SID";
        } // END of segments-left definition.

        leaf end-pop  {
            type  uint32;
            description "The Maximum End Pop MSD Type specifies the maximum number of SIDs in
                        the SRH to which the router can apply PSP or USP behavior, as defined
                        in flavors.";
        } // END of end-pop definition.

        leaf h-encaps  {
            type  uint32;
            description "The Maximum H.Encaps MSD Type specifies the maximum number of SIDs
                        that can be included as part of the H.Encaps behavior as defined in
                        SRH Max H.encaps Type: 44";
        } // END of h-encaps definition.

        leaf decap-sids  {
            type  uint32;
            description "The Maximum End D MSD Type specifies the maximum number of SIDs in an
                        SRH when performing decapsulation associated with End.Dx behaviors
                        (End.DX6 and End.DT6) as defined in SRH Max End D Type: 45";
        } // END of decap-sids definition.

    } // END of isis-level-lspdb-tlv-router-cap-stlv-max-sid-depth definition.
    grouping isis-level-lspdb-tlv-srv6-locator-state {
        description
            "State items for SRv6 Locator State";
        leaf locator-algorithm  {
            type  uint32;
            description "Associated algorithm. Algorithm values are defined in the IGP
                        Algorithm Type registry.";
        } // END of locator-algorithm definition.

        leaf locator-flag  {
            type  uint32;
            description "SRv6 Locator Flag which contains the info about 'D' flag and other
                        reserved info. Route-leaking decision to be taken based on 'D' flag.
                        This is to prevent looping";
        } // END of locator-flag definition.

        leaf locator-metric  {
            type  uint32;
            description "Metric value of SRv6 Locator";
        } // END of locator-metric definition.

        leaf locator-prefix  {
            type  cml-data-types:cml_ipv6_prefix_t;
            description "SRv6 Locator Prefix";
        } // END of locator-prefix definition.

    } // END of isis-level-lspdb-tlv-srv6-locator-state definition.
    grouping isis-level-lspdb-tlv-srv6-locator-stlv-state {
        description
            "State items for ISIS Level LSPDB TLV SRv6 Locator STLV";
        leaf stlv-index  {
            type  uint16;
            description "Sub TLV Index";
        } // END of stlv-index definition.

        leaf stlv-endpoint-function  {
            type  uint16;
            description "SRv6 EndPoint Function";
        } // END of stlv-endpoint-function definition.

    } // END of isis-level-lspdb-tlv-srv6-locator-stlv-state definition.
    grouping isis-level-lspdb-tlv-srv6-locator-sid-entries {
        description
            "State items for SRv6 Locator SID Entries";
        leaf end-sid  {
            type  inet:ipv6-address;
            description "end Segment Identier Ipv6 address";
        } // END of end-sid definition.

        leaf sid-flags  {
            type  uint32;
            description "No flags are currently defined.  All bits are reserved for future use.
                        They MUST be set to zero on transmission and MUST be ignored on
                        receipt.";
        } // END of sid-flags definition.

        leaf end-point-behavior  {
            type  string {
                length "1..1965";
                pattern "[^?' =,>|]+";
            }
            description "end-point-behavior associated with a SID instance";
        } // END of end-point-behavior definition.

    } // END of isis-level-lspdb-tlv-srv6-locator-sid-entries definition.
    grouping isis-level-lspdb-tlv-router-cap-stlv-sr-algo-state {
        description
            "State items for ISIS Level LSPDB TLV Router Capability STLV SR
                        Algorithm";
        leaf-list sr-algorithm-vector  {
            type  ipi-isis-types:isis_sr_algo_choice_t;
            description "Segment Routing Algorithms to calculate reachability to other nodes.";
        } // END of sr-algorithm-vector definition.

    } // END of isis-level-lspdb-tlv-router-cap-stlv-sr-algo-state definition.
    grouping isis-level-lspdb-tlv-router-cap-stlv-srms-preference-state {
        description
            "State items for ISIS Level LSPDB TLV Router Capability STLV SRMS
                        Preference";
        leaf preference  {
            type  uint32;
            description "preference of the segment-routing mapping server. It ranges
                        from 1 to 255. Default value is 128";
        } // END of preference definition.

    } // END of isis-level-lspdb-tlv-router-cap-stlv-srms-preference-state definition.
    grouping isis-level-proto-vertex-state {
        description
            "State items for ISIS Level IPv4 Protocol Vertex";
        leaf metric  {
            type  uint32;
            description "Vertex Metric";
        } // END of metric definition.

        leaf destination-system-id  {
            type  string {
                length "1..1965";
                pattern "[^?' =,>|]+";
            }
            description "Nexthop neighbor source ID";
        } // END of destination-system-id definition.

    } // END of isis-level-proto-vertex-state definition.
    grouping isis-level-proto-vertex-nexthop-state {
        description
            "State items for ISIS Level IPv4 Protocol Vertex";
        leaf nexthop-interface  {
            type  string {
                length "1..1965";
                pattern "[^?' =,>|]+";
            }
            description "Nexthop interface index";
        } // END of nexthop-interface definition.

        leaf nexthop-system-id  {
            type  string {
                length "1..1965";
                pattern "[^?' =,>|]+";
            }
            description "Nexthop neighbor source ID";
        } // END of nexthop-system-id definition.

        leaf snpa-mac-address  {
            type  cml-data-types:cml_mac_addr_t {
                length "1..1965";
            }
            description "SNPA MAC Address";
        } // END of snpa-mac-address definition.

    } // END of isis-level-proto-vertex-nexthop-state definition.

    grouping  spf-levels-grouping {
    description
        "Enclosing container for the list of spf-levels associated";
    container spf-levels {
        if-feature feature-list:HAVE_ISISD;
        description
            "Enclosing container for the list of spf-levels associated";

        list spf-level {
        // when " ipi-isis-lsp:spf-levels/spf-level/spf-delays/spf-delay/spf-min-delay ";
            key "level";
            description
                "This objectlist defines the ISIS Level SPF Parameters";
            leaf level  {
                type  leafref {
                    path  "../config/level";
                }
                description "IS-IS instance level,(1|2|1-2)";
            } // END of level definition.

            container spf-delays {
                description
                    "Enclosing container for ISIS SPF Parameters";

                list spf-delay {
                    key "spf-min-delay spf-max-delay";
                    max-elements 1;
                    description
                        "This objectlist defines the ISIS SPF Parameters";
                    leaf spf-min-delay  {
                        type  leafref {
                            path  "../config/spf-min-delay";
                        }
                        description "Minimum delay between receiving a change to SPF calculation in
                                    milliseconds. The default value is 500";
                    } // END of spf-min-delay definition.

                    leaf spf-max-delay  {
                        type  leafref {
                            path  "../config/spf-max-delay";
                        }
                        description "Maximum delay between receiving a change to SPF calculation in
                                    milliseconds. The default value is 5000";
                    } // END of spf-max-delay definition.

                    container config {
                        description
                            "This container defines the ISIS SPF Configurations";
                        uses isis-spf-config;
                    } // END of config-container definition.
                    container state {
                        config false;
                        description
                            "This container defines the ISIS SPF state information";
                        uses isis-spf-config;
                    } // END of state-container definition.
                } // End of spf-delay-list
            } // END of spf-delays-container definition.
            container config {
                description
                    "This container defines the ISIS SPF config parameters";
                uses isis-spf-level-config;
            } // END of config-container definition.
            container state {
                config false;
                description
                    "This container defines the ISIS SPF state parameters";
                uses isis-spf-level-config;
            } // END of state-container definition.
        } // End of spf-level-list
    } // END of spf-levels-container definition.
    } // END of spf-levels-grouping definition.

    grouping  levels-grouping {
    description
        "Enclosing container for the list of levels associated";
    container levels {
        if-feature feature-list:HAVE_ISISD;
        description
            "Enclosing container for the list of levels associated";

        list level {
            key "type";
            description
                "This objectlist defines the ISIS Level Parameters";
            leaf type  {
                type  leafref {
                    path  "../config/type";
                }
                description "IS-IS instance level,(1|2|3)";
            } // END of type definition.

            container config {
                description
                    "This container defines the ISIS Level Configurations";
                uses isis-level-config;
            } // END of config-container definition.
            container state {
                config false;
                description
                    "This container defines the ISIS Level State";
                uses isis-level-config;
            } // END of state-container definition.
            container authentication {
                description
                    "Configutational and state parameters for ISIS instance level
                            authentication";
                container config {
                    presence "authentication mode is needed for keychain";
                    description
                        "Configutational parameters for ISIS authentication";
                    uses isis-authentication-config;
                } // END of config-container definition.
                container state {
                    config false;
                    description
                        "State parameters for ISIS interface level authentication";
                    uses isis-authentication-config;
                } // END of state-container definition.
            } // END of authentication-container definition.
        } // End of level-list
    } // END of levels-container definition.
    } // END of levels-grouping definition.


}
