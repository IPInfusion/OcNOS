/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-isis-global-flxalg.yang
*
*/

submodule ipi-isis-global-flxalg {

    yang-version 1.1;

    belongs-to  ipi-isis { prefix ipi-isis; }

    organization
        "IP Infusion Inc.";

    contact
        "Address: 3965 Freedom Circle, Suite 200, Santa Clara, CA 95054
         Phone: +1 408-400-1900
         E-mail: support@ipinfusion.com
         Web: http://www.ipinfusion.com/";

    description
        "Model for managing IS-IS Flexible Algorithm specific global parameters";


    revision "2024-10-23" {
        description "Added hidden-cli tag for flex-algo clis";
        reference " 0.1.2.";
    }

    revision "2024-03-27" {
        description "Updated flex-algo global parameters";
        reference " 0.1.1.";
    }

    revision "2024-03-06" {
        description "Moved all Flexible Algorithm related ISIS per-instance parameters into seperate XML files";
        reference " 0.1.0.";
    }

    grouping isis-global-flexalgo-config {
        description
            "Global Configuration items for ISIS";
        leaf disable-asla-usage-flex-algo  {
            type  empty;
            description "Use this attribute to configure the policy of ASLA Link attributes
                        usage in ASLA Sub-TLV (RFC-8919) for Flexible Algorithm. ISIS uses
                        ASLA Link attributes by default. The command with no keyword enables
                        this usage.";
        } // END of disable-asla-usage-flex-algo definition.

        leaf disable-asla-strict-flex-algo  {
            type  empty;
            description "Use this attribute to configure the policy of strict ASLA Link
                        attributes usage for Flexible Algorithm path calculations. ISIS uses
                        ASLA Link attributes by default, may also use legacy TE Link
                        attributes. The command with no keyword enables this usage.";
        } // END of disable-asla-strict-flex-algo definition.

        leaf disable-flex-algo-usage  {
            type  empty;
            description "Use this attribute to enable/disable usage of Flexible Algorithm in
                        LSP TX/RX and CSPF path calculations";
        } // END of disable-flex-algo-usage definition.

    } // END of isis-global-flexalgo-config definition.
    grouping isis-global-flexalgo-cmds {
        description
            "ISIS Flexible Algorithm specific Global configuration commands";
    } // END of isis-global-flexalgo-cmds definition.


}
