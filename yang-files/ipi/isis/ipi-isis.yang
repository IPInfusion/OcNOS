/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-isis.yang
*
*/

module ipi-isis {

    yang-version 1.1;

    namespace   "http://www.ipinfusion.com/yang/ocnos/ipi-isis";

    prefix "ipi-isis";

    import cml-data-types {
        prefix cml-data-types;
        revision-date 2026-05-15;
    }

    import ipi-vrf {
        prefix ipi-vrf;
        revision-date 2026-08-12;
    }

    import ipi-network-instance {
        prefix ipi-network-instance;
        revision-date 2026-08-12;
    }

    import ipi-isis-types {
        prefix ipi-isis-types;
        revision-date 2025-12-05;
    }

    import ietf-inet-types {
        prefix inet;
        revision-date 2013-07-15;
    }

    import ipi-interface {
        prefix ipi-interface;
        revision-date 2026-03-10;
    }

    import feature-list {
        prefix feature-list;
        revision-date 2026-09-15;
    }

    include ipi-isis-cspf { revision-date 2025-09-01;}
    include ipi-isis-extended { revision-date 2026-05-22;}
    include ipi-isis-fad { revision-date 2025-09-17;}
    include ipi-isis-interface { revision-date 2025-09-06;}
    include ipi-isis-lsp { revision-date 2025-10-24;}
    include ipi-isis-sr { revision-date 2025-10-24;}
    include ipi-isis-lsp-flxalg { revision-date 2024-04-22;}
    include ipi-isis-interface-flxalg { revision-date 2026-02-04;}
    organization
        "IP Infusion Inc.";

    contact
        "Address: 3965 Freedom Circle, Suite 200, Santa Clara, CA 95054
         Phone: +1 408-400-1900
         E-mail: support@ipinfusion.com
         Web: http://www.ipinfusion.com/";

    description
        "Model for managing IS-IS Instance";


    revision "2026-05-22" {
        description "Enabling automatic isisd restart after GR";
        reference " 1.1.1.";
    }

    revision "2026-02-04" {
        description "Added leafref for Interface Flex-Algo admin group attributes";
        reference " 1.1.0.";
    }

    revision "2025-12-05" {
        description "Added default values for ISIS-FRR tie-break command's";
        reference " 1.0.12.";
    }

    revision "2025-11-27" {
        description "Corrected help text in LFA Protection menu";
        reference " 1.0.11.";
    }

    revision "2025-11-07" {
        description "Added install-condition tag to skip the FRR option on a specific DC board";
        reference " 1.0.09.";
    }

    revision "2025-11-03" {
        description "Corrected the help-string for ISIS-FRR tie-break command's 'node-protecting' option";
        reference " 1.0.08.";
    }

    revision "2025-10-24" {
        description "Updated attr name from protocol-distance to protocol-metric and dropped srv6-ms";
        reference " 1.0.07.";
    }

    revision "2025-10-16" {
        description "Changed Datatype of tunnel-lsp-endpoint";
        reference " 1.0.06.";
    }

    revision "2025-09-26" {
        description "ISIS TE-global counters clear command";
        reference " 1.0.05.";
    }

    revision "2025-09-18" {
        description "Corrected SRLG Minimum Value";
        reference " 1.0.04.";
    }

    revision "2025-09-17" {
        description "Added Distance command with system-id and access-list for ipv6";
        reference " 1.0.03.";
    }

    revision "2025-09-15" {
        description "Change of metric-style cli structure from container to objectlist";
        reference " 1.0.10.";
    }

    revision "2025-09-08" {
        description "Updated compiler flag/if-feature for micro-loop-avoidance";
        reference " 1.0.02.";
    }

    revision "2025-09-06" {
        description "TI-LFA SRLG-protection state addition dependency";
        reference " 1.0.01.";
    }

    revision "2025-09-04" {
        description "Removed EVPN_IRB_IF_MODE while configuring IRB interface";
        reference " 0.14.04.";
    }

    revision "2025-09-01" {
        description "Chaning datatype of lsp-reop-time and next-reop-due-in";
        reference " 0.14.03.";
    }

    revision "2025-08-11" {
        description "Updated the range for metric";
        reference " 0.14.02.";
    }

    revision "2025-08-08" {
        description "Added new attributes lsp-name, include-all-mask, lsp-reoptimize, lsp-in-reop-list, lsp-reop-time and next-reop-due-in to isis-cspf-lsp-state group";
        reference " 0.14.1.";
    }

    revision "2025-06-10" {
        description "Flex-Algo ASLA TE-Metric Max Value changes dependency";
        reference " 0.14.00.";
    }

    revision "2025-06-05" {
        description "Added a new objectlist to display SRLB range information";
        reference " 0.13.50.";
    }

    revision "2025-06-02" {
        description "Changed the Datatype of nexthop-ip";
        reference " 0.13.51.";
    }

    revision "2025-05-31" {
        description "ISIS Interface and global ASLA params change";
        reference " 0.13.49.";
    }

    revision "2025-05-28" {
        description "Remove if-feature from isis-microloop-avoidance-sr-protocols-config";
        reference " 0.13.48.";
    }

    revision "2025-04-30" {
        description "Micro-loop/sr-micro-loop configs are made mutually exclusive";
        reference " 0.13.47.";
    }

    revision "2025-04-23" {
        description "Updated element position for micro-loop-avoidance";
        reference " 0.13.46.";
    }

    revision "2025-03-30" {
        description "Added micro-loop avoidance data-model changes";
        reference " 0.13.45.";
    }

    revision "2025-03-28" {
        description "Changed display string for flexalgo clis";
        reference " 0.13.44.";
    }

    revision "2025-02-20" {
        description "ISIS authentication help string changed";
        reference " 0.13.43.";
    }

    revision "2025-02-04" {
        description "Changed Inteface Flex-Algo ASLA SRLG params to hidden";
        reference " 0.13.42.";
    }

    revision "2025-01-16" {
        description "Added cli-set-sequence for distance command";
        reference " 0.13.41.";
    }

    revision "2024-12-31" {
        description "Added Flex-Algo (FAD) readvertise capability commands";
        reference " 0.13.38.";
    }

    revision "2024-12-30" {
        description "Changed cli command for flex-algo-cspf, asla-usage-flex-algo ";
        reference " 0.13.40.";
    }

    revision "2024-12-28" {
        description "Added cli command for advertise and particpate";
        reference " 0.13.39.";
    }

    revision "2024-12-26" {
        description "Unsupported commands of Flex-Algo made hidden";
        reference " 0.13.37.";
    }

    revision "2024-12-22" {
        description "Updated revisions since included file ipi-isis-type was updated";
        reference " 0.13.36.";
    }

    revision "2024-12-11" {
        description "Changed unsupported global Flex-Algo Set/Unset commands to hidden";
        reference " 0.13.35.";
    }

    revision "2024-12-08" {
        description "Update Flex-Algo FAD definitions in FAD XML file";
        reference " 0.13.34.";
    }

    revision "2024-11-08" {
        description "Removed protocol-topology cli";
        reference " 0.13.33.";
    }

    revision "2024-10-22" {
        description "Added yaml file for IS-IS to support streaming telemetry.";
        reference " 0.13.32.";
    }

    revision "2024-09-20" {
        description "Added flag for when tag with HAVE_SRLG";
        reference " 0.13.31.";
    }

    revision "2024-09-12" {
        description "Updated Flex-Algo ASLA Interface parameters XML file";
        reference " 0.13.30.";
    }

    revision "2024-09-06" {
        description "Updated since dependency included Flex-Algo FAD XML data-model changed";
        reference " 0.13.29.";
    }

    revision "2024-09-05" {
        description "Updated if-feature for datatype ISIS_REDISTRIBUTE_T";
        reference " 0.13.28.";
    }

    revision "2024-08-26" {
        description "Made changes to commit in user given order";
        reference " 0.13.27.";
    }

    revision "2024-08-10" {
        description "Updated for included XML dependency of Flex-Algo FAD container changes";
        reference " 0.13.27.";
    }

    revision "2024-07-10" {
        description "Implicit delete tag added wrt fast-reroute";
        reference " 0.13.25.";
    }

    revision "2024-07-05" {
        description "Updated included Flex-Algo containers";
        reference " 0.13.24.";
    }

    revision "2024-07-03" {
        description "Added when tag for metric-style under Multi-topology";
        reference " 0.13.23.";
    }

    revision "2024-06-25" {
        description "Interface delay normalization params updated";
        reference " 0.13.22.";
    }

    revision "2024-06-14" {
        description "Added attributes required for IS-IS SR ECMP";
        reference " 0.13.26.";
    }

    revision "2024-06-04" {
        description "Dependent Flex-Algo data-model XML files updated";
        reference " 0.13.21.";
    }

    revision "2024-05-25" {
        description "Change of metric-style cli structure from objectlist to container";
        reference " 0.13.20.";
    }

    revision "2024-05-17" {
        description "MT ipv6 reachability tlv";
        reference " 0.13.19.";
    }

    revision "2024-05-12" {
        description "Added implicit delete tag wrt fast-reroute";
        reference " 0.13.18.";
    }

    revision "2024-05-10" {
        description "Removed interlevel-external from isis_supress_t datatype";
        reference " 0.13.17.";
    }

    revision "2024-05-07" {
        description "Added Microloop avoidance container objects in FAD's XML";
        reference " 0.13.16.";
    }

    revision "2024-04-24" {
        description "Remove old Segment Routing entropy CLI";
        reference " 0.13.15.";
    }

    revision "2024-04-22" {
        description "Commented out ISIS-LSP-Flex-Algo state containers usage for now";
        reference " 0.13.14.";
    }

    revision "2024-04-17" {
        description "Added Get API header file name for generation";
        reference " 0.13.13.";
    }

    revision "2024-04-15" {
        description "Added custom error code in SR XML file for non-configured SRGB deletion attempts";
        reference " 0.13.12.";
    }

    revision "2024-04-12" {
        description "Changed domain-password to domain password";
        reference " 0.13.11.";
    }

    revision "2024-04-10" {
        description "Removed unused imports from Interface Flex-Algo XML files";
        reference " 0.13.10.";
    }

    revision "2024-03-30" {
        description "Moved back Flex-Algo call backs to this file's callbacks Yaml files";
        reference " 0.13.9.";
    }

    revision "2024-03-27" {
        description "Updated Flexible-Algorithm objects data-model XML file";
        reference " 0.13.8.";
    }

    revision "2024-03-22" {
        description "Added when tag for area-password and domain-password container";
        reference " 0.13.7.";
    }

    revision "2024-03-13" {
        description "Update Segment Routing and entropy CLI dependency";
        reference " 0.13.6.";
    }

    revision "2024-03-09" {
        description "Moved all Flexible Algorithm related callbacks into a seperate yaml files";
        reference " 0.13.5.";
    }

    revision "2024-03-06" {
        description "Moved all Flexible Algorithm related data models into seperate XML files";
        reference " 0.13.4.";
    }

    revision "2024-02-09" {
        description "Updated MT IS Reachability with SRV6 attributes";
        reference " 0.13.3.";
    }

    revision "2024-02-02" {
        description "Updated the MT type bit position values";
        reference " 0.13.2.";
    }

    revision "2024-01-24" {
        description "Updated ISIS Flexible Algorithm Data Model";
        reference " 0.13.1.";
    }

    revision "2023-11-03" {
        description "Added when tag for multi-topology wrt metric style";
        reference " 0.12.12.";
    }

    revision "2023-10-18" {
        description "Added dependent object tag for metric style at mpls te";
        reference " 0.12.11.";
    }

    revision "2023-10-07" {
        description "Linking Segment Routing and entropy capabilty";
        reference " 0.12.11.";
    }

    revision "2023-09-30" {
        description "Included ISIS Flexible Algorithm Data Model";
        reference " 0.13.0.";
    }

    revision "2023-09-13" {
        description "Cspf flag change for debug isis spf-trace command";
        reference " 0.12.10.";
    }

    revision "2023-09-01" {
        description "Updated confirmation string for isis-restart-graceful";
        reference " 0.12.9.";
    }

    revision "2023-08-31" {
        description "Added SNMP Context Name functionality";
        reference " 0.12.8.";
    }

    revision "2023-08-28" {
        description "Added Segment Routing Capability Entropy";
        reference " 0.12.7.";
    }

    revision "2023-08-10" {
        description "JIRA-61800:Added remaining enclosing containers";
        reference " 0.12.6.";
    }

    revision "2023-08-09" {
        description "Added Segment Routing capability entropy";
        reference " 0.12.6.";
    }

    revision "2023-08-04" {
        description "Added desc for attr isisSRv6enable,container state,removal and addition of cliprependstr accordingly";
        reference " 0.12.5.";
    }

    revision "2023-08-02" {
        description "ISIS CLI Commands for EVPN IRB Interface";
        reference " 0.12.4.";
    }

    revision "2023-07-28" {
        description "OCFEAT-536:Updated flag for frr 'when' tag";
        reference " 0.12.3.";
    }

    revision "2023-07-11" {
        description "Added attributes for grouping adjacency-state.";
        reference " 0.12.2.";
    }

    revision "2023-06-29" {
        description "JIRA-61800:Added enclosing containers";
        reference " 0.12.1.";
    }

    revision "2023-06-16" {
        description "ISIS-LSP-MAX-WAIT-DEFAULT-VALUE-CHANGE";
        reference " 0.12.0.";
    }

    revision "2023-05-09" {
        description "Change in MPLS TE hierarchy";
        reference " 0.11.9.";
    }

    revision "2023-05-02" {
        description "JIRA-67560: standardize isis redistribute-level-2-1 for v4 and v6";
        reference " 0.11.8.";
    }

    revision "2023-04-25" {
        description "Added dependency for is-type and mpls te";
        reference " 0.11.7.";
    }

    revision "2023-04-21" {
        description "JIRA-67560: standardize isis redistribute-level for v4 and v6";
        reference " 0.11.6.";
    }

    revision "2023-02-26" {
        description "Added When tag for no-debug-all command";
        reference " 0.11.5.";
    }

    revision "2023-02-14" {
        description "Update if-feature for ISIS Microloop Avoidance";
        reference " 0.11.4.";
    }

    revision "2023-01-18" {
        description "Datamodel changes for ISIS Microloop Avoidance";
        reference " 0.11.3.";
    }

    revision "2023-01-12" {
        description "Updated input for RDN attrs";
        reference " 0.11.2.";
    }

    revision "2022-11-25" {
        description "ISIS-LSP-MTU-RANGE-CHANGE-FIX";
        reference " 0.11.1.";
    }

    revision "2022-10-22" {
        description "Updation of SRGB default value";
        reference " 0.11.0.";
    }

    revision "2022-08-10" {
        description "Debug hierarchy change";
        reference " 0.10.3.";
    }

    revision "2022-08-03" {
        description "Stop using inet:ipv4-prefix and inet:ipv6-prefix due to Cisco NSO iterop";
        reference " 0.10.2.";
    }

    revision "2022-08-02" {
        description "Updation of SRGB starting range value";
        reference " 0.10.1.";
    }

    revision "2022-07-30" {
        description "Updated when expressions in submodule yang";
        reference " 0.10.0.";
    }

    revision "2022-07-19" {
        description "Update if-feature for Notification";
        reference " 0.9.2.";
    }

    revision "2022-06-13" {
        description "Update attribute name of ISIS-TILFA";
        reference " 0.9.1.";
    }

    revision "2022-06-01" {
        description "Updated the yang file with feature";
        reference " 0.9.0.";
    }

    revision "2022-04-27" {
        description "Get Api related changes in ISIS TILFA";
        reference " 0.8.0.";
    }

    revision "2022-04-20" {
        description "SID Label Binding TLV attribute changed as per RFC 8667";
        reference " 0.7.1.";
    }

    revision "2022-04-04" {
        description "Added if-feature whereever needed";
        reference " 0.7.0.";
    }

    revision "2022-02-20" {
        description "Datamodel changes for authentication issue, OCFEAT-276";
        reference " 0.6.0.";
    }

    revision "2022-02-14" {
        description "SRv6 GET API related Changes in ISIS LSP";
        reference " 0.6.";
    }

    revision "2022-02-07" {
        description "Datamodel change for isis ol-bit on-startup and net commands";
        reference " 0.6.1.";
    }

    revision "2021-12-07" {
        description "Datamodel change for debug isis cspf command";
        reference " 0.5.1.";
    }

    revision "2021-09-08" {
        description "Datamodel change for passive-interface command";
        reference " 0.5.0.";
    }

    revision "2021-09-03" {
        description "Update descriptions of attribute";
        reference " 0.5.0.";
    }

    revision "2021-08-16" {
        description "ISIS-TE Metric Extension's GET API support";
        reference " 0.4.0.";
    }

    revision "2021-01-11" {
        description " 1.JIRA-42469:changed redistribute-level-1-2 and redistribute-level-2-1 as objectlist with
                        enable as RDN
                        2.JIRA-42382:redistribute config is not retained after system upgrade from SP3.0.135 build to SP4.1.188 Nebula branch
        ";
        reference " 0.3.0.";
    }

    revision "2020-12-15" {
        description "Change to have data-types in lower case instead of camel case";
        reference " 0.2.0.";
    }

    revision "2020-05-06" {
        description "Datamodel restructuring";
        reference " 0.1.0.";
    }

    grouping isis-notif-state {
        description
            "State items for ISIS notification";
        leaf lsp-identifier  {
            type  leafref {
                path  "/ipi-isis:isis/ipi-isis:isis-instances/ipi-isis:isis-instance/ipi-isis:level-runtime/ipi-isis:lspdb/ipi-isis:state/ipi-isis:lsp-identifier";
            }
            config false;
            description "LSP ID";
        } // END of lsp-identifier definition.

        leaf overload  {
            type  leafref {
                path  "/isis/isis-instances/isis-instance/state/overload";
            }
            config false;
            description "New overload state of the IS-IS instance";
        } // END of overload definition.

        leaf pdu-length  {
            type  leafref {
                path  "/ipi-isis:isis/ipi-isis:isis-instances/ipi-isis:isis-instance/ipi-isis:level-runtime/ipi-isis:lspdb/ipi-isis:state/ipi-isis:pdu-length";
            }
            config false;
            description "Size of the LSP PDU";
        } // END of pdu-length definition.

        leaf raw-pdu  {
            type  string {
                length "1..1965";
            }
            config false;
            description "Received raw PDU";
        } // END of raw-pdu definition.

        leaf pdu-field-len  {
            type  uint8;
            config false;
            description "Size of the ID length in the received PDU";
        } // END of pdu-field-len definition.

        leaf max-area-addresses  {
            type  uint8;
            config false;
            description "Received number of supported areas";
        } // END of max-area-addresses definition.

        leaf protocol-version  {
            type  uint8;
            config false;
            description "Protocol version received in the PDU";
        } // END of protocol-version definition.

        leaf reason  {
            type  string {
                length "1..1965";
                pattern "[^?' =,>|]+";
            }
            config false;
            description "string describing the reason";
        } // END of reason definition.

        leaf protocols  {
            type  uint8;
            config false;
            description "List of protocols supported by the remote system";
        } // END of protocols definition.

        leaf error-offset  {
            type  uint32;
            config false;
            description "If the problem is a malformed TLV, the error-offset points to the
                        start of the TLV. If the problem is with the LSP header, the
                        error-offset points to the errant byte";
        } // END of error-offset definition.

        leaf tlv-type  {
            type  uint8;
            config false;
            description "If the problem is a malformed TLV, the tlv-type is set to the type
                        value of the suspicious TLV. Otherwise, this leaf is not presen";
        } // END of tlv-type definition.

        leaf global-block-base  {
            if-feature feature-list:HAVE_ISIS_SR;
            type  int32;
            config false;
            description "Start ID";
        } // END of global-block-base definition.

        leaf global-block-range  {
            if-feature feature-list:HAVE_ISIS_SR;
            type  int32;
            config false;
            description "End ID";
        } // END of global-block-range definition.

        leaf received-index  {
            if-feature feature-list:HAVE_ISIS_SR;
            type  uint32;
            config false;
            description "Index";
        } // END of received-index definition.

        leaf routing-protocol  {
            if-feature feature-list:HAVE_ISIS_SR;
            type  string {
                length "1..1965";
                pattern "[^?' =,>|]+";
            }
            config false;
            description "Module Name";
        } // END of routing-protocol definition.

    } // END of isis-notif-state definition.
    grouping isis-global-config {
        description
            "Global Configuration items for ISIS";
        leaf instance  {
            type  string {
                length "1..1965";
                pattern "[^?' =,>|]+";
            }
            description "Use this attribute to initiate an ISIS routing instance.Configure at
                        least one NET to start routing.";
        } // END of instance definition.

        leaf distance  {
            type  uint8 {
                 range "1..255"  {
                    description "1..255: Supported range 1 - 255";
                 }
            }
            default "115";
            description "Use this attribute to set the administrative distance for all IPv4
                        routes.";
        } // END of distance definition.

        leaf vrf-name  {
            type  leafref {
                path  "/ipi-network-instance:network-instances/ipi-network-instance:network-instance/ipi-vrf:vrf/ipi-vrf:config/ipi-vrf:vrf-name";
            }
            mandatory true;
            description "VRF Name to associate with this instance";
        } // END of vrf-name definition.

        leaf dynamic-host-name  {
            type  ipi-isis-types:isis_dynamic_hostanme_t;
            default "dynamic-hostname";
            description "Use this attribute to configure the hostname to be advertised for an
                        ISIS instance using the dynamic hostname exchange mechanism (RFC 2763)
                        and system-ID-to-hostname translation.This command configures a
                        hostname to be used for the Dynamic Hostname Exchange Mechanism and
                        System-ID tohostname translation. Use the routing area tag as the
                        hostname, not the router.s global hostname";
        } // END of dynamic-host-name definition.

        leaf disable-adjacency-check  {
            type  empty;
            description "Use this attribute to configure the policy of adjacency based on the
                        protocol related TLVs in the ISIS Hello packet. ISIS checks adjacency
                        with protocol related TLVs including Protocols Supported TLV or IP
                        Interface Address TLV by default. The command with no parameter
                        disables this check.";
        } // END of disable-adjacency-check definition.

        leaf disable-asla-usage-flex-algo  {
            type  empty;
            description "Use this attribute to configure the policy of ASLA Link attributes
                        usage in ASLA Sub-TLV (RFC-8919) for Flexible Algorithm. ISIS uses
                        ASLA Link attributes by default, i.e. does not use legacy link
                        attributes. The command with no keyword disables Flex-Algo ASLA usage,
                        i.e. enables advertisement of legacy bit in ASLA. Command without no
                        keyword enables ASLA Flex-Algo advertisement, i.e. disables legacy bit
                        in ASLA sub-tlv.";
        } // END of disable-asla-usage-flex-algo definition.

        leaf enable-asla-strict-flex-algo  {
            type  empty;
            description "Use this attribute to configure the policy of strict ASLA Link
                        attributes usage for Flexible Algorithm path calculations. ISIS uses
                        ASLA Link attributes by default, may also use legacy TE Link
                        attributes. The command with no keyword disables this usage.";
        } // END of enable-asla-strict-flex-algo definition.

        leaf enable-asla-usage-all-apps  {
            type  empty;
            description "Use this attribute to configure the policy of ASLA Link attributes
                        usage for all applications for path calculations. ISIS does not use
                        ASLA Link attributes for all applications by default. The command with
                        no keyword disables this usage.";
        } // END of enable-asla-usage-all-apps definition.

        leaf enable-flex-algo-routing  {
            type  empty;
            description "Use this attribute to enable/disable routing of Flexible Algorithm in
                        LSP TX/RX and CSPF path calculations";
        } // END of enable-flex-algo-routing definition.

        leaf enable-flex-algo-readvertise  {
            type  empty;
            description "Use this attribute to enable/disable readvertisement of Flexible
                        Algorithm (FAD) from ISIS Level-2 to Level-1 routing area";
        } // END of enable-flex-algo-readvertise definition.

        leaf disable-flex-algo-cspf  {
            type  empty;
            description "Use this attribute to enable/disable CPSF constrained routing of
                        Flexible Algorithm in SPF path calculations";
        } // END of disable-flex-algo-cspf definition.

        leaf enable-flex-algo-adjacency-sid  {
            type  empty;
            description "Use this attribute to enable/disable Flexible Algorithm specific
                        Adjacency-SID support";
        } // END of enable-flex-algo-adjacency-sid definition.

        leaf enable-flex-algo-strict-adjacency-sid  {
            type  empty;
            description "Use this attribute to enable/disable Flexible Algorithm specific
                        strict Adjacency-SID support";
        } // END of enable-flex-algo-strict-adjacency-sid definition.

        leaf enable-flex-algo-backup-adjacency-sid  {
            type  empty;
            description "Use this attribute to enable/disable Flexible Algorithm specific
                        backup Adjacency-SID support";
        } // END of enable-flex-algo-backup-adjacency-sid definition.

        leaf enable-flex-algo-qos-policy  {
            type  empty;
            description "Use this attribute to enable/disable Flexible Algorithm specific QoS
                        policy support";
        } // END of enable-flex-algo-qos-policy definition.

        leaf enable-flex-algo-bgp-ls  {
            type  empty;
            description "Use this attribute to enable/disable advertisement of Flexible
                        Algorithm TLV(s)/Sub-TLV(s) in BGP Link-state packets";
        } // END of enable-flex-algo-bgp-ls definition.

        leaf enable-backup-srlg-disjoint-path  {
            type  empty;
            description "Use this attribute to enable/disable default algorithm's SRLG-disjoint
                        backup path calculation";
        } // END of enable-backup-srlg-disjoint-path definition.

        leaf enable-backup-srlg-disjoint-forced  {
            type  empty;
            description "Use this attribute to enable/disable default algorithm's forced
                        SRLG-disjoint backup path calculation";
        } // END of enable-backup-srlg-disjoint-forced definition.

        leaf ignore-lsp-errors  {
            type  empty;
            description "Use this attribute to ignore LSPs with checksum errors. By default,
                        ISIS validates checksum for LSP whenever it receives LSPs and if the
                        checksum has an error, the LSP will be dropped. Configuring this
                        command to ignore the LSP checksum error and treat it as if checksum
                        is passed.";
        } // END of ignore-lsp-errors definition.

        leaf lfa-hold-timer  {
            if-feature feature-list:HAVE_ISIS_LFA;
            type  int32 {
                 range "100..100000"  {
                    description "100..100000: Supported range 100 - 100000";
                 }
            }
            default "1000";
            description "LFA terminate-hold-on interval";
        } // END of lfa-hold-timer definition.

        leaf level-capability  {
            type  ipi-isis-types:isis_is_type_t;
            default "level-1-2";
            description "Use this attribute to set the IS to the specified level of
                        routing.Changing is-type brings down, then brings up a particular
                        level of routing. There is a limitation: Only one ISIS instance can
                        run Level-2 routing (either Level-2 only IS, or Level-1-2 IS)";
        } // END of level-capability definition.

        leaf authentication-send-only  {
            type  ipi-isis-types:isis_auth_level_type_t;
            default "level-1-2";
            description "Use this attribute to set the send-only option at the instance
                        level.Use this command before configuring the authentication mode and
                        authentication key-chain, so that the implementation of authentication
                        goes smoothly. That is, the routers will have more time for the keys
                        to be configured on each router if authentication is inserted only on
                        the packets being sent, not checked on packets being received. After
                        all routers that must communicate are configured with this command,
                        enable the authentication mode and key chain on each router.";
        } // END of authentication-send-only definition.

        leaf incremental-spf-levels  {
            type  ipi-isis-types:isis_is_type_t;
            default "level-1-2";
            description "Use this attribute to enable incremental SPF for a routing process";
        } // END of incremental-spf-levels definition.

        leaf priority-tag  {
            if-feature feature-list:HAVE_WIDE_METRIC;
            type  uint32 {
                 range "1..4294967295"  {
                    description "1..4294967295: Supported range 1 - 4294967295";
                 }
            }
            description "Use this attribute to set a high priority tag value";
        } // END of priority-tag definition.

        leaf enable-cspf-capability  {
            when " /ipi-isis:isis/ipi-isis:isis-instances/ipi-isis:isis-instance/ipi-isis:mpls-traffic-engg/ipi-isis:config/ipi-isis:enable-level-1 or /ipi-isis:isis/ipi-isis:isis-instances/ipi-isis:isis-instance/ipi-isis:mpls-traffic-engg/ipi-isis:config/ipi-isis:enable-level-2 ";
            if-feature feature-list:HAVE_ISIS_CSPF;
            type  empty;
            description "Use this attribute to enable the constrained shortest path first
                        (CSPF) feature in the ISIS module. CSPF calculates            optimum
                        explicit route (ER), using Traffic Engineering Database and (TED) and
                        pre-existing Label Switched Path (LSP). The resulting ER is used by a
                        signaling protocol (RSVP-TE) to set up LSPs.";
        } // END of enable-cspf-capability definition.

        leaf disable-gr-capability  {
            if-feature feature-list:HAVE_RESTART;
            type  empty;
            description "Use this attribute to enable the GR";
        } // END of disable-gr-capability definition.

        leaf enable-bfd-all-interfaces  {
            if-feature feature-list:HAVE_BFD;
            type  empty;
            description "Use this attribute to enable the Bidirectional Forwarding Detection
                        (BFD) feature on the interfaces enabled with this              ISIS
                        instance. This command sets BFD fall-over check for all the neighbors
                        under specified process.";
        } // END of enable-bfd-all-interfaces definition.

        leaf maximum-area-addresses  {
            type  uint8 {
                 range "3..254"  {
                    description "3..254: Supported range 3 - 254";
                 }
            }
            default "3";
            description "Use this attribute to set the maximum number of ISIS areas that can be
                        configured on this router with the net command. By default, ISIS
                        permits a maximum of three areas that can be defined on a router.";
        } // END of maximum-area-addresses definition.

        leaf distribute-bgp-ls  {
            if-feature feature-list:HAVE_BGP_LS;
            type  ipi-isis-types:isis_bgp_ls_type_t;
            description "Use this attribute to distribute linkstate and TE Database to BGP";
        } // END of distribute-bgp-ls definition.

        leaf context-name  {
            if-feature feature-list:HAVE_SNMP;
            type  string {
                length "1..32";
                pattern "[^?' =,>|]+";
            }
            description "Use this attribute to set the SNMP context name for ISIS instance.";
        } // END of context-name definition.

    } // END of isis-global-config definition.
    grouping isis-net-config {
        description
            "Configure NET for ISIS instance";
        leaf-list net  {
            type  string {
                length "1..1965";
                pattern "[^?' =,>|]+";
            }
            description "Use this attribute to add a Network Entity Title (NET) for the
                        instance.On a router running ISIS, a NET can be 8 to 20 bytes in
                        length. The last byte is always the n-selector, and must be zero. The
                        n-selector indicates no transport entity, and means that the packet is
                        for the routing software of the system. The six bytes directly
                        preceding the n-selector are the system ID. The system ID length is a
                        fixed size and cannot be changed. The system ID must be unique
                        throughout each area (Level 1) and throughout the backbone (Level 2).
                        The bytes preceding the system ID are the area ID, which can be from 1
                        - 13 bytes in length. By default, a maximum of three NETs per router
                        are allowed with a different area ID but the system ID should be the
                        same for all NETs. You can increase the number of area IDs per system
                        ID with the max-area-address command.";
        } // END of net definition.

    } // END of isis-net-config definition.
    grouping isis-mpls-traffic-engg-top {
        description
            "Top level container for ISIS MPLS Traffic Engineering";
        container mpls-traffic-engg {
            description
                "ISIS MPLS Traffic Engg";
            container config {
                description
                    "Configuration Data For ISIS MPLS Traffic Engg";
                uses isis-mpls-traffic-engg-level-config;
            } // END of config-container definition.
            container state {
                config false;
                description
                    "This Container Defines The ISIS MPLS Traffic Engg.";
                uses isis-mpls-traffic-engg-level-config;
            } // END of state-container definition.
        } // END of mpls-traffic-engg-container definition.
    } // END of isis-mpls-traffic-engg-top definition.
    grouping isis-mpls-traffic-engg-level-config {
        description
            "Configuration items for ISIS MPLS Traffic Engineering";
        leaf enable-level-1  {
            when " /ipi-isis:isis/ipi-isis:isis-instances/ipi-isis:isis-instance/ipi-isis:metric/ipi-isis:config/ipi-isis:style and /ipi-isis:isis/ipi-isis:isis-instances/ipi-isis:isis-instance/ipi-isis:metric/ipi-isis:config/ipi-isis:style = 'wide' and /ipi-isis:isis/ipi-isis:isis-instances/ipi-isis:isis-instance/ipi-isis:metric/ipi-isis:config/ipi-isis:level-number != 'level-2' and /ipi-isis:isis/ipi-isis:isis-instances/ipi-isis:isis-instance/ipi-isis:config/ipi-isis:level-capability != 'level-2-only' ";
            if-feature feature-list:HAVE_ISIS_TE;
            type  empty;
            description "Use this attribute to configure MPLS Traffic Engineering feature for
                        ISIS.";
        } // END of enable-level-1 definition.

        leaf enable-level-2  {
            when " /ipi-isis:isis/ipi-isis:isis-instances/ipi-isis:isis-instance/ipi-isis:metric/ipi-isis:config/ipi-isis:style and /ipi-isis:isis/ipi-isis:isis-instances/ipi-isis:isis-instance/ipi-isis:metric/ipi-isis:config/ipi-isis:style = 'wide' and /ipi-isis:isis/ipi-isis:isis-instances/ipi-isis:isis-instance/ipi-isis:metric/ipi-isis:config/ipi-isis:level-number != 'level-1' and /ipi-isis:isis/ipi-isis:isis-instances/ipi-isis:isis-instance/ipi-isis:config/ipi-isis:level-capability != 'level-1' ";
            if-feature feature-list:HAVE_ISIS_TE;
            type  empty;
            description "Use this attribute to configure MPLS Traffic Engineering feature for
                        ISIS.";
        } // END of enable-level-2 definition.

    } // END of isis-mpls-traffic-engg-level-config definition.
    grouping isis-global-state {
        description
            "Global State items for ISIS";
        leaf next-global-update-level-1  {
            type  uint32;
            description "Time remaining for next global update";
        } // END of next-global-update-level-1 definition.

        leaf next-global-update-level-2  {
            type  uint32;
            description "Time remaining for next global update";
        } // END of next-global-update-level-2 definition.

        leaf overload  {
            type  ipi-isis-types:isis_overload_state_t;
            description "New overload state of the IS-IS instance";
        } // END of overload definition.

    } // END of isis-global-state definition.
    grouping isis-adjacency-counter-state {
        description
            "State items for ISIS Adjacency Counters";
        leaf system-level-1-adjacency-count  {
            type  uint32;
            description "System level 1 adjacency count";
        } // END of system-level-1-adjacency-count definition.

        leaf system-level-2-adjacency-count  {
            type  uint32;
            description "System level 2 adjacency count";
        } // END of system-level-2-adjacency-count definition.

        leaf system-total-adjacency-count  {
            type  uint32;
            description "System total adjacency count";
        } // END of system-total-adjacency-count definition.

    } // END of isis-adjacency-counter-state definition.
    grouping isis-igp-shortcut-lsp-state {
        description
            "State items for ISIS IGP Shortcut";
        leaf index  {
            type  uint32;
            description "Index";
        } // END of index definition.

        leaf metric  {
            type  uint16;
            description "Metric Value";
        } // END of metric definition.

        leaf tunnel-id  {
            type  uint32;
            description "Tunnel ID";
        } // END of tunnel-id definition.

        leaf tunnel-endpoint  {
            type  string {
                length "1..1965";
                pattern "[^?' =,>|]+";
            }
            description "Tunnel Endpoint";
        } // END of tunnel-endpoint definition.

        leaf lock  {
            type  uint16;
            description "Lock";
        } // END of lock definition.

        leaf status  {
            type  ipi-isis-types:isis_igp_shortcut_lsp_status_t;
            description "Status";
        } // END of status definition.

    } // END of isis-igp-shortcut-lsp-state definition.
    grouping isis-prc-config {
        description
            "Configuration items for ISIS PRC";
        leaf minimum-delay  {
            type  uint32 {
                 range "0..2147483647"  {
                    description "0..2147483647: Supported range 0 - 2147483647";
                 }
            }
            description "Minimum delay between receiving a change to PRC calculation in
                        milliseconds.Default value is 500";
        } // END of minimum-delay definition.

        leaf maximum-delay  {
            type  uint32 {
                 range "0..2147483647"  {
                    description "0..2147483647: Supported range 0 - 2147483647";
                 }
            }
            description "Maximum delay between receiving a change to PRC calculation in
                        milliseconds.Default value is 50000";
        } // END of maximum-delay definition.

    } // END of isis-prc-config definition.
    grouping isis-area-auth-config {
        description
            "Configuration items for ISIS Area Authentication";
        leaf area-password  {
            type  string {
                length "1..1965";
                pattern "[^?' =,>|]+";
            }
            mandatory true;
            description "Use this attribute to set the authentication password for the Level-1
                        area and to set authentication on Level-1 SNP PDUs. This command
                        enables authentication when receiving and sending LSP and SNP PDU in
                        Level-1 areas. Area password must be the same for all the ISIS routers
                        in the same area";
        } // END of area-password definition.

        leaf sequence-number-packet  {
            // when " ipi-isis:isis/isis-instances/isis-instance/area-authentication/config/area-password ";
            type  ipi-isis-types:isis_snp_t;
            description "Use this attribute to set the authentication password for the Level-1
                        area and to set authentication on Level-1 SNP PDUs. This command
                        enables authentication when receiving and sending LSP and SNP PDU in
                        Level-1 areas. Area password must be the same for all the ISIS routers
                        in the same area";
        } // END of sequence-number-packet definition.

    } // END of isis-area-auth-config definition.
    grouping isis-domain-auth-config {
        description
            "Configuration items for ISIS Domain Authentication";
        leaf domain-password  {
            type  string {
                length "1..1965";
                pattern "[^?' =,>|]+";
            }
            mandatory true;
            description "Use this attribute to set the authentication password for the Level-2
                        domain, and optionally, the authentication password on Level-2 SNP
                        PDUs.Configuring this command to enable authentication when receiving
                        and sending LSP and SNP PDU in Level-2 domain. Domain password must be
                        the same in Level-2 domain.";
        } // END of domain-password definition.

        leaf domain-snp  {
            // when " ipi-isis:isis/isis-instances/isis-instance/domain-authentication/config/domain-password ";
            type  ipi-isis-types:isis_snp_t;
            description "Use this attribute to set the authentication password for the Level-2
                        domain, and optionally, the authentication password on Level-2 SNP
                        PDUs.Configuring this command to enable authentication when receiving
                        and sending LSP and SNP PDU in Level-2 domain. Domain password must be
                        the same in Level-2 domain.";
        } // END of domain-snp definition.

    } // END of isis-domain-auth-config definition.
    grouping isis-passive-interface-top {
        description
            "Grouping for ISIS passive interface";
        container passive-interfaces {
            description
                "ISIS passive interfaces";
            container config {
                description
                    "Configuration data for ISIS passive interface all";
                uses isis-passive-interface-all-config;
            } // END of config-container definition.
            container state {
                config false;
                description
                    "Operational state data for ISIS passive interface all";
                uses isis-passive-interface-all-config;
            } // END of state-container definition.
            uses isis-passive-interface-name-top;
            uses isis-disable-passive-interface-name-top;
        } // END of passive-interfaces-container definition.
    } // END of isis-passive-interface-top definition.
    grouping isis-microloop-avoidance-sr-protocols-config {
        description
            "configuration items for microloop-avoidance";
        leaf protocol  {
            type  ipi-isis-types:isis_level_proto_t;
            description "Protocol Address Family";
        } // END of protocol definition.

        leaf fib-delay  {
            type  uint32 {
                 range "100..300000"  {
                    description "100..300000: Supported range 100 - 300000";
                 }
            }
            default "1500";
            description "Fib-delay";
        } // END of fib-delay definition.

    } // END of isis-microloop-avoidance-sr-protocols-config definition.
    grouping isis-microloop-avoidance-sr-protocols-top {
        description
            "Description";
        container protocols {
            if-feature feature-list:HAVE_ISIS_SR;
            if-feature feature-list:HAVE_ISIS_LFA_OR_HAVE_ISIS_TI_LFA;
            description
                "This container defines the Protocol Address Family Information";

            list protocol {
                key "protocol";
                description
                    "Protocol Address Family Information";
                leaf protocol  {
                    type  leafref {
                        path  "../config/protocol";
                    }
                    description "Protocol Address Family";
                } // END of protocol definition.

                container config {
                    description
                        "This container defines the ISIS Microloop-avoidances Segemnt-Routing
                                Configurations";
                    uses isis-microloop-avoidance-sr-protocols-config;
                } // END of config-container definition.
                container state {
                    config false;
                    description
                        "This container defines the ISIS Microloop Avoidance State";
                    uses isis-microloop-avoidance-sr-protocols-config;
                } // END of state-container definition.
            } // End of protocol-list
        } // END of protocols-container definition.
    } // END of isis-microloop-avoidance-sr-protocols-top definition.
    grouping isis-microloop-avoidance-params-sr-config {
        description
            "configuration items for microloop-avoidance";
        leaf level-type  {
            type  ipi-isis-types:isis_level2_t;
            description "IS-IS instance level,(1|2)";
        } // END of level-type definition.

    } // END of isis-microloop-avoidance-params-sr-config definition.
    grouping isis-microloop-avoidance-sr-top {
        description
            "Description";
        container microloop-avoidance-segment-routing {
            // when " not(/ipi-isis:isis/ipi-isis:isis-instances/ipi-isis:isis-instance/ipi-isis:microloop-avoidances/ipi-isis:microloop-avoidance/ipi-isis:config/ipi-isis:enable) ";
            if-feature feature-list:HAVE_ISIS_SR;
            if-feature feature-list:HAVE_ISIS_LFA_OR_HAVE_ISIS_TI_LFA;
            description
                "This container defines the ISIS Microloop Avoidance segment-routing";

            list segment-routing {
            // when " ipi-isis:isis/isis-instances/isis-instance/microloop-avoidance-segment-routing/segment-routing/protocols/protocol/config ";
                key "level-type";
                description
                    "This objectlist defines the microloop-avoidance segment-routing";
                leaf level-type  {
                    type  leafref {
                        path  "../config/level-type";
                    }
                    description "IS-IS instance level,(1|2)";
                } // END of level-type definition.

                container config {
                    description
                        "This container defines the ISIS Microloop Avoidance SR configurations";
                    uses isis-microloop-avoidance-params-sr-config;
                } // END of config-container definition.
                container state {
                    config false;
                    description
                        "This container defines the ISIS Microloop Avoidance SR State";
                    uses isis-microloop-avoidance-params-sr-config;
                } // END of state-container definition.
                uses isis-microloop-avoidance-sr-protocols-top;
            } // End of segment-routing-list
        } // END of microloop-avoidance-segment-routing-container definition.
    } // END of isis-microloop-avoidance-sr-top definition.
    grouping isis-microloop-avoidance-top {
        description
            "Grouping for ISIS Microloop Avoidance";
        container microloop-avoidances {
            if-feature feature-list:HAVE_ISIS_LFA_OR_HAVE_ISIS_TI_LFA;
            description
                "This container defines the ISIS Microloop Avoidance";

            list microloop-avoidance {
            // when " ipi-isis:isis/isis-instances/isis-instance/microloop-avoidances/microloop-avoidance/config/enable ";
                key "level-type";
                description
                    "This objectlist defines the ISIS Microloop Avoidance";
                leaf level-type  {
                    type  leafref {
                        path  "../config/level-type";
                    }
                    description "IS-IS instance level,(1|2)";
                } // END of level-type definition.

                container config {
                    description
                        "This container defines the ISIS Microloop Avoidance configurations";
                    uses isis-microloop-avoidance-params-config;
                } // END of config-container definition.
                container state {
                    config false;
                    description
                        "This container defines the ISIS Microloop Avoidance State";
                    uses isis-microloop-avoidance-params-config;
                } // END of state-container definition.
            } // End of microloop-avoidance-list
        } // END of microloop-avoidances-container definition.
        uses isis-microloop-avoidance-sr-top;
    } // END of isis-microloop-avoidance-top definition.
    grouping isis-microloop-avoidance-params-config {
        description
            "configuration items for microloop-avoidance";
        leaf hold-timer  {
            type  uint8 {
                 range "1..60"  {
                    description "1..60: Supported range 1 - 60";
                 }
            }
            description "Time that a router waits to acquire a set of LSPs to process together";
        } // END of hold-timer definition.

        leaf max-fib  {
            type  uint8 {
                 range "1..60"  {
                    description "1..60: Supported range 1 - 60";
                 }
            }
            description "Maximum time required to update a FIB irrespective of the change";
        } // END of max-fib definition.

        leaf level-type  {
            type  ipi-isis-types:isis_level2_t;
            description "IS-IS instance level,(1|2)";
        } // END of level-type definition.

        leaf enable  {
            type  empty;
            description "Microloop avoidance";
        } // END of enable definition.

    } // END of isis-microloop-avoidance-params-config definition.
    grouping isis-passive-interface-name-top {
        description
            "Grouping for isis passive interface name";

        list passive-interface {
            key "name";
            description
                "List of ISIS passive interfaces";
            leaf name  {
                type  leafref {
                    path  "../config/name";
                }
                description "Use this attribute to set interface as passive.";
            } // END of name definition.

            container config {
                description
                    "Configuration data for ISIS passive interface";
                uses isis-passive-interface-name-config;
            } // END of config-container definition.
            container state {
                config false;
                description
                    "Operational state data for ISIS passive interface state";
                uses isis-passive-interface-name-config;
            } // END of state-container definition.
        } // End of passive-interface-list
    } // END of isis-passive-interface-name-top definition.
    grouping isis-passive-interface-name-config {
        description
            "Grouping for ISIS passive interface configuration data";
        leaf name  {
            type  leafref {
                path  "/ipi-interface:interfaces/ipi-interface:interface/ipi-interface:name";
            }
            description "Use this attribute to set interface as passive.";
        } // END of name definition.

    } // END of isis-passive-interface-name-config definition.
    grouping isis-disable-passive-interface-name-top {
        description
            "Grouping for disabled isis passive interface name";
        container disable-passive-interfaces {
            description
                "Enclosing container for the list of passive-interfaces disabled";

            list disable-passive-interface {
                key "name";
                description
                    "List of ISIS passive interfaces disabled";
                leaf name  {
                    type  leafref {
                        path  "../config/name";
                    }
                    description "Use this attribute to set interface as passive.";
                } // END of name definition.

                container config {
                    description
                        "Configuration data for ISIS passive interface disable";
                    uses isis-disable-passive-interface-name-config;
                } // END of config-container definition.
                container state {
                    config false;
                    description
                        "Operational state data for ISIS passive interface disable state";
                    uses isis-disable-passive-interface-name-config;
                } // END of state-container definition.
            } // End of disable-passive-interface-list
        } // END of disable-passive-interfaces-container definition.
    } // END of isis-disable-passive-interface-name-top definition.
    grouping isis-disable-passive-interface-name-config {
        description
            "Grouping for ISIS disable passive interface configuration data";
        leaf name  {
            type  leafref {
                path  "/ipi-interface:interfaces/ipi-interface:interface/ipi-interface:name";
            }
            description "Use this attribute to disbale passive interface.";
        } // END of name definition.

    } // END of isis-disable-passive-interface-name-config definition.
    grouping isis-metric-config {
        description
            "Configuration items for ISIS Metric";
        leaf style  {
            // when " ipi-isis:isis/isis-instances/isis-instance/metric/config/level-number ";
            if-feature feature-list:HAVE_WIDE_METRIC;
            type  ipi-isis-types:isis_metric_style_t;
            description "Use this attribute to configure the ISIS metric style";
        } // END of style definition.

        leaf level-number  {
            // when " ipi-isis:isis/isis-instances/isis-instance/metric/config/style ";
            if-feature feature-list:HAVE_WIDE_METRIC;
            type  ipi-isis-types:isis_level3_t;
            description "Use this attribute to configure the ISIS metric style";
        } // END of level-number definition.

    } // END of isis-metric-config definition.
    grouping isis-area-addr-state {
        description
            "State items for ISIS Metric";
        leaf-list address  {
            type  string {
                length "1..1965";
                pattern "[^?' =,>|]+";
            }
            description "Manual Area Addresses";
        } // END of address definition.

    } // END of isis-area-addr-state definition.
    grouping isis-recv-area-addr-state {
        description
            "State items for ISIS Recv Area Address";
        leaf-list address  {
            type  string {
                length "1..1965";
                pattern "[^?' =,>|]+";
            }
            description "Rcv Area Addresses - other than already in Manual area addr list";
        } // END of address definition.

    } // END of isis-recv-area-addr-state definition.
    grouping isis-lsp-timers-config {
        description
            "Configuration items for ISIS LSP Timers";
        leaf lsp-refresh-interval  {
            type  uint16 {
                 range "1..65535"  {
                    description "1..65535: Supported range 1 - 65535";
                 }
            }
            default "900";
            description "Use this attribute to set the LSP refresh interval.IP Infusion Inc.
                        recommends making the lsp-refresh-interval smaller than
                        max-lsp-lifetime value.";
        } // END of lsp-refresh-interval definition.

        leaf lsp-lifetime-interval  {
            type  uint16 {
                 range "350..65535"  {
                    description "350..65535: Supported range 350 - 65535";
                 }
            }
            default "1200";
            description "Use this attribute to set the maximum LSP lifetime. You must set
                        max-lsp-lifetime greater than lsp-refreshinterval.";
        } // END of lsp-lifetime-interval definition.

    } // END of isis-lsp-timers-config definition.
    grouping isis-te-ipv4-router-id-config {
        description
            "Configuration items for ISIS IPv4 router id";
        leaf ipv4-router-id  {
            if-feature feature-list:HAVE_ISIS_TE;
            type  inet:ipv4-address;
            description "Use this attribute to configure the traffic engineering stable IP
                        address for a system.";
        } // END of ipv4-router-id definition.

    } // END of isis-te-ipv4-router-id-config definition.
    grouping isis-te-ipv6-router-id-config {
        description
            "Configuration items for ISIS IPv6 router id";
        leaf ipv6-router-id  {
            if-feature feature-list:HAVE_ISIS_TE;
            if-feature feature-list:HAVE_IPV6;
            type  inet:ipv6-address;
            description "Use this attribute to configure the traffic engineering stable IPv6
                        address for a system.";
        } // END of ipv6-router-id definition.

    } // END of isis-te-ipv6-router-id-config definition.
    grouping isis-passive-interface-all-config {
        description
            "Grouping for ISIS passive interface all configuration data";
        leaf passive-interface-all  {
            type  empty;
            description "Use this attribute to set all interfaces as passive.";
        } // END of passive-interface-all definition.

    } // END of isis-passive-interface-all-config definition.
    grouping isis-route-state {
        description
            "State items for ISIS Route";
        leaf destination-prefix  {
            type  cml-data-types:cml_ipv4_addr_prefix_t;
            description "Destination Prefix";
        } // END of destination-prefix definition.

        leaf destination-path-metric  {
            type  uint32;
            description "Destination Path Metric";
        } // END of destination-path-metric definition.

        leaf destination-path-type  {
            type  string {
                length "1..1965";
                pattern "[^?' =,>|]+";
            }
            description "Destination Path Type";
        } // END of destination-path-type definition.

        leaf is-destination-path-type-external  {
            type  boolean;
            description "Destination Path Type External";
        } // END of is-destination-path-type-external definition.

        leaf tunnel-lsp-metric  {
            if-feature feature-list:HAVE_MPLS;
            type  uint32;
            description "Tunnel LSP Metric";
        } // END of tunnel-lsp-metric definition.

        leaf tunnel-lsp-tunnel-identifier  {
            if-feature feature-list:HAVE_MPLS;
            type  uint32;
            description "Tunnel LSP Tunnel Endpoint";
        } // END of tunnel-lsp-tunnel-identifier definition.

        leaf tunnel-lsp-tunnel-endpoint  {
            if-feature feature-list:HAVE_MPLS;
            type  inet:ipv4-address;
            description "Tunnel LSP Tunnel Endpoint";
        } // END of tunnel-lsp-tunnel-endpoint definition.

        leaf ilm-id  {
            if-feature feature-list:HAVE_ISIS_SR;
            type  uint32;
            description "Prefix ILM-ID";
        } // END of ilm-id definition.

        leaf ftn-id  {
            if-feature feature-list:HAVE_ISIS_SR;
            type  uint32;
            description "Prefix FTN-ID";
        } // END of ftn-id definition.

        leaf in-label  {
            if-feature feature-list:HAVE_ISIS_SR;
            type  uint32;
            description "Prefix In-Label";
        } // END of in-label definition.

    } // END of isis-route-state definition.
    grouping isis-route-nh-state {
        description
            "State items for ISIS Next Hop";
        leaf nexthop-ip  {
            type  inet:ipv4-address;
            description "Prefix";
        } // END of nexthop-ip definition.

        leaf outgoing-interface  {
            type  string {
                length "1..1965";
                pattern "[^?' =,>|]+";
            }
            description "Outgoing Port";
        } // END of outgoing-interface definition.

        leaf redistribute-map-tag  {
            type  uint32;
            description "Redist Map Tag";
        } // END of redistribute-map-tag definition.

        leaf source-identifier  {
            type  string {
                length "1..1965";
                pattern "[^?' =,>|]+";
            }
            description "Nexthop neighbor source ID";
        } // END of source-identifier definition.

        leaf out-label  {
            if-feature feature-list:HAVE_ISIS_SR;
            type  uint32;
            description "Nexthop Out-Label";
        } // END of out-label definition.

    } // END of isis-route-nh-state definition.
    grouping isis-ipv6-route-state {
        description
            "State items for ISIS IPv6 Route";
        leaf destination-prefix  {
            type  cml-data-types:cml_ipv6_prefix_t;
            description "Destination Prefix";
        } // END of destination-prefix definition.

        leaf destination-path-metric  {
            type  uint32;
            description "Destination Path Metric";
        } // END of destination-path-metric definition.

        leaf destination-path-type  {
            type  string {
                length "1..1965";
                pattern "[^?' =,>|]+";
            }
            description "Destination Path Type";
        } // END of destination-path-type definition.

        leaf is-destination-path-type-external  {
            type  boolean;
            description "Destination Path Type External";
        } // END of is-destination-path-type-external definition.

    } // END of isis-ipv6-route-state definition.
    grouping isis-ipv6-route-nh-state {
        description
            "State items for ISIS IPv6 Route Next Hop";
        leaf nexthop-ip  {
            type  inet:ipv6-address;
            description "Nexthop Prefix";
        } // END of nexthop-ip definition.

        leaf outgoing-interface  {
            type  string {
                length "1..1965";
                pattern "[^?' =,>|]+";
            }
            description "Outgoing Port";
        } // END of outgoing-interface definition.

        leaf redistribute-map-tag  {
            type  uint32;
            description "Redistribute Map Tag";
        } // END of redistribute-map-tag definition.

    } // END of isis-ipv6-route-nh-state definition.
    grouping isis-af-ipv6-config {
        description
            "Configuration items for ISIS AF IPv6";
        leaf afi-name  {
            type  ipi-isis-types:isis_address_ipv6_t;
            mandatory true;
            description "Use this attribute to configure IPv6 routing specific configuration";
        } // END of afi-name definition.

        leaf administrative-distance  {
            type  uint32 {
                 range "1..255"  {
                    description "1..255: Supported range 1 - 255";
                 }
            }
            default "115";
            description "Use this attribute to set the administrative distance for all IPv6
                        routes";
        } // END of administrative-distance definition.

        leaf disable-adjacency-check  {
            type  empty;
            description "Use this attribute to configure the policy of adjacency based on the
                        protocol related TLVs in the ISIS Hello packet. ISIS checks adjacency
                        with protocol related TLVs including Protocols Supported TLV or IP
                        Interface Address TLV by default. The command with no parameter
                        disables this check.";
        } // END of disable-adjacency-check definition.

    } // END of isis-af-ipv6-config definition.
    grouping isis-af-ipv6-redist-1-2-config {
        description
            "Configuration items for ISIS AF IPv6 Redist level 1 into level 2";
        leaf enable  {
            type  empty;
            description "Use this attribute to redistribute reachability information from one
                        level to the other level. If an distribute-list name is given with
                        this command for an access list that does not exist, the routes are
                        still redistributed.";
        } // END of enable definition.

        leaf level-1-acl  {
            type  string {
                length "1..1965";
                pattern "[^?' =,>|]+";
            }
            description "Use this attribute to redistribute reachability information from one
                        level to the other level. If an distribute-list name is given with
                        this command for an access list that does not exist, the routes are
                        still redistributed.";
        } // END of level-1-acl definition.

    } // END of isis-af-ipv6-redist-1-2-config definition.
    grouping isis-af-ipv6-redist-2-1-config {
        description
            "Configuration items for ISIS AF IPv6 Redist level 2 into level 1";
        leaf enable  {
            type  empty;
            description "Use this attribute to redistribute reachability information from one
                        level to the other level. If an distribute-list name is given with
                        this command for an access list that does not exist, the routes are
                        still redistributed.";
        } // END of enable definition.

        leaf level-2-acl  {
            type  string {
                length "1..1965";
                pattern "[^?' =,>|]+";
            }
            description "Use this attribute to redistribute reachability information from one
                        level to the other level. If an distribute-list name is given with
                        this command for an access list that does not exist, the routes are
                        still redistributed.";
        } // END of level-2-acl definition.

    } // END of isis-af-ipv6-redist-2-1-config definition.
    grouping isis-af-ipv6-default-info-config {
        description
            "Configuration items for ISIS AF Default Info";
        leaf originate  {
            type  ipi-isis-types:isis_origin_type_t;
            description "Use this attribute to set originate reachability information to
                        Default destination into LSP.There is no default information in
                        Level-2 domain by default, while Level-1 router calculates default to
                        L1L2 route during SPF calculation. This command enables to originate
                        default route into Level-2 domain.";
        } // END of originate definition.

        leaf route-map-name  {
            // when " ipi-isis:isis/isis-instances/isis-instance/address-family-ipv6/default-route-informations/default-route-information/config/originate ";
            type  string {
                length "0..1965";
                pattern "[^?' =,>|]*";
            }
            default "";
            description "Route-map Name";
        } // END of route-map-name definition.

    } // END of isis-af-ipv6-default-info-config definition.
    grouping isis-ipv6-proto-redist-config {
        description
            "Configuration items for ISIS Protocol Redist";
        leaf ipv6-protocol-type  {
            type  ipi-isis-types:isis_redistribute_t;
            description "Use this attribute to redistribute routes from another protocol into
                        the ISIS routing table.";
        } // END of ipv6-protocol-type definition.

    } // END of isis-ipv6-proto-redist-config definition.
    grouping isis-ipv6-redist-config {
        description
            "Configuration items for ISIS Redist";
        leaf ipv6-level  {
            type  ipi-isis-types:isis_is_type3_t;
            default "level-2";
            description "Redist level";
        } // END of ipv6-level definition.

        leaf ipv6-metric-value  {
            type  uint32 {
                 range "0..16777215"  {
                    description "0..16777215: Supported range 0 - 16777215";
                 }
            }
            default "0";
            description "Use this attributes to redistribute routes from another protocol into
                        the ISIS routing table. With metric, metric-type, level and route-map
                        options.";
        } // END of ipv6-metric-value definition.

        leaf ipv6-metric-type  {
            type  ipi-isis-types:isis_metric_t;
            default "internal";
            description "Redist metric type";
        } // END of ipv6-metric-type definition.

        leaf ipv6-route-map  {
            type  string {
                length "0..1965";
                pattern "[^?' =,>|]*";
            }
            default "";
            description "Routemap name";
        } // END of ipv6-route-map definition.

    } // END of isis-ipv6-redist-config definition.
    grouping isis-summary-prefix-config {
        description
            "Configuration items for ISIS Summary Prefix";
        leaf prefix  {
            type  cml-data-types:cml_ipv6_prefix_t;
            description "Use this attribute to configure the summary prefix to summarize IPv6
                        reachability information.";
        } // END of prefix definition.

        leaf level  {
            // when " ipi-isis:isis/isis-instances/isis-instance/address-family-ipv6/summary-prefixes/summary-prefix/config/prefix ";
            type  ipi-isis-types:isis_summary_level_t;
            mandatory true;
            description "IS-IS instance level,(1|2|3)";
        } // END of level definition.

        leaf metric  {
            // when " ipi-isis:isis/isis-instances/isis-instance/address-family-ipv6/summary-prefixes/summary-prefix/config/prefix ";
            type  uint8 {
                 range "1..63"  {
                    description "1..63: Supported range 1 - 63";
                 }
            }
            description "Metric value";
        } // END of metric definition.

    } // END of isis-summary-prefix-config definition.
    grouping isis-mt-config {
        description
            "Configuration items for ISIS MT";
        leaf level  {
            type  ipi-isis-types:isis_multi_topology_level_type_t;
            description "Use this attribute to configure the ISIS MT";
        } // END of level definition.

    } // END of isis-mt-config definition.
    grouping isis-srv6-config {
        description
            "config attribute for SRv6 for SR Policies";
        leaf isisSRv6enable  {
            type  empty;
            mandatory true;
            description "enable SRv6 for SR Policies";
        } // END of isisSRv6enable definition.

    } // END of isis-srv6-config definition.
    grouping locator-name-config {
        description
            "config attribute for SRv6 for SR Policies";
        leaf isisSRv6LocatorName  {
            type  string {
                length "1..1965";
                pattern "[^?' =,>|]+";
            }
            description "Locator name";
        } // END of isisSRv6LocatorName definition.

    } // END of locator-name-config definition.
    grouping isis-srv6-locator-lists-config {
        description
            "Locator";
        container locator-lists {
            when " /ipi-isis:isis/ipi-isis:isis-instances/ipi-isis:isis-instance/ipi-isis:address-family-ipv6/ipi-isis:isis-srv6/ipi-isis:config/ipi-isis:isisSRv6enable ";
            description
                "SRv6 Locator List";

            list locator-list {
                key "isisSRv6LocatorName";
                description
                    "Properties of a locator list";
                leaf isisSRv6LocatorName  {
                    type  leafref {
                        path  "../config/isisSRv6LocatorName";
                    }
                    description "Locator name";
                } // END of isisSRv6LocatorName definition.

                container config {
                    description
                        "Config parameters for locator-list configuration";
                    uses locator-name-config;
                } // END of config-container definition.
                container state {
                    config false;
                    description
                        "Operational state data for a locator list";
                    uses locator-name-config;
                } // END of state-container definition.
            } // End of locator-list-list
        } // END of locator-lists-container definition.
    } // END of isis-srv6-locator-lists-config definition.
    grouping isis-distance-ipv4-config {
        description
            "Configuration items for ISIS Distance";
        leaf system-id  {
            type  string {
                length "0..1965";
                pattern "[^?' =,>|]*";
            }
            description "System ID";
        } // END of system-id definition.

        leaf value  {
            type  uint8 {
                 range "1..255"  {
                    description "1..255: Supported range 1 - 255";
                 }
            }
            mandatory true;
            description "Distance Value";
        } // END of value definition.

        leaf access-list-name  {
            // when " ipi-isis:isis/isis-instances/isis-instance/distances/distance/config/value ";
            type  string {
                length "0..1965";
                pattern "[^?' =,>|]*";
            }
            default "";
            description "Use this attribute to set the administrative distance for specific
                        IPv4 routes.";
        } // END of access-list-name definition.

    } // END of isis-distance-ipv4-config definition.
    grouping isis-distance-ipv6-config {
        description
            "Configuration items for ISIS Distance";
        leaf system-id  {
            type  string {
                length "0..1965";
                pattern "[^?' =,>|]*";
            }
            description "System ID";
        } // END of system-id definition.

        leaf value  {
            type  uint8 {
                 range "1..255"  {
                    description "1..255: Supported range 1 - 255";
                 }
            }
            mandatory true;
            description "Distance Value";
        } // END of value definition.

        leaf access-list-name  {
            // when " ipi-isis:isis/isis-instances/isis-instance/address-family-ipv6/distances/distance/config/value ";
            type  string {
                length "0..1965";
                pattern "[^?' =,>|]*";
            }
            default "";
            description "Use this attribute to set the administrative distance for specific
                        IPv6 routes.";
        } // END of access-list-name definition.

    } // END of isis-distance-ipv6-config definition.
    grouping isis-lsp-overload-config {
        description
            "Configuration items for ISIS LSP Overlaod";
        leaf enabled  {
            type  empty;
            mandatory true;
            description "Use this attribute to set the overload-bit in self-LSPs. If the
                        overload-bit is set in LSPs, the router is not used as a transit
                        router during SPF calculation. This configuration causes a router to
                        update its own LSP with the overload bit set and causes the other
                        routers not to use this router as a transit or forwarding router. The
                        router continues to receive LSPs when the overload bit is set. If the
                        on-startup option is specified, the router sets the overload bit only
                        at startup, then clears the bit after the specified interval has
                        elapsed. If the on-startup option is specified using the wait-for-bgp
                        option, the overload bit is setup at startup, then the bit is cleared
                        after the BGP router signals it has finished converging or if the
                        router does not signal it has finished converging in 10 minutes. If
                        there is no BGP process running, the overload bit clears immediately.";
        } // END of enabled definition.

        leaf suppress-type  {
            type  ipi-isis-types:isis_suppress_t;
            description "Use this attributes to set the overload-bit in self-LSPs. If the
                        overload-bit is set in LSPs, the router is not used as a transit
                        router during SPF calculation. This configuration causes a router to
                        update its own LSP with the overload bit set and causes the other
                        routers not to use this router as a transit or forwarding router. The
                        router continues to receive LSPs when the overload bit is set. If the
                        on-startup option is specified, the router sets the overload bit only
                        at startup, then clears the bit after the specified interval has
                        elapsed. If the on-startup option is specified using the wait-for-bgp
                        option, the overload bit is setup at startup, then the bit is cleared
                        after the BGP router signals it has finished converging or if the
                        router does not signal it has finished converging in 10 minutes. If
                        there is no BGP process running, the overload bit clears immediately.";
        } // END of suppress-type definition.

        leaf set-bit-on-boot  {
            type  ipi-isis-types:isis_onstartup_t;
            description "Overload interval after reboot";
        } // END of set-bit-on-boot definition.

    } // END of isis-lsp-overload-config definition.
    grouping isis-af-ipv4-state {
        description
            "State items for ISIS AF IPv4";
        leaf existence-state  {
            type  uint8;
            description "SNMP variable";
        } // END of existence-state definition.

        leaf redistribute-update  {
            type  int32;
            description "Redistrubution timer argument";
        } // END of redistribute-update definition.

        leaf redistribute-timer-value  {
            type  string {
                length "1..1965";
                pattern "[^?' =,>|]+";
            }
            description "Redistribution last performed";
        } // END of redistribute-timer-value definition.

    } // END of isis-af-ipv4-state definition.
    grouping isis-af-ipv4-distribution-level-1-2-config {
        description
            "Configuration items for ISIS AF IPv4 level 1 to 2 Distribution";
        leaf enable  {
            type  empty;
            description "Use this attribute to redistribute reachability information from one
                        level to the other level. If an distribute-list name is given with
                        this command for an access list that does not exist, the routes are
                        still redistributed.";
        } // END of enable definition.

        leaf level-1-acl  {
            type  string {
                length "1..1965";
                pattern "[^?' =,>|]+";
            }
            description "Use this attribute to redistribute reachability information from one
                        level to the other level. If an distribute-list name is given with
                        this command for an access list that does not exist, the routes are
                        still redistributed.";
        } // END of level-1-acl definition.

    } // END of isis-af-ipv4-distribution-level-1-2-config definition.
    grouping isis-af-ipv4-distribution-level-2-1-config {
        description
            "Configuration items for ISIS AF IPv4 level 2 to 1 Distribution";
        leaf enable  {
            type  empty;
            description "Use this attribute to redistribute reachability information from one
                        level to the other level. If an distribute-list name is given with
                        this command for an access list that does not exist, the routes are
                        still redistributed.";
        } // END of enable definition.

        leaf level-2-acl  {
            type  string {
                length "1..1965";
                pattern "[^?' =,>|]+";
            }
            description "Use this attribute to redistribute reachability information from one
                        level to the other level. If an distribute-list name is given with
                        this command for an access list that does not exist, the routes are
                        still redistributed.";
        } // END of level-2-acl definition.

    } // END of isis-af-ipv4-distribution-level-2-1-config definition.
    grouping isis-af-ipv4-default-info-config {
        description
            "Configuration items for ISIS AF IPv4 Default Info";
        leaf originate  {
            type  ipi-isis-types:isis_origin_type_t;
            description "Use this attribute to originate reachability information to Default
                        destination into LSP.There is no default information in Level-2 domain
                        by default, while Level-1 router calculates default to L1L2 route
                        during SPF calculation. This command enables to originate default
                        route into Level-2 domain.";
        } // END of originate definition.

        leaf route-map-name  {
            // when " ipi-isis:isis/isis-instances/isis-instance/address-family-ipv4/default-route-informations/default-route-information/config/originate ";
            type  string {
                length "0..1965";
                pattern "[^?' =,>|]*";
            }
            default "";
            description "Route Map Name Attribute";
        } // END of route-map-name definition.

    } // END of isis-af-ipv4-default-info-config definition.
    grouping isis-af-ipv4-redistribution-config {
        description
            "Configuration items for ISIS AF IPv4 Redistribution";
        leaf protocol-type  {
            type  ipi-isis-types:isis_redistribute_t;
            description "Use this attribute to redistribute routes from another protocol into
                        the ISIS routing table.";
        } // END of protocol-type definition.

    } // END of isis-af-ipv4-redistribution-config definition.
    grouping isis-af-ipv4-redistribution-configurations-config {
        description
            "Configuration items for ISIS AF IPv4 Redistribution Configuration";
        leaf level  {
            type  ipi-isis-types:isis_is_type3_t;
            default "level-2";
            description "Level Redistribution";
        } // END of level definition.

        leaf metric-value  {
            type  uint32 {
                 range "0..16777215"  {
                    description "0..16777215: Supported range 0 - 16777215";
                 }
            }
            default "0";
            description "IS-IS metric";
        } // END of metric-value definition.

        leaf metric-type  {
            type  ipi-isis-types:isis_metric_t;
            default "internal";
            description "External metric type, (Internal|External)";
        } // END of metric-type definition.

        leaf route-map  {
            type  string {
                length "0..1965";
                pattern "[^?' =,>|]*";
            }
            default "";
            description "Name of route-map";
        } // END of route-map definition.

    } // END of isis-af-ipv4-redistribution-configurations-config definition.
    grouping isis-af-ipv4-summary-prefix-config {
        description
            "Configuration items for ISIS AF IPv4 Summary Prefix";
        leaf prefix  {
            type  cml-data-types:cml_ipv4_prefix_t;
            description "Use this attribute to Summary Address to summarize IPv4 reachability
                        information.";
        } // END of prefix definition.

        leaf level  {
            // when " ipi-isis:isis/isis-instances/isis-instance/address-family-ipv4/summary-addresses/summary-address/config/prefix ";
            type  ipi-isis-types:isis_summary_level_t;
            mandatory true;
            description "IS-IS instance level";
        } // END of level definition.

        leaf metric  {
            // when " ipi-isis:isis/isis-instances/isis-instance/address-family-ipv4/summary-addresses/summary-address/config/prefix ";
            type  uint8 {
                 range "1..63"  {
                    description "1..63: Supported range 1 - 63";
                 }
            }
            description "Metric value";
        } // END of metric definition.

    } // END of isis-af-ipv4-summary-prefix-config definition.
    grouping isis-af-ipv4-redist-isis-config {
        description
            "Configuration items for ISIS AF IPv4 Redist ISIS";
        leaf id  {
            type  string {
                length "1..1965";
                pattern "[^?' =,>|]+";
            }
            description "Instance ID";
        } // END of id definition.

    } // END of isis-af-ipv4-redist-isis-config definition.
    grouping isis-conf-mode-debug-config {
        description
            "Debug flags for configuration";
        leaf options  {
            type  ipi-isis-types:isis_debug_t;
            description "Debug Configuration Flag";
        } // END of options definition.

        leaf enable-hello  {
            type  empty;
            description "Use this attribute to turn on debugging for ISIS hello.";
        } // END of enable-hello definition.

        leaf-list interface-hello  {
            type  string {
                length "1..1965";
                pattern "[^?' =,>|]+";
            }
            description "Use this attribute to turn on debugging for ISIS Interface hello";
        } // END of interface-hello definition.

        leaf-list system-id-hello  {
            type  string {
                length "1..1965";
                pattern "[^?' =,>|]+";
            }
            description "Use this attribute to turn on debugging for ISIS SID hello";
        } // END of system-id-hello definition.

        leaf cspf  {
            if-feature feature-list:HAVE_ISIS_CSPF;
            type  ipi-isis-types:isis_cspf_debug_t;
            description "Use this attribute to enable CSPF debug logs.";
        } // END of cspf definition.

    } // END of isis-conf-mode-debug-config definition.
    grouping isis-terminal-mode-debug-state {
        description
            "Operational debug information for terminal mode";
        container terminal-debug {
            config false;
            description
                "Runtime attributes for terminal debug";
            leaf terminal-debug-status  {
                type  ipi-isis-types:isis_debug_t;
                description "Debug Terminal Flag";
            } // END of terminal-debug-status definition.

            leaf terminal-debug-status-hello  {
                type  cml-data-types:cml_on_off_t;
                description "Use this attribute to turn on debugging for ISIS hello.";
            } // END of terminal-debug-status-hello definition.

            leaf-list terminal-debug-status-interface-hello  {
                type  string {
                    length "1..1965";
                    pattern "[^?' =,>|]+";
                }
                description "Use this attribute to turn on debugging for ISIS Interface hello";
            } // END of terminal-debug-status-interface-hello definition.

            leaf-list terminal-debug-status-system-id-hello  {
                type  string {
                    length "1..1965";
                    pattern "[^?' =,>|]+";
                }
                description "Use this attribute to turn on debugging for ISIS SID hello";
            } // END of terminal-debug-status-system-id-hello definition.

            leaf terminal-debug-status-cspf  {
                if-feature feature-list:HAVE_ISIS_CSPF;
                type  ipi-isis-types:isis_cspf_debug_t;
                description "Use this attribute to enable CSPF debug logs.";
            } // END of terminal-debug-status-cspf definition.

        } // END of terminal-debug-container definition.
    } // END of isis-terminal-mode-debug-state definition.

    grouping  isis-grouping {
    description
        "IS-IS master for instance wide configurations";
    container isis {
        if-feature feature-list:HAVE_ISISD;
        description
            "IS-IS master for instance wide configurations";
        container isis-instances {
            description
                "Enclosing container for the list of instance wide configurations";

            list isis-instance {
            // when " ipi-isis:isis/isis-instances/isis-instance/config/vrf-name ";
                key "instance";

                ordered-by user;
                description
                    "IS-IS structure";
                leaf instance  {
                    type  leafref {
                        path  "../config/instance";
                    }
                    description "Use this attribute to initiate an ISIS routing instance.Configure at
                                least one NET to start routing.";
                } // END of instance definition.


                list ipv4-route {
                    key "destination-prefix";
                    config false;
                    description
                        "This container defines the ISIS Route";
                    leaf destination-prefix  {
                        type  leafref {
                            path  "../state/destination-prefix";
                        }
                        description "Destination Prefix";
                    } // END of destination-prefix definition.


                    list nexthop {
                        key "nexthop-ip";
                        config false;
                        description
                            "This container defines the ISIS Route Next Hop";
                        leaf nexthop-ip  {
                            type  leafref {
                                path  "../state/nexthop-ip";
                            }
                            description "Prefix";
                        } // END of nexthop-ip definition.

                        container state {
                            config false;
                            description
                                "This container defines the ISIS Route Next Hop State";
                            uses isis-route-nh-state;
                        } // END of state-container definition.
                    } // End of nexthop-list
                    container state {
                        config false;
                        description
                            "This container defines the ISIS State";
                        uses isis-route-state;
                    } // END of state-container definition.
                } // End of ipv4-route-list

                list ipv6-route {
                    key "destination-prefix";
                    config false;
                    description
                        "This container defines the ISIS IPv6 Route";
                    leaf destination-prefix  {
                        type  leafref {
                            path  "../state/destination-prefix";
                        }
                        description "Destination Prefix";
                    } // END of destination-prefix definition.


                    list nexthop {
                        key "nexthop-ip";
                        config false;
                        description
                            "This container defines the ISIS IPv6 Route Next Hop";
                        leaf nexthop-ip  {
                            type  leafref {
                                path  "../state/nexthop-ip";
                            }
                            description "Nexthop Prefix";
                        } // END of nexthop-ip definition.

                        container state {
                            config false;
                            description
                                "This container defines the ISIS IPv6 Route Next Hop State";
                            uses isis-ipv6-route-nh-state;
                        } // END of state-container definition.
                    } // End of nexthop-list
                    container state {
                        config false;
                        description
                            "This container defines the ISIS IPv6 State";
                        uses isis-ipv6-route-state;
                    } // END of state-container definition.
                } // End of ipv6-route-list
                container config {
                    description
                        "This container defines the ISIS top configurations.";
                    uses isis-global-config;
                } // END of config-container definition.
                container state {
                    config false;
                    description
                        "This container defines the ISIS top states.";
                    container counters {
                        config false;
                        description
                            "This container defines the ISIS Adjacency Counters";
                        uses isis-adjacency-counter-state;
                    } // END of counters-container definition.
                    uses isis-global-state;
                    uses isis-global-config;
                } // END of state-container definition.
                container vrf {
                    config false;
                    description
                        "This container defines the ISIS VRF";

                    list igp-shortcut-lsp {
                        key "index";
                        config false;
                        description
                            "This objectlist defines the ISIS IGP shortcut LSP";
                        leaf index  {
                            type  leafref {
                                path  "../state/index";
                            }
                            description "Index";
                        } // END of index definition.

                        container state {
                            config false;
                            description
                                "This container defines the ISIS IGP shortcut LSP state";
                            uses isis-igp-shortcut-lsp-state;
                        } // END of state-container definition.
                    } // End of igp-shortcut-lsp-list
                } // END of vrf-container definition.
                container partial-route-computations {
                    description
                        "Enclosing container for the list of partial-route-computations
                                associated";

                    list partial-route-computation {
                        key "minimum-delay maximum-delay";
                        description
                            "This objectlist defines the ISIS PRC";
                        leaf minimum-delay  {
                            type  leafref {
                                path  "../config/minimum-delay";
                            }
                            description "Minimum delay between receiving a change to PRC calculation in
                                        milliseconds.Default value is 500";
                        } // END of minimum-delay definition.

                        leaf maximum-delay  {
                            type  leafref {
                                path  "../config/maximum-delay";
                            }
                            description "Maximum delay between receiving a change to PRC calculation in
                                        milliseconds.Default value is 50000";
                        } // END of maximum-delay definition.

                        container config {
                            description
                                "This container defines the ISIS PRC configurations.";
                            uses isis-prc-config;
                        } // END of config-container definition.
                        container state {
                            config false;
                            description
                                "This container defines the ISIS PRC runtime information.";
                            uses isis-prc-config;
                        } // END of state-container definition.
                    } // End of partial-route-computation-list
                } // END of partial-route-computations-container definition.
                container area-authentication {
                    when " /ipi-isis:isis/ipi-isis:isis-instances/ipi-isis:isis-instance/ipi-isis:config/ipi-isis:level-capability != 'level-2-only' ";
                    description
                        "This container defines the ISIS Area Auth";
                    container config {
                        presence "To configure area-password";
                        description
                            "This container defines the ISIS Area Auth configurations.";
                        uses isis-area-auth-config;
                    } // END of config-container definition.
                    container state {
                        config false;
                        description
                            "This container defines the ISIS Area Auth operational parameters.";
                        uses isis-area-auth-config;
                    } // END of state-container definition.
                } // END of area-authentication-container definition.
                container network-entity-title {
                    description
                        "To configure NET for an ISIS instance";
                    container config {
                        description
                            "This container defines the ISIS NET configuration.";
                        uses isis-net-config;
                    } // END of config-container definition.
                    container state {
                        config false;
                        description
                            "This container defines the ISIS net operational parameter.";
                        uses isis-net-config;
                    } // END of state-container definition.
                } // END of network-entity-title-container definition.
                container domain-authentication {
                    when " /ipi-isis:isis/ipi-isis:isis-instances/ipi-isis:isis-instance/ipi-isis:config/ipi-isis:level-capability != 'level-1' ";
                    description
                        "This container defines the ISIS Domain Auth";
                    container config {
                        presence "To configure domain-password";
                        description
                            "This container defines the ISIS Area Domain configurations.";
                        uses isis-domain-auth-config;
                    } // END of config-container definition.
                    container state {
                        config false;
                        description
                            "This container defines the ISIS Area Domain operational parameters.";
                        uses isis-domain-auth-config;
                    } // END of state-container definition.
                } // END of domain-authentication-container definition.
                container metric {
                    if-feature feature-list:HAVE_WIDE_METRIC;
                    description
                        "This container defines the ISIS Metric";
                    container config {
                        description
                            "This container defines the ISIS Metric configurations.";
                        uses isis-metric-config;
                    } // END of config-container definition.
                    container state {
                        config false;
                        description
                            "This container defines the ISIS Metric Operational parameters.";
                        uses isis-metric-config;
                    } // END of state-container definition.
                } // END of metric-container definition.
                container manual-area-addresses {
                    description
                        "This container defines the ISIS Address Area";
                    container state {
                        config false;
                        description
                            "This container defines the ISIS Address Area state";
                        uses isis-area-addr-state;
                    } // END of state-container definition.
                } // END of manual-area-addresses-container definition.
                container receive-area-addresses {
                    description
                        "This container defines the ISIS Recv Address Area";
                    container state {
                        config false;
                        description
                            "This container defines the ISIS Recv Address Area state";
                        uses isis-recv-area-addr-state;
                    } // END of state-container definition.
                } // END of receive-area-addresses-container definition.
                container timers {
                    description
                        "This container defines the ISIS LSP Timers";
                    container config {
                        description
                            "This container defines the ISIS LSP Timers configurations.";
                        uses isis-lsp-timers-config;
                    } // END of config-container definition.
                    container state {
                        config false;
                        description
                            "This container defines the ISIS LSP Timers Operational parameters.";
                        uses isis-lsp-timers-config;
                    } // END of state-container definition.
                } // END of timers-container definition.
                container traffic-engineering {
                    description
                        "This container defines the ISIS Traffic Engineering";
                    container config {
                        description
                            "This container defines the ISIS TE Router ID configurations.";
                        uses isis-te-ipv4-router-id-config;
                        uses isis-te-ipv6-router-id-config;
                    } // END of config-container definition.
                    container state {
                        config false;
                        description
                            "This container defines the ISIS TE Router ID operational information.";
                        uses isis-te-ipv4-router-id-config;
                        uses isis-te-ipv6-router-id-config;
                    } // END of state-container definition.
                } // END of traffic-engineering-container definition.
                container address-family-ipv6 {
                    // when " ipi-isis:isis/isis-instances/isis-instance/address-family-ipv6/config/afi-name ";
                    description
                        "This container defines the ISIS IPv6 Route";
                    container level-1-into-2-redistributes {
                        description
                            "Enclosing container for redistribute-level-1-into-2 list";

                        list redistribute-level-1-into-2 {
                            key "enable";
                            max-elements 1;
                            description
                                "This objectlist defines isis redistribution from level 1 into level 2";
                            leaf enable  {
                                type  leafref {
                                    path  "../config/enable";
                                }
                                description "Use this attribute to redistribute reachability information from one
                                            level to the other level. If an distribute-list name is given with
                                            this command for an access list that does not exist, the routes are
                                            still redistributed.";
                            } // END of enable definition.

                            container config {
                                description
                                    "This container defines configurations for isis redistribution from
                                            level 1 into level 2";
                                uses isis-af-ipv6-redist-1-2-config;
                            } // END of config-container definition.
                            container state {
                                config false;
                                description
                                    "This container defines operational information for isis redistribution
                                            from level 1 into level 2";
                                uses isis-af-ipv6-redist-1-2-config;
                            } // END of state-container definition.
                        } // End of redistribute-level-1-into-2-list
                    } // END of level-1-into-2-redistributes-container definition.
                    container level-2-into-1-redistributes {
                        description
                            "Enclosing container for redistribute-level-2-into-1 list";

                        list redistribute-level-2-into-1 {
                            key "enable";
                            max-elements 1;
                            description
                                "This objectlist defines isis redistribution from level 2 into level 1";
                            leaf enable  {
                                type  leafref {
                                    path  "../config/enable";
                                }
                                description "Use this attribute to redistribute reachability information from one
                                            level to the other level. If an distribute-list name is given with
                                            this command for an access list that does not exist, the routes are
                                            still redistributed.";
                            } // END of enable definition.

                            container config {
                                description
                                    "This container defines configurations for isis redistribution from
                                            level 2 into level 1";
                                uses isis-af-ipv6-redist-2-1-config;
                            } // END of config-container definition.
                            container state {
                                config false;
                                description
                                    "This container defines operational information for isis redistribution
                                            from level 2 into level 1";
                                uses isis-af-ipv6-redist-2-1-config;
                            } // END of state-container definition.
                        } // End of redistribute-level-2-into-1-list
                    } // END of level-2-into-1-redistributes-container definition.
                    container default-route-informations {
                        description
                            "Enclosing container for the list of default-route-information";

                        list default-route-information {
                            key "originate";
                            max-elements 1;
                            description
                                "This objectlist defines the ISIS Protocol Default Information
                                            Configurations and state information";
                            leaf originate  {
                                type  leafref {
                                    path  "../config/originate";
                                }
                                description "Use this attribute to set originate reachability information to
                                            Default destination
                                            into LSP.There is no default information in Level-2 domain by default,
                                            while Level-1 router calculates default to L1L2 route during SPF
                                            calculation. This command enables to originate default route into
                                            Level-2 domain.";
                            } // END of originate definition.

                            container config {
                                description
                                    "ISIS Protocol Default Information Configurations";
                                uses isis-af-ipv6-default-info-config;
                            } // END of config-container definition.
                            container state {
                                config false;
                                description
                                    "ISIS Protocol Default Information operational information";
                                uses isis-af-ipv6-default-info-config;
                            } // END of state-container definition.
                        } // End of default-route-information-list
                    } // END of default-route-informations-container definition.
                    container config {
                        presence "To enable address family ipv6";
                        description
                            "This container defines the ISIS AF IPv6 configurations";
                        uses isis-af-ipv6-config;
                    } // END of config-container definition.
                    container state {
                        config false;
                        description
                            "This container defines the ISIS AF IPv6 operational information";
                        uses isis-af-ipv6-config;
                    } // END of state-container definition.
                    container redistributions {
                        description
                            "Enclosing container for the redistribution parameters";

                        list redistribute {
                            key "ipv6-protocol-type";
                            description
                                "This objectlist defines the Redistribute List";
                            leaf ipv6-protocol-type  {
                                type  leafref {
                                    path  "../config/ipv6-protocol-type";
                                }
                                description "Use this attribute to redistribute routes from another protocol into
                                            the ISIS routing table.";
                            } // END of ipv6-protocol-type definition.

                            container config {
                                description
                                    "This container defines the ISIS Proto Redistribute Configurations";
                                uses isis-ipv6-proto-redist-config;
                                uses isis-ipv6-redist-config;
                            } // END of config-container definition.
                            container state {
                                config false;
                                description
                                    "This container defines the ISIS Proto Redistribute Operational
                                            information";
                                uses isis-ipv6-proto-redist-config;
                                uses isis-ipv6-redist-config;
                            } // END of state-container definition.
                        } // End of redistribute-list
                    } // END of redistributions-container definition.
                    container summary-prefixes {
                        description
                            "Enclosing container for the list of summary addresses";

                        list summary-prefix {
                            key "prefix";
                            description
                                "This objectlist defines the Summary Prefix List";
                            leaf prefix  {
                                type  leafref {
                                    path  "../config/prefix";
                                }
                                description "Use this attribute to configure the summary prefix to summarize IPv6
                                            reachability information.";
                            } // END of prefix definition.

                            container config {
                                description
                                    "This container defines the ISIS Summary Prefix Configurations";
                                uses isis-summary-prefix-config;
                            } // END of config-container definition.
                            container state {
                                config false;
                                description
                                    "This container defines the ISIS Summary Prefix operational information";
                                uses isis-summary-prefix-config;
                            } // END of state-container definition.
                        } // End of summary-prefix-list
                    } // END of summary-prefixes-container definition.
                    container multi-topologies {
                        description
                            "Enclosing container for Multi-topology";

                        list multi-topology {
                        when " /ipi-isis:isis/ipi-isis:isis-instances/ipi-isis:isis-instance/ipi-isis:metric/ipi-isis:config/ipi-isis:style and /ipi-isis:isis/ipi-isis:isis-instances/ipi-isis:isis-instance/ipi-isis:metric/ipi-isis:config/ipi-isis:style = 'wide' ";
                        // when " ipi-isis:isis/isis-instances/isis-instance/metric/config/level-number ";
                            if-feature feature-list:HAVE_MULTI_TOPOLOGY;
                            key "level";
                            max-elements 1;
                            description
                                "This objectlist defines the Multi-topology";
                            leaf level  {
                                type  leafref {
                                    path  "../config/level";
                                }
                                description "Use this attribute to configure the ISIS Multi-topology";
                            } // END of level definition.

                            container config {
                                description
                                    "This container defines the ISIS Multi topology configurations.";
                                uses isis-mt-config;
                            } // END of config-container definition.
                            container state {
                                config false;
                                description
                                    "This container defines the ISIS Multi topology.";
                                uses isis-mt-config;
                            } // END of state-container definition.
                        } // End of multi-topology-list
                    } // END of multi-topologies-container definition.
                    container isis-srv6 {
                        when " /ipi-isis:isis/ipi-isis:isis-instances/ipi-isis:isis-instance/ipi-isis:address-family-ipv6/ipi-isis:config/ipi-isis:afi-name ";
                        if-feature feature-list:HAVE_SRV6;
                        description
                            "SRv6 container for segment routing";
                        container config {
                            presence "yes";
                            description
                                "Segment routing SRv6 configuration and other CLIs inside srv6";
                            uses isis-srv6-config;
                        } // END of config-container definition.
                        container state {
                            config false;
                            description
                                "Segment routing V6 runtime parameters";
                            uses isis-srv6-config;
                        } // END of state-container definition.
                        uses isis-srv6-locator-lists-config;
                    } // END of isis-srv6-container definition.
                    container distances {
                        if-feature feature-list:HAVE_IPV6;
                        description
                            "Enclosing container for distances";

                        list distance {
                            key "system-id";
                            description
                                "ISIS Distance Attributes";
                            leaf system-id  {
                                type  leafref {
                                    path  "../config/system-id";
                                }
                                description "System ID";
                            } // END of system-id definition.

                            container config {
                                description
                                    "ISIS Distance Attributes";
                                uses isis-distance-ipv6-config;
                            } // END of config-container definition.
                            container state {
                                config false;
                                description
                                    "Operational Attributes for ISIS Distance";
                                uses isis-distance-ipv6-config;
                            } // END of state-container definition.
                        } // End of distance-list
                    } // END of distances-container definition.
                } // END of address-family-ipv6-container definition.
                container distances {
                    description
                        "Enclosing container for the list of distances";

                    list distance {
                        key "system-id";
                        description
                            "ISIS Distance Attributes";
                        leaf system-id  {
                            type  leafref {
                                path  "../config/system-id";
                            }
                            description "System ID";
                        } // END of system-id definition.

                        container config {
                            description
                                "Config Attributes for ISIS Distance";
                            uses isis-distance-ipv4-config;
                        } // END of config-container definition.
                        container state {
                            config false;
                            description
                                "Operational Attributes for ISIS Distance";
                            uses isis-distance-ipv4-config;
                        } // END of state-container definition.
                    } // End of distance-list
                } // END of distances-container definition.
                container lsp-over-load {
                    // when " ipi-isis:isis/isis-instances/isis-instance/lsp-over-load/config/enabled ";
                    description
                        "set overload bit";
                    container config {
                        presence "To enable LSP overload";
                        description
                            "LSP Overload Configurations";
                        uses isis-lsp-overload-config;
                    } // END of config-container definition.
                    container state {
                        config false;
                        description
                            "LSP Overload operational information";
                        uses isis-lsp-overload-config;
                    } // END of state-container definition.
                } // END of lsp-over-load-container definition.
                container address-family-ipv4 {
                    description
                        "IS-IS protocol IPV4";
                    container state {
                        config false;
                        description
                            "This container defines the ISIS Protocol State Information";
                        uses isis-af-ipv4-state;
                    } // END of state-container definition.
                    container level-1-into-2-redistributes {
                        description
                            "Enclosing container for redistribute-level-1-into-2 list";

                        list redistribute-level-1-into-2 {
                            key "enable";
                            max-elements 1;
                            description
                                "This objectlist defines the ISIS Protocol Redistribution
                                            Configurations";
                            leaf enable  {
                                type  leafref {
                                    path  "../config/enable";
                                }
                                description "Use this attribute to redistribute reachability information from one
                                            level to the other level. If an distribute-list name is given with
                                            this command for an access list that does not exist, the routes are
                                            still redistributed.";
                            } // END of enable definition.

                            container config {
                                description
                                    "ISIS Protocol Default Information Configurations";
                                uses isis-af-ipv4-distribution-level-1-2-config;
                            } // END of config-container definition.
                            container state {
                                config false;
                                description
                                    "ISIS Protocol Default Information Operational information";
                                uses isis-af-ipv4-distribution-level-1-2-config;
                            } // END of state-container definition.
                        } // End of redistribute-level-1-into-2-list
                    } // END of level-1-into-2-redistributes-container definition.
                    container level-2-into-1-redistributes {
                        description
                            "Enclosing container for redistribute-level-2-into-1 list";

                        list redistribute-level-2-into-1 {
                            key "enable";
                            max-elements 1;
                            description
                                "This objectlist defines the ISIS Protocol Redistribution
                                            Configurations";
                            leaf enable  {
                                type  leafref {
                                    path  "../config/enable";
                                }
                                description "Use this attribute to redistribute reachability information from one
                                            level to the other level. If an distribute-list name is given with
                                            this command for an access list that does not exist, the routes are
                                            still redistributed.";
                            } // END of enable definition.

                            container config {
                                description
                                    "ISIS Protocol Default Information Configurations";
                                uses isis-af-ipv4-distribution-level-2-1-config;
                            } // END of config-container definition.
                            container state {
                                config false;
                                description
                                    "ISIS Protocol Default Information Operational information";
                                uses isis-af-ipv4-distribution-level-2-1-config;
                            } // END of state-container definition.
                        } // End of redistribute-level-2-into-1-list
                    } // END of level-2-into-1-redistributes-container definition.
                    container default-route-informations {
                        description
                            "Enclosing container for the list of default-route-information";

                        list default-route-information {
                            key "originate";
                            max-elements 1;
                            description
                                "This objectlist defines the ISIS Protocol Default Information
                                            Configurations and state information";
                            leaf originate  {
                                type  leafref {
                                    path  "../config/originate";
                                }
                                description "Use this attribute to originate reachability information to Default
                                            destination into LSP.There is no default information in Level-2 domain
                                            by default, while Level-1 router calculates default to L1L2 route
                                            during SPF calculation. This command enables to originate default
                                            route into Level-2 domain.";
                            } // END of originate definition.

                            container config {
                                description
                                    "ISIS Protocol Default Information Configurations";
                                uses isis-af-ipv4-default-info-config;
                            } // END of config-container definition.
                            container state {
                                config false;
                                description
                                    "ISIS Protocol Default Information operational information";
                                uses isis-af-ipv4-default-info-config;
                            } // END of state-container definition.
                        } // End of default-route-information-list
                    } // END of default-route-informations-container definition.
                    container redistributions {
                        description
                            "Enclosing container for the redistribution parameters";

                        list redistribute {
                            key "protocol-type";
                            description
                                "This objectlist defines configuration and state information for
                                            redistribution of routes from other protocols";
                            leaf protocol-type  {
                                type  leafref {
                                    path  "../config/protocol-type";
                                }
                                description "Use this attribute to redistribute routes from another protocol into
                                            the ISIS routing table.";
                            } // END of protocol-type definition.

                            container config {
                                description
                                    "ISIS Protocol Default Information Configurations";
                                uses isis-af-ipv4-redistribution-config;
                                uses isis-af-ipv4-redistribution-configurations-config;
                            } // END of config-container definition.
                            container state {
                                config false;
                                description
                                    "ISIS Protocol Default Information state information";
                                uses isis-af-ipv4-redistribution-config;
                                uses isis-af-ipv4-redistribution-configurations-config;
                            } // END of state-container definition.
                        } // End of redistribute-list
                    } // END of redistributions-container definition.
                    container summary-addresses {
                        description
                            "Enclosing container for the list of summary addresses";

                        list summary-address {
                            key "prefix";
                            description
                                "This objectlist contains config and state information related to
                                            summary-address";
                            leaf prefix  {
                                type  leafref {
                                    path  "../config/prefix";
                                }
                                description "Use this attribute to Summary Address to summarize IPv4 reachability
                                            information.";
                            } // END of prefix definition.

                            container config {
                                description
                                    "AF IPv4 Summary Prefix List";
                                uses isis-af-ipv4-summary-prefix-config;
                            } // END of config-container definition.
                            container state {
                                config false;
                                description
                                    "AF IPv4 Summary Prefix List state information";
                                uses isis-af-ipv4-summary-prefix-config;
                            } // END of state-container definition.
                        } // End of summary-address-list
                    } // END of summary-addresses-container definition.
                    container redistribute-isis-instances {
                        description
                            "Enclosing container for redistribute-isis-instance list";

                        list redistribute-isis-instance {
                            key "id";
                            max-elements 1;
                            description
                                "This objectlist defines config and state information related to isis
                                            redistribuition";
                            leaf id  {
                                type  leafref {
                                    path  "../config/id";
                                }
                                description "Instance ID";
                            } // END of id definition.

                            container config {
                                description
                                    "AF IPv4 Redistribution Configurations";
                                uses isis-af-ipv4-redist-isis-config;
                                uses isis-af-ipv4-redistribution-configurations-config;
                            } // END of config-container definition.
                            container state {
                                config false;
                                description
                                    "AF IPv4 Redistribution state information";
                                uses isis-af-ipv4-redist-isis-config;
                                uses isis-af-ipv4-redistribution-configurations-config;
                            } // END of state-container definition.
                        } // End of redistribute-isis-instance-list
                    } // END of redistribute-isis-instances-container definition.
                } // END of address-family-ipv4-container definition.
                uses isis-passive-interface-top;
                uses isis-microloop-avoidance-top;
                uses isis-mpls-traffic-engg-top;
                uses isis-extended-admin-group-top;
                uses isis-flexalgo-top-grp;
                uses level-runtime-grouping;
                uses spf-levels-grouping;
                uses levels-grouping;
                uses cspf-grouping;
                uses ipv4-lfa-route-grouping;
                uses ipv6-lfa-route-grouping;
                uses fast-reroute-levels-grouping;
                uses segment-routing-capability-grouping;
                uses segment-routing-mapping-server-ipv4-grouping;
                uses segment-routing-grouping;
            } // End of isis-instance-list
        } // END of isis-instances-container definition.
        container debug {
            description
                "Debug Flags";
            container config {
                description
                    "Debug flags for configuration";
                uses isis-conf-mode-debug-config;
            } // END of config-container definition.
            container state {
                config false;
                description
                    "Debug flags state information";
                uses isis-conf-mode-debug-config;
                uses isis-terminal-mode-debug-state;
            } // END of state-container definition.
        } // END of debug-container definition.
        container state {
            config false;
            description
                "Notification state information";
            leaf-list host-name  {
                type  string {
                    length "1..1965";
                    pattern "[^?' =,>|]+";
                }
                description "Hostname";
            } // END of host-name definition.

            uses isis-notif-state;
        } // END of state-container definition.
        uses graceful-restart-grouping;
        uses interfaces-grouping;
    } // END of isis-container definition.
    } // END of isis-grouping definition.

    uses isis-grouping;

    rpc isis-restart-graceful {
        if-feature feature-list:HAVE_RESTART;
        if-feature feature-list:HAVE_ISISD;
        description "Use this RPC to gracefully restart the IS-IS router.";
        input  {
            leaf grace-period  {
                type uint16 {
                    range "1..65535";
                }
                description "The time within which ISIS should come up";
            }
        }
    }

    rpc isis-clear-interface-counters {
        if-feature feature-list:HAVE_ISISD;
        description "Use this attribute to clear interface counters. If you do not specify
                    a parameter, then counters for all interfaces are cleared.";
        input  {
            leaf name  {
                type string;
                description "Specify the Interface name for which counters should be reset";
            }
        }
    }

    rpc isis-clear-is-neighbors {
        if-feature feature-list:HAVE_ISISD;
        description "Use this attribute to clear IS neighbor adjacencies.";
        input  {
            leaf system-id  {
                type string;
                mandatory true;
                description "Specify the system-id for which neighbourship has to be cleared";
            }
        }
    }

    rpc isis-clear-clns-neighbors {
        if-feature feature-list:HAVE_ISISD;
        description "Use this attribute to clear CLNS neighbor adjacencies.";
    }

    rpc isis-clear-ip-route {
        if-feature feature-list:HAVE_ISISD;
        description "Use this attribute to clear IPv4 routes.";
        input  {
            leaf instance  {
                type string;
                description "Specify for which instance we need to clear";
            }
            leaf ipv4-route  {
                type ipi-isis-types:isis_route_t;
                mandatory true;
                description "Specify for which route-type we need to clear";
            }
        }
    }

    rpc isis-clear-ipv6-route {
        if-feature feature-list:HAVE_ISISD;
        description "Use this attribute to clear IPv6 routes.";
        input  {
            leaf instance  {
                type string;
                description "Specify for which instance we need to clear";
            }
            leaf ipv6-route  {
                type ipi-isis-types:isis_route_t;
                mandatory true;
                description "Specify for which route-type we need to clear";
            }
        }
    }

    rpc isis-process-clear {
        if-feature feature-list:HAVE_ISISD;
        description "Use this attribute to restart ISIS processes. If you do not specify a
                    parameter, then all ISIS processes are restarted.";
        input  {
            leaf instance  {
                type string;
                mandatory true;
                description "Specify for which instance we need to clear";
            }
        }
    }

    rpc isis-clear-counters {
        if-feature feature-list:HAVE_ISISD;
        description "Use this attribute to clear system-wide IS-IS counters
                    (IsisSystemCounterEntry in RFC 4444).";
    }

    rpc isis-clear-te-global-counters {
        if-feature feature-list:HAVE_ISISD;
        description "Use this attribute to clear system-wide IS-IS TE-global counters.";
        input  {
            leaf te-global-counter-options  {
                type ipi-isis-types:isis_te_global_counter_type_t;
                mandatory true;
                description "Use this command to clear ISIS TE-global counters.";
            }
        }
    }

    rpc isis-clear-adjacency-all {
        if-feature feature-list:HAVE_ISISD;
        description "Use this attribute to clear all isis adjacency.";
        input  {
            leaf adjacency-vrf-name  {
                type string;
                description "Specify for which vrf we need to clear adjacency";
            }
        }
    }

    rpc isis-process-clear-adjacency-all {
        if-feature feature-list:HAVE_ISISD;
        description "Use this attribute to clear all isis adjacency to specified router.";
        input  {
            leaf tag-name  {
                type string;
                mandatory true;
                description "Specify for which instance we need to clear adjacency";
            }
            leaf adjacency-vrf-name  {
                type string;
                description "Specify for which vrf we need to clear adjacency";
            }
        }
    }

    rpc isis-process-clear-adjacency-interface {
        if-feature feature-list:HAVE_ISISD;
        description "Use this attribute to clear isis adjacency with specific interface.";
        input  {
            leaf tag-name  {
                type string;
                mandatory true;
                description "Specify for which instance we need to clear adjacency";
            }
            leaf tag-if-name  {
                type string;
                description "Specify for which interface we need to clear adjacency";
            }
            leaf adjacency-vrf-name  {
                type string;
                description "Specify for which vrf we need to clear adjacency";
            }
        }
    }

    rpc isis-clear-adjacency-interface {
        if-feature feature-list:HAVE_ISISD;
        description "Use this attribute to clear isis adjacency for specific router.";
        input  {
            leaf adjacency-if-name  {
                type string;
                description "Specify for which interface we need to clear adjacency";
            }
            leaf adjacency-vrf-name  {
                type string;
                description "Specify for which vrf we need to clear adjacency";
            }
        }
    }

    rpc isis-process-clear-adjacency-system-id {
        if-feature feature-list:HAVE_ISISD;
        description "Use this attribute to clear isis adjacency for specific system-id.";
        input  {
            leaf tag-name  {
                type string;
                mandatory true;
                description "Specify for which instance we need to clear adjacency";
            }
            leaf tag-system-id  {
                type ipi-isis-types:isis_systemid_t;
                mandatory true;
                description "Specify for which system-id we need to clear adjacency";
            }
            leaf tag-vrf-name  {
                type string;
                description "Specify for which vrf we need to clear adjacency";
            }
        }
    }

    rpc isis-clear-adjacency-system-id {
        if-feature feature-list:HAVE_ISISD;
        description "Use this attribute to clear isis adjacency for specific system-id.";
        input  {
            leaf adjacency-system-id  {
                type ipi-isis-types:isis_systemid_t;
                mandatory true;
                description "Specify for which system-id we need to clear adjacency";
            }
            leaf adjacency-vrf-name  {
                type string;
                description "Specify for which vrf we need to clear adjacency";
            }
        }
    }

    rpc isis-restart-snmp {
        if-feature feature-list:HAVE_SNMP;
        if-feature feature-list:HAVE_ISISD;
        description "Use this attribute to restart SNMP in Intermediate System to
                    Intermediate System (IS-IS)";
    }

    rpc isis-terminal-debug-all-on {
        if-feature feature-list:HAVE_ISISD;
        description "Use this RPC to       enable debug all ISIS";
    }

    rpc isis-terminal-debug-all-off {
        if-feature feature-list:HAVE_ISISD;
        description "Use this RPC to disable debug all ISIS";
    }

    rpc isis-terminal-debug-on {
        if-feature feature-list:HAVE_ISISD;
        description "Use this RPC to enable debug on ISIS";
        input  {
            leaf terminal-debug-options  {
                type ipi-isis-types:isis_debug_t;
                mandatory true;
                description "Use this command to turn on, ISIS debugging at various levels.";
            }
        }
    }

    rpc isis-debug-off {
        if-feature feature-list:HAVE_ISISD;
        description "Use this RPC to disable debug on ISIS";
        input  {
            leaf terminal-debug-options  {
                type ipi-isis-types:isis_debug_t;
                mandatory true;
                description "Use this command to turn off, ISIS debugging at various levels.";
            }
        }
    }

    rpc isis-debug-hello-on {
        if-feature feature-list:HAVE_ISISD;
        description "Use this RPC to enable debug on ISIS hello messages.";
    }

    rpc isis-debug-hello-off {
        if-feature feature-list:HAVE_ISISD;
        description "Use this RPC to disable debug on ISIS hello messages.";
    }

    rpc isis-debug-interface-hello-on {
        if-feature feature-list:HAVE_ISISD;
        description "Use this RPC to enable debug on ISIS hello messages for an interface.";
        input  {
            leaf interface  {
                type string;
                mandatory true;
                description "Use this attribute to turn on debugging for ISIS Interface hello";
            }
        }
    }

    rpc isis-debug-interface-hello-off {
        if-feature feature-list:HAVE_ISISD;
        description "Use this RPC to disable debug on ISIS hello messages for an interface.";
        input  {
            leaf interface  {
                type string;
                mandatory true;
                description "Use this attribute to turn off debugging for ISIS Interface hello";
            }
        }
    }

    rpc isis-debug-system-id-hello-on {
        if-feature feature-list:HAVE_ISISD;
        description "Use this RPC to enable debug on ISIS SID hello messages.";
        input  {
            leaf system-id  {
                type string;
                mandatory true;
                description "Use this attribute to turn on debugging for ISIS SID hello";
            }
        }
    }

    rpc isis-debug-system-id-hello-off {
        if-feature feature-list:HAVE_ISISD;
        description "Use this RPC to disable debug on ISIS SID hello messages.";
        input  {
            leaf system-id  {
                type string;
                mandatory true;
                description "Use this attribute to turn off debugging for ISIS SID hello";
            }
        }
    }

    rpc isis-all-debug-off {
        if-feature feature-list:HAVE_ISISD;
        description "Use this RPC to disable debug on ISIS.";
    }

    rpc isis-debug-cspf-on {
        if-feature feature-list:HAVE_ISIS_CSPF;
        if-feature feature-list:HAVE_ISISD;
        description "Use this RPC to enable debug on ISIS CSPF events.";
        input  {
            leaf cspf-debug  {
                type ipi-isis-types:isis_cspf_debug_t;
                mandatory true;
                description "Use this attribute to enable CSPF debug logs.";
            }
        }
    }

    rpc isis-debug-cspf-off {
        if-feature feature-list:HAVE_ISIS_CSPF;
        if-feature feature-list:HAVE_ISISD;
        description "Use this RPC to disable debug on ISIS CSPF events.";
        input  {
            leaf cspf-debug  {
                type ipi-isis-types:isis_cspf_debug_t;
                mandatory true;
                description "Use this attribute to enable CSPF debug logs.";
            }
        }
    }

    notification isis-database-overload {
        if-feature feature-list:HAVE_ISISD;

        description "This notification is sent when an IS-IS instance overload state changes..";

        leaf severity {
            type cml-data-types:cml_notif_severity_t;
            description "Notification severity level (value: MAJOR)";
        }

        leaf eventClass {
            type cml-data-types:cml_notif_class_t;
            description "Notification event class (value: STATE)";
        }

        leaf overload {
            type ipi-isis-types:isis_overload_state_t;
        description
            "New overload state of the IS-IS instance";
        }
    }

    notification isis-lsp-too-large {
        if-feature feature-list:HAVE_ISISD;

        description "This notification is sent when we attempt to propagate an LSP that is larger than the dataLinkBlockSize (ISO10589) for the circuit.The notification generation must be throttled with at least 5 seconds between successive notifications..";

        leaf severity {
            type cml-data-types:cml_notif_severity_t;
            description "Notification severity level (value: MINOR)";
        }

        leaf eventClass {
            type cml-data-types:cml_notif_class_t;
            description "Notification event class (value: STATE)";
        }

        leaf lsp-identifier {
            type  string;
        description
            "LSP ID";
        }

        leaf pdu-length {
            type  uint32;
        description
            "Size of the LSP PDU";
        }
    }

    notification isis-corrupted-lsp-detected {
        if-feature feature-list:HAVE_ISISD;

        description "This notification is sent when we find that an LSP that was stored in memory has become corrupted..";

        leaf severity {
            type cml-data-types:cml_notif_severity_t;
            description "Notification severity level (value: MAJOR)";
        }

        leaf eventClass {
            type cml-data-types:cml_notif_class_t;
            description "Notification event class (value: STATE)";
        }

        leaf lsp-identifier {
            type  string;
        description
            "LSP ID";
        }
    }

    notification isis-attempt-to-exceed-max-sequence {
        if-feature feature-list:HAVE_ISISD;

        description "This notification is sent when the system wraps the 32-bit sequence counter of an LSP..";

        leaf severity {
            type cml-data-types:cml_notif_severity_t;
            description "Notification severity level (value: MINOR)";
        }

        leaf eventClass {
            type cml-data-types:cml_notif_class_t;
            description "Notification event class (value: STATE)";
        }

        leaf lsp-identifier {
            type  string;
        description
            "LSP ID";
        }
    }

    notification isis-id-len-mismatch {
        if-feature feature-list:HAVE_ISISD;

        description "This notification is sent when we receive a PDU with a different value for the system-id length.The notification generation must be throttled with at least 5 seconds between successive notifications..";

        leaf severity {
            type cml-data-types:cml_notif_severity_t;
            description "Notification severity level (value: MINOR)";
        }

        leaf eventClass {
            type cml-data-types:cml_notif_class_t;
            description "Notification event class (value: STATE)";
        }

        leaf pdu-field-len {
            type  uint8;
        description
            "Size of the ID length in the received PDU";
        }

        leaf raw-pdu {
            type  string;
        description
            "Received raw PDU";
        }
    }

    notification isis-max-area-addresses-mismatch {
        if-feature feature-list:HAVE_ISISD;

        description "This notification is sent when we receive a PDU with a different value for the Maximum Area Addresses.The notification generation must be throttled with at least 5 seconds between successive notifications..";

        leaf severity {
            type cml-data-types:cml_notif_severity_t;
            description "Notification severity level (value: MINOR)";
        }

        leaf eventClass {
            type cml-data-types:cml_notif_class_t;
            description "Notification event class (value: STATE)";
        }

        leaf max-area-addresses {
            type  uint8;
        description
            "Received number of supported areas";
        }

        leaf raw-pdu {
            type  string;
        description
            "Received raw PDU";
        }
    }

    notification isis-own-lsp-purge {
        if-feature feature-list:HAVE_ISISD;

        description "This notification is sent when the system receives a PDU with its own system-id and zero age..";

        leaf severity {
            type cml-data-types:cml_notif_severity_t;
            description "Notification severity level (value: MINOR)";
        }

        leaf eventClass {
            type cml-data-types:cml_notif_class_t;
            description "Notification event class (value: STATE)";
        }

        leaf lsp-identifier {
            type  string;
        description
            "LSP ID";
        }
    }

    notification isis-sequence-number-skipped {
        if-feature feature-list:HAVE_ISISD;

        description "This notification is sent when the system receives a PDU with its own system-id and different contents. The system has to originate the LSP with a higher sequence number..";

        leaf severity {
            type cml-data-types:cml_notif_severity_t;
            description "Notification severity level (value: MINOR)";
        }

        leaf eventClass {
            type cml-data-types:cml_notif_class_t;
            description "Notification event class (value: STATE)";
        }

        leaf lsp-identifier {
            type  string;
        description
            "LSP ID";
        }
    }

    notification isis-authentication-type-failure {
        if-feature feature-list:HAVE_ISISD;

        description "This notification is sent when the system receives a PDU with the wrong authentication type field.The notification generation must be throttled with at least 5 seconds between successive notifications..";

        leaf severity {
            type cml-data-types:cml_notif_severity_t;
            description "Notification severity level (value: MINOR)";
        }

        leaf eventClass {
            type cml-data-types:cml_notif_class_t;
            description "Notification event class (value: STATE)";
        }

        leaf raw-pdu {
            type  string;
        description
            "Received raw PDU";
        }
    }

    notification isis-authentication-failure {
        if-feature feature-list:HAVE_ISISD;

        description "This notification is sent when the system receives a PDU with the wrong authentication information.The notification generation must be throttled..";

        leaf severity {
            type cml-data-types:cml_notif_severity_t;
            description "Notification severity level (value: MINOR)";
        }

        leaf eventClass {
            type cml-data-types:cml_notif_class_t;
            description "Notification event class (value: STATE)";
        }

        leaf raw-pdu {
            type  string;
        description
            "Received raw PDU";
        }
    }

    notification isis-version-skew {
        if-feature feature-list:HAVE_ISISD;

        description "This notification is sent when the system receives a PDU with a different protocol version number.The notification generation must be throttled with at least 5 seconds between successive notifications..";

        leaf severity {
            type cml-data-types:cml_notif_severity_t;
            description "Notification severity level (value: MINOR)";
        }

        leaf eventClass {
            type cml-data-types:cml_notif_class_t;
            description "Notification event class (value: STATE)";
        }

        leaf protocol-version {
            type  uint8;
        description
            "Protocol version received in the PDU";
        }

        leaf raw-pdu {
            type  string;
        description
            "Received raw PDU";
        }
    }

    notification isis-area-mismatch {
        if-feature feature-list:HAVE_ISISD;

        description "This notification is sent when the system receives a Hello PDU from an IS that does not share any area address. The notification generation must be throttled with at least 5 seconds between successive notifications..";

        leaf severity {
            type cml-data-types:cml_notif_severity_t;
            description "Notification severity level (value: MINOR)";
        }

        leaf eventClass {
            type cml-data-types:cml_notif_class_t;
            description "Notification event class (value: STATE)";
        }

        leaf raw-pdu {
            type  string;
        description
            "Received raw PDU";
        }
    }

    notification isis-rejected-adjacency {
        if-feature feature-list:HAVE_ISISD;

        description "This notification is sent when the system receives a Hello PDU from an IS but does not establish an adjacency for some reason. The notification generation must be throttled with at least 5 seconds between successive notifications..";

        leaf severity {
            type cml-data-types:cml_notif_severity_t;
            description "Notification severity level (value: MINOR)";
        }

        leaf eventClass {
            type cml-data-types:cml_notif_class_t;
            description "Notification event class (value: STATE)";
        }

        leaf raw-pdu {
            type  string;
        description
            "Received raw PDU";
        }

        leaf reason {
            type  string;
        description
            "string describing the reason";
        }
    }

    notification isis-protocols-supported-mismatch {
        if-feature feature-list:HAVE_ISISD;

        description "This notification is sent when the system receives a non-pseudonode LSP that has no matching protocols supported. The notification generation must be throttled with at least 5 seconds between successive notifications..";

        leaf severity {
            type cml-data-types:cml_notif_severity_t;
            description "Notification severity level (value: MINOR)";
        }

        leaf eventClass {
            type cml-data-types:cml_notif_class_t;
            description "Notification event class (value: STATE)";
        }

        leaf raw-pdu {
            type  string;
        description
            "Received raw PDU";
        }

        leaf protocols {
            type  uint8;
        description
            "List of protocols supported by the remote system";
        }
    }

    notification isis-lsp-error-detected {
        if-feature feature-list:HAVE_ISISD;

        description "This notification is sent when the system receives an LSP with a parse error. The notification generation must be throttled with at least 5 seconds between successive notifications..";

        leaf severity {
            type cml-data-types:cml_notif_severity_t;
            description "Notification severity level (value: MINOR)";
        }

        leaf eventClass {
            type cml-data-types:cml_notif_class_t;
            description "Notification event class (value: STATE)";
        }

        leaf lsp-identifier {
            type  string;
        description
            "LSP ID";
        }

        leaf raw-pdu {
            type  string;
        description
            "Received raw PDU";
        }

        leaf error-offset {
            type  uint32;
        description
            "If the problem is a malformed TLV, the error-offset points to the
                    start of the TLV. If the problem is with the LSP header, the
                    error-offset points to the errant byte";
        }

        leaf tlv-type {
            type  uint8;
        description
            "If the problem is a malformed TLV, the tlv-type is set to the type
                    value of the suspicious TLV. Otherwise, this leaf is not presen";
        }
    }

    notification isis-segment-routing-index-out-of-range {
        if-feature feature-list:HAVE_ISISD;
        if-feature feature-list:HAVE_ISIS_SR;

        description "SRGB range.";

        leaf severity {
            type cml-data-types:cml_notif_severity_t;
            description "Notification severity level (value: MAJOR)";
        }

        leaf eventClass {
            type cml-data-types:cml_notif_class_t;
            description "Notification event class (value: STATE)";
        }

        leaf global-block-base {
            type  int32;
        description
            "Start ID";
        }

        leaf global-block-range {
            type  int32;
        description
            "End ID";
        }

        leaf received-index {
            type  uint32;
        description
            "Index";
        }

        leaf routing-protocol {
            type  string;
        description
            "Module Name";
        }
    }

}
