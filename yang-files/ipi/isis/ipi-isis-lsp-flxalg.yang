/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-isis-lsp-flxalg.yang
*
*/

submodule ipi-isis-lsp-flxalg {

    yang-version 1.1;

    belongs-to  ipi-isis { prefix ipi-isis; }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Model for managing IS-IS Flexible Algorithm Specific LSDB Extension";


    revision "2024-04-22" {
        description "Defined group aliases for all Flex-Algo state container definitions";
        reference " 0.1.2.";
    }

    revision "2024-04-17" {
        description "Added Get API header file name for generation";
        reference " 0.1.1.";
    }

    revision "2023-09-29" {
        description "Initial release of IGP Flexible Algorithm for ISIS Segment Routing";
        reference " 0.1.0.";
    }

    grouping isis-level-lspdb-mismatch-state {
        description
            "State items for ISIS Level LSPDB Mismatch";
        leaf mismatch-length  {
            type  uint16;
            description "stlv Mismatch in Length";
        } // END of mismatch-length definition.

    } // END of isis-level-lspdb-mismatch-state definition.
    grouping isis-level-lspdb-tlv-rcap-fa-sstlv-state {
        description
            "ISIS Router Capability, Flexible Algorithm Sub-STLV State";
        leaf sstlv-index  {
            type  uint16;
            description "Index";
        } // END of sstlv-index definition.

    } // END of isis-level-lspdb-tlv-rcap-fa-sstlv-state definition.
    grouping isis-lspdb-fa-sstlv-eag-exclude-any-state {
        description
            "Flexible Algorithm Exclude Admin Group, RFC7308 sub-TLV State";
        leaf-list ext-admin-group-exclude-any  {
            type  uint32;
            description "Flex-Algo exclude admin groups";
        } // END of ext-admin-group-exclude-any definition.

    } // END of isis-lspdb-fa-sstlv-eag-exclude-any-state definition.
    grouping isis-lspdb-fa-sstlv-eag-include-any-state {
        description
            "Flexible Algorithm Include Any Admin Group, RFC7308 sub-TLV State";
        leaf-list ext-admin-group-include-any  {
            type  uint32;
            description "Flex-Algo include any admin groups";
        } // END of ext-admin-group-include-any definition.

    } // END of isis-lspdb-fa-sstlv-eag-include-any-state definition.
    grouping isis-lspdb-fa-sstlv-eag-include-all-state {
        description
            "Flexible Algorithm Include All Admin Group, RFC7308 sub-TLV State";
        leaf-list ext-admin-group-include-all  {
            type  uint32;
            description "Flex-Algo include all admin groups";
        } // END of ext-admin-group-include-all definition.

    } // END of isis-lspdb-fa-sstlv-eag-include-all-state definition.
    grouping isis-lspdb-fa-sstlv-flags-state {
        description
            "Flexible Algorithm definition Flags sub-TLV State";
        leaf fad-flags  {
            type  uint32;
            description "Flex-Algo definition flags";
        } // END of fad-flags definition.

    } // END of isis-lspdb-fa-sstlv-flags-state definition.
    grouping isis-lspdb-fa-sstlv-exclude-srlg-state {
        description
            "Flexible Algorithm Exclude SRLG, RFC4203 sub-TLV State";
        leaf-list exclude-srlg  {
            type  uint32;
            description "Flex-Algo exclude SRLGs";
        } // END of exclude-srlg definition.

    } // END of isis-lspdb-fa-sstlv-exclude-srlg-state definition.
    grouping isis-level-lspdb-tlv-router-cap-stlv-fad-fixed-state {
        description
            "Grouping for IS-IS FAD sub-TLVs";
        leaf flex-algo-num  {
            type  uint32;
            description "Flex-Algo number, value between 128 and 255 inclusive";
        } // END of flex-algo-num definition.

        leaf metric-type  {
            type  uint32;
            description "Flex-Algo metric, to be used during the path calculation";
        } // END of metric-type definition.

        leaf calc-type  {
            type  uint32;
            description "IGP algorithm types to be used during path calculation, value from 0
                        to 127";
        } // END of calc-type definition.

        leaf priority  {
            type  uint32;
            description "Flex-Algo priority of the advertisement";
        } // END of priority definition.

    } // END of isis-level-lspdb-tlv-router-cap-stlv-fad-fixed-state definition.
    grouping isis-level-lspdb-tlv-router-cap-stlv-fad-var-state {
        description
            "Grouping for IS-IS FAD sub-TLVs";
        container fad-stlv-list {
            if-feature feature-list:HAVE_ISIS_SR_OR_HAVE_SRV6;
            config false;
            description
                "IS-IS FAD sub-sub-TLV List";

            list fad-sstlv {
                key "sstlv-index";
                config false;
                description
                    "IS-IS FAD Sub-TLV operational Information";
                leaf sstlv-index  {
                    type  leafref {
                        path  "../state/sstlv-index";
                    }
                    description "Index";
                } // END of sstlv-index definition.

                container state {
                    config false;
                    description
                        "ISIS Level LSP DB Router Capability, Flexible Algorithm STLV State";
                    uses isis-level-lspdb-tlv-rcap-fa-sstlv-state;
                } // END of state-container definition.
                container router-cap-fa-sstlv-eag-exclude-any {
                    if-feature feature-list:HAVE_ISIS_SR;
                    config false;
                    description
                        "ISIS Level LSP DB Router Capability Flex-Algo EAG Exclude Any";
                    container state {
                        config false;
                        description
                            "ISIS Level LSP DB Router Capability Flex-Algo Exclude Any EAG State";
                        uses isis-lspdb-fa-sstlv-eag-exclude-any-state;
                        uses isis-level-lspdb-mismatch-state;
                    } // END of state-container definition.
                } // END of router-cap-fa-sstlv-eag-exclude-any-container definition.
                container router-cap-fa-sstlv-eag-include-any {
                    if-feature feature-list:HAVE_ISIS_SR;
                    config false;
                    description
                        "ISIS Level LSP DB Router Capability Flex-Algo EAG Include Any";
                    container state {
                        config false;
                        description
                            "ISIS Level LSP DB Router Capability Flex-Algo Include Any EAG State";
                        uses isis-lspdb-fa-sstlv-eag-include-any-state;
                        uses isis-level-lspdb-mismatch-state;
                    } // END of state-container definition.
                } // END of router-cap-fa-sstlv-eag-include-any-container definition.
                container router-cap-fa-sstlv-eag-include-all {
                    if-feature feature-list:HAVE_ISIS_SR;
                    config false;
                    description
                        "ISIS Level LSP DB Router Capability Flex-Algo EAG Include All";
                    container state {
                        config false;
                        description
                            "ISIS Level LSP DB Router Capability Flex-Algo Include All EAG State";
                        uses isis-lspdb-fa-sstlv-eag-include-all-state;
                        uses isis-level-lspdb-mismatch-state;
                    } // END of state-container definition.
                } // END of router-cap-fa-sstlv-eag-include-all-container definition.
                container router-cap-fa-sstlv-flags-state {
                    if-feature feature-list:HAVE_ISIS_SR;
                    config false;
                    description
                        "ISIS Level LSP DB Router Capability Flex-Algo Flags";
                    container state {
                        config false;
                        description
                            "ISIS Level LSP DB Router Capability Flex-Algo Flags State";
                        uses isis-lspdb-fa-sstlv-flags-state;
                        uses isis-level-lspdb-mismatch-state;
                    } // END of state-container definition.
                } // END of router-cap-fa-sstlv-flags-state-container definition.
                container router-cap-fa-sstlv-exclude-srlg {
                    if-feature feature-list:HAVE_ISIS_SR;
                    config false;
                    description
                        "ISIS Level LSP DB Router Capability Flex-Algo Exclude SRLG";
                    container state {
                        config false;
                        description
                            "ISIS Level LSP DB Router Capability Flex-Algo Exclude SRLG State";
                        uses isis-lspdb-fa-sstlv-exclude-srlg-state;
                        uses isis-level-lspdb-mismatch-state;
                    } // END of state-container definition.
                } // END of router-cap-fa-sstlv-exclude-srlg-container definition.
            } // End of fad-sstlv-list
        } // END of fad-stlv-list-container definition.
    } // END of isis-level-lspdb-tlv-router-cap-stlv-fad-var-state definition.
    grouping isis-level-lspdb-sr-ext-prefix-stlv-fa-fapm-state {
        description
            "ISIS Segment Routing Flexible Algorithm Prefix Metric (FAPM) Sub-TLV
                        State";
        leaf flex-algo-num  {
            type  uint32;
            description "Flex-Algo number, value between 128 and 255 inclusive";
        } // END of flex-algo-num definition.

        leaf prefix-metric  {
            type  uint32;
            description "Prefix metric";
        } // END of prefix-metric definition.

    } // END of isis-level-lspdb-sr-ext-prefix-stlv-fa-fapm-state definition.
    grouping isis-level-lspdb-sr-ext-eipv4-reach-prefix-stlv-fa-fapm-state {
        description
            "ISIS-SR extended IPv4 reachability Flex-Algo FAPM Sub-TLV State";
        container flxalg-fapm {
            if-feature feature-list:HAVE_ISIS_SR;
            description
                "ISIS Level LSP DB Extended IPv4 Reachability STLV Flex-Algo";
            container state {
                description
                    "ISIS Level LSP DB Extended IPv4 Reachability STLV Flex-Algo State";
                uses isis-level-lspdb-sr-ext-prefix-stlv-fa-fapm-state;
                uses isis-level-lspdb-mismatch-state;
            } // END of state-container definition.
        } // END of flxalg-fapm-container definition.
    } // END of isis-level-lspdb-sr-ext-eipv4-reach-prefix-stlv-fa-fapm-state definition.
    grouping isis-level-lspdb-sr-ext-eipv6-reach-prefix-stlv-fa-fapm-state {
        description
            "ISIS-SR extended IPv6 reachability Flex-Algo FAPM Sub-TLV State";
        container flxalg-fapm {
            if-feature feature-list:HAVE_ISIS_SR;
            description
                "ISIS Level LSP DB IPv6 Reachability STLV Flex-Algo";
            container state {
                description
                    "ISIS Level LSP DB IPv6 Reachability STLV Flex-Algo State";
                uses isis-level-lspdb-sr-ext-prefix-stlv-fa-fapm-state;
                uses isis-level-lspdb-mismatch-state;
            } // END of state-container definition.
        } // END of flxalg-fapm-container definition.
    } // END of isis-level-lspdb-sr-ext-eipv6-reach-prefix-stlv-fa-fapm-state definition.
    grouping isis-level-lspdb-sr-ext-mtipv4-reach-prefix-stlv-fa-fapm-state {
        description
            "ISIS-SR multi-topology IPv4 reachability Flex-Algo FAPM Sub-TLV State";
        container flxalg-fapm {
            if-feature feature-list:HAVE_ISIS_SR;
            description
                "ISIS Level LSP DB Multi-Topology IPv4 Reachability STLV Flex-Algo";
            container state {
                description
                    "ISIS Level LSP DB Multi-Topology IPv4 Reachability STLV Flex-Algo
                            State";
                uses isis-level-lspdb-sr-ext-prefix-stlv-fa-fapm-state;
                uses isis-level-lspdb-mismatch-state;
            } // END of state-container definition.
        } // END of flxalg-fapm-container definition.
    } // END of isis-level-lspdb-sr-ext-mtipv4-reach-prefix-stlv-fa-fapm-state definition.
    grouping isis-level-lspdb-sr-ext-mtipv6-reach-prefix-stlv-fa-fapm-state {
        description
            "ISIS-SR multi-topology IPv6 reachability Flex-Algo FAPM Sub-TLV State";
        container flxalg-fapm {
            if-feature feature-list:HAVE_ISIS_SR;
            description
                "ISIS Level LSP DB Multi-Topology IPv6 Reachability STLV Flex-Algo";
            container state {
                description
                    "ISIS Level LSP DB Multi-Topology IPv6 Reachability STLV Flex-Algo
                            State";
                uses isis-level-lspdb-sr-ext-prefix-stlv-fa-fapm-state;
                uses isis-level-lspdb-mismatch-state;
            } // END of state-container definition.
        } // END of flxalg-fapm-container definition.
    } // END of isis-level-lspdb-sr-ext-mtipv6-reach-prefix-stlv-fa-fapm-state definition.
    grouping isis-level-lspdb-sr-ext-rcap-stlv-fa-defn-state {
        description
            "ISIS-SR router capability Flex-Algo Sub-TLV State";
        container router-cap-flxalg-defn {
            if-feature feature-list:HAVE_ISIS_SR;
            config false;
            description
                "ISIS Level LSP DB Router Capability STLV Flex-Algo";
            container state {
                config false;
                description
                    "ISIS Level LSP DB Router Capability STLV Flex-Algo State";
                uses isis-level-lspdb-tlv-router-cap-stlv-fad-fixed-state;
                uses isis-level-lspdb-tlv-router-cap-stlv-fad-var-state;
                uses isis-level-lspdb-mismatch-state;
            } // END of state-container definition.
        } // END of router-cap-flxalg-defn-container definition.
    } // END of isis-level-lspdb-sr-ext-rcap-stlv-fa-defn-state definition.


}
