/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-isis-interface-flxalg.yang
*
*/

submodule ipi-isis-interface-flxalg {

    yang-version 1.1;

    belongs-to  ipi-isis { prefix ipi-isis; }

    import feature-list {
        prefix feature-list;
        revision-date 2026-09-15;
    }

    import ipi-global-te {
        prefix ipi-global-te;
        revision-date 2024-12-23;
    }

    organization
        "IP Infusion Inc.";

    contact
        "Address: 3965 Freedom Circle, Suite 200, Santa Clara, CA 95054
         Phone: +1 408-400-1900
         E-mail: support@ipinfusion.com
         Web: http://www.ipinfusion.com/";

    description
        "Model for managing IS-IS interfaces Flexible-Algorithm configurations
                and state";


    revision "2026-02-04" {
        description "Added leafref for Interface Flex-Algo admin group attributes";
        reference " 0.3.1.";
    }

    revision "2025-09-06" {
        description "Corrected Interface Flex-Algo ASLA SRLG Min Value to 1";
        reference " 0.2.2.";
    }

    revision "2025-09-04" {
        description "Removed EVPN_IRB_IF_MODE while configuring IRB interface";
        reference " 0.2.1.";
    }

    revision "2025-06-09" {
        description "Corrected Interface Flex-Algo ASLA TE-Metric Max Value to 16777215";
        reference " 0.2.0.";
    }

    revision "2025-05-28" {
        description "Added Interface ASLA all applications params usage enable/disable CLI command";
        reference " 0.1.6.";
    }

    revision "2025-02-04" {
        description "Changed Interface Flex-Algo ASLA SRLG params to hidden";
        reference " 0.1.5.";
    }

    revision "2024-06-25" {
        description "Moved delay normalizations params to main interface XML";
        reference " 0.1.4.";
    }

    revision "2024-04-16" {
        description "Added interface bandwidth metric parameters";
        reference " 0.1.3.";
    }

    revision "2024-04-10" {
        description "Removed unused imports";
        reference " 0.1.2.";
    }

    revision "2024-03-27" {
        description "Updated Flexible Algorithm ASLA parameters";
        reference " 0.1.1.";
    }

    revision "2024-03-06" {
        description "Updated Flexible Algorithm specific ASLA Interface parameters";
        reference " 0.1.0.";
    }

    grouping isis-interface-flexalgo-config {
        description
            "Configuration items for ISIS interfaces";
        leaf maximum-bandwidth-flex-algo  {
            type  string {
                length "1..1965";
                pattern "(([1-9]{1}[0-9]{0,2}[m|M|k|K]{1})|([1-9]{1}.[0-9]{1}[g|G|m|M|k|K]{1})|([1-9]{1}[0-9]{0,1}[g|G]{1})|(100[g|G]{1}))+";
            }
            description "Interface ASLA maximum bandwidth value for IGP Flexible Algorithm. The
                        bandwidth input ranges are 1 to 999 Kbps, 1 to 999 Mbps and 1 to 100
                        Gbps.";
        } // END of maximum-bandwidth-flex-algo definition.

        leaf disable-asla-usage-flex-algo  {
            type  empty;
            description "Use this attribute to disable ASLA Link attributes usage for
                        flexible-algorithm on this Link. The command with no keyword enables
                        the ASLA usage";
        } // END of disable-asla-usage-flex-algo definition.

    } // END of isis-interface-flexalgo-config definition.
    grouping isis-interface-level-params-flexalgo-config {
        description
            "Configuration items for ISIS interface level Flexible-Algorithm";
        leaf te-metric-flex-algo-ipv4  {
            if-feature feature-list:HAVE_ISIS_TE;
            type  uint32 {
                 range "1..16777215"  {
                    description "1..16777215: Supported range 1 - 16777215";
                 }
            }
            description "Interface IPv4 te-metric for usage in IGP Flexible Algorithm specific
                        CSPF path calculation purposes. This metric is put into Extended IS
                        reachability TLVs and IPv4 reachability TLVs in LSPs.";
        } // END of te-metric-flex-algo-ipv4 definition.

        leaf te-metric-flex-algo-ipv6  {
            if-feature feature-list:HAVE_ISIS_TE;
            type  uint32 {
                 range "1..16777215"  {
                    description "1..16777215: Supported range 1 - 16777215";
                 }
            }
            description "Interface IPv6 te-metric for usage in IGP Flexible Algorithm specific
                        CSPF path calculation purposes. This metric is put into Extended IS
                        reachability TLVs and IPv6 reachability TLVs in LSPs.";
        } // END of te-metric-flex-algo-ipv6 definition.

        leaf bandwidth-metric-ipv4  {
            if-feature feature-list:HAVE_ISIS_TE;
            type  uint32 {
                 range "1..16777215"  {
                    description "1..16777215: Supported range 1 - 16777215";
                 }
            }
            description "Interface IPv4 bandwidth-metric for usage in IGP CSPF path calculation
                        purposes. This metric is put into Extended IS reachability TLVs and
                        IPv4 reachability TLVs in LSPs.";
        } // END of bandwidth-metric-ipv4 definition.

        leaf bandwidth-metric-ipv6  {
            if-feature feature-list:HAVE_ISIS_TE;
            type  uint32 {
                 range "1..16777215"  {
                    description "1..16777215: Supported range 1 - 16777215";
                 }
            }
            description "Interface IPv6 bandwidth-metric for usage in CSPF path calculation
                        purposes. This metric is put into Extended IS reachability TLVs and
                        IPv6 reachability TLVs in LSPs.";
        } // END of bandwidth-metric-ipv6 definition.

        leaf bandwidth-metric-flex-algo-ipv4  {
            if-feature feature-list:HAVE_ISIS_TE;
            type  uint32 {
                 range "1..16777215"  {
                    description "1..16777215: Supported range 1 - 16777215";
                 }
            }
            description "Interface IPv4 bandwidth-metric for usage in IGP Flexible Algorithm
                        specific CSPF path calculation purposes. This metric is put into
                        Extended IS reachability TLVs and IPv4 reachability TLVs in LSPs.";
        } // END of bandwidth-metric-flex-algo-ipv4 definition.

        leaf bandwidth-metric-flex-algo-ipv6  {
            if-feature feature-list:HAVE_ISIS_TE;
            type  uint32 {
                 range "1..16777215"  {
                    description "1..16777215: Supported range 1 - 16777215";
                 }
            }
            description "Interface IPv6 bandwidth-metric for usage in IGP Flexible Algorithm
                        specific CSPF path calculation purposes. This metric is put into
                        Extended IS reachability TLVs and IPv6 reachability TLVs in LSPs.";
        } // END of bandwidth-metric-flex-algo-ipv6 definition.

        leaf te-minimum-delay  {
            type  uint32 {
                 range "1..16777215"  {
                    description "1..16777215: Supported range 1 - 16777215";
                 }
            }
            units "microseconds";
            description "Interface minimum delay value in microseconds.";
        } // END of te-minimum-delay definition.

        leaf te-maximum-delay  {
            type  uint32 {
                 range "1..16777215"  {
                    description "1..16777215: Supported range 1 - 16777215";
                 }
            }
            units "microseconds";
            description "Interface maximum delay value in microseconds.";
        } // END of te-maximum-delay definition.

        leaf te-minimum-delay-flex-algo  {
            type  uint32 {
                 range "1..16777215"  {
                    description "1..16777215: Supported range 1 - 16777215";
                 }
            }
            units "microseconds";
            description "Interface minimum delay value for IGP Flexible Algorithm in
                        microseconds.";
        } // END of te-minimum-delay-flex-algo definition.

        leaf te-maximum-delay-flex-algo  {
            type  uint32 {
                 range "1..16777215"  {
                    description "1..16777215: Supported range 1 - 16777215";
                 }
            }
            units "microseconds";
            description "Interface maximum delay value for IGP Flexible Algorithm in
                        microseconds.";
        } // END of te-maximum-delay-flex-algo definition.

        leaf-list extended-admin-group-flex-algo  {
            if-feature feature-list:HAVE_ISIS_TE;
            type  leafref {
                path  "/ipi-global-te:extended-admin-groups/ipi-global-te:extended-admin-group/ipi-global-te:name";
            }
            description "Use this attribute to assign one or more, extended administrative
                        groups (EAG) for normal delay in the interface for Flexible-Algorithm
                        purposes";
        } // END of extended-admin-group-flex-algo definition.

        leaf-list extended-admin-group-flex-algo-anomaly  {
            if-feature feature-list:HAVE_ISIS_TE;
            type  leafref {
                path  "/ipi-global-te:extended-admin-groups/ipi-global-te:extended-admin-group/ipi-global-te:name";
            }
            description "Use this attribute to assign one or more, extended administrative
                        groups (EAG) for anomalous delay in the interface for
                        Flexible-Algorithm purposes";
        } // END of extended-admin-group-flex-algo-anomaly definition.

        leaf-list admin-group-flex-algo  {
            if-feature feature-list:HAVE_ISIS_TE;
            type  leafref {
                path  "/ipi-global-te:admin-groups/ipi-global-te:admin-group/ipi-global-te:name";
            }
            description "Use this attribute to assign one or more, administrative groups (AG)
                        to the interface for Flexible-Algorithm purposes";
        } // END of admin-group-flex-algo definition.

        leaf-list admin-group-flex-algo-anomaly  {
            if-feature feature-list:HAVE_ISIS_TE;
            type  leafref {
                path  "/ipi-global-te:admin-groups/ipi-global-te:admin-group/ipi-global-te:name";
            }
            description "Use this attribute to assign one or more, administrative groups (AG)
                        for anomalous delay in the interface for Flexible-Algorithm purposes";
        } // END of admin-group-flex-algo-anomaly definition.

        leaf-list shared-risk-link-group-flex-algo  {
            if-feature feature-list:HAVE_SRLG;
            type  uint32 {
                 range "1..4294967295"  {
                    description "1..4294967295: Supported range 1 - 4294967295";
                 }
            }
            description "Use this attribute to add the link to a flexible-algorithm application
                        specific srlg group";
        } // END of shared-risk-link-group-flex-algo definition.

    } // END of isis-interface-level-params-flexalgo-config definition.


}
