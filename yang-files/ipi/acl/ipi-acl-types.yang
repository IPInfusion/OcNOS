/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-acl-types.yang
*
*/

module ipi-acl-types {

    yang-version 1.1;

    namespace   "http://www.ipinfusion.com/yang/ocnos/ipi-acl-types";

    prefix "ipi-acl-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-acl-types";


    revision "2025-04-10" {
        description "Defined a new V6 protocls type for COPP ACL";
        reference " 0.9.2.";
    }

    revision "2025-04-08" {
        description "Added new types including prefix groups";
        reference " 0.9.1.";
    }

    revision "2025-03-07" {
        description "Adding new ACL type IPv6 copp";
        reference " 0.9.0.";
    }

    revision "2024-12-13" {
        description "Adding new ACL type copp";
        reference " 0.8.0.";
    }

    revision "2024-10-06" {
        description "Removing neq option of L4 src/dst port from ip/ipv6 acl";
        reference " 0.7.0.";
    }

    revision "2023-06-12" {
        description "Implementing netconf port feature";
        reference " 0.6.0.";
    }

    revision "2023-04-10" {
        description "Reverting the Fix for Removed none from ACL_ARP_PACKET_TYPE_T";
        reference " 0.5.1.";
    }

    revision "2023-02-22" {
        description "Enforce hexadecimal pattern for ACL_ETHER_HEX_VAL_STRING_T";
        reference " 0.5.0.";
    }

    revision "2022-09-20" {
        description "Corrected IPv6 protocol name ipipv6";
        reference " 0.4.0.";
    }

    revision "2022-06-01" {
        description "Updated the yang file with feature";
        reference " 0.3.2.";
    }

    revision "2022-01-20" {
        description "Merged protocol-name and protocol-value into single attribute protocol-name";
        reference " 0.3.1.";
    }

    revision "2022-01-17" {
        description "Added if-feature";
        reference " 0.3.0.";
    }

    revision "2022-01-04" {
        description "Removed none from ACL_ARP_PACKET_TYPE_T";
        reference " 0.4.1.";
    }

    revision "2021-09-03" {
        description "Update descriptions of attribute";
        reference " 0.2.0.";
    }

    revision "2021-07-14" {
        description "Restructured module as per OpenConfig style";
        reference " 0.1.0.";
    }



    typedef  acl_types_t {
        type enumeration {
            enum mac {
                value 1;
                description "Configure mac parameters";
            }
            enum ip {
                value 3;
                description "Configure ip parameters";
            }
            enum ipv6 {
                value 4;
                description "Configure ipv6 parameters";
            }
            enum arp {
                value 5;
                description "Configure arp parameters";
            }
            enum copp {
                value 8;
                if-feature feature-list:HAVE_COPP_FILTER;
                description "Configure copp parameters";
            }
            enum ipv6-copp {
                value 9;
                if-feature feature-list:HAVE_COPP_FILTER;
                if-feature feature-list:HAVE_IPV6;
                description "Configure IPv6 copp parameters";
            }
        }
        description "type definition for ACL_TYPES_T";
    }

    typedef  acl_standard_types_t {
        type enumeration {
            enum standard_ip {
                value 6;
                description "Internet Protocol (IP)";
            }
            enum standard_ipv6 {
                value 7;
                description "Internet Protocol version 6 (IPv6)";
            }
        }
        description "type definition for ACL_STANDARD_TYPES_T";
    }

    typedef  acl_forwarding_action_t {
        type enumeration {
            enum deny {
                value 0;
                description "Specify packets to reject";
            }
            enum permit {
                value 1;
                description "Specify packets to forward";
            }
        }
        description "type definition for ACL_FORWARDING_ACTION_T";
    }

    typedef  acl_src_port_operations_t {
        type enumeration {
            enum eq {
                value 1;
                description "Source port Equal to";
            }
            enum neq {
                value 2;
                if-feature feature-list:NOT_HAVE_DNX;
                description "Source port not equal to";
            }
            enum lt {
                value 3;
                description "Source port less than";
            }
            enum gt {
                value 4;
                description "Source port greater than";
            }
        }
        description "type definition for ACL_SRC_PORT_OPERATIONS_T";
    }

    typedef  acl_dest_port_operations_t {
        type enumeration {
            enum eq {
                value 1;
                description "Dest. port Equal to";
            }
            enum neq {
                value 2;
                if-feature feature-list:NOT_HAVE_DNX;
                description "Dest. port not equal to";
            }
            enum lt {
                value 3;
                description "Dest. port less than";
            }
            enum gt {
                value 4;
                description "Dest. port greater than";
            }
        }
        description "type definition for ACL_DEST_PORT_OPERATIONS_T";
    }

    typedef  acl_copp_src_port_operations_t {
        type enumeration {
            enum eq {
                value 1;
                description "Source port Equal to";
            }
        }
        description "type definition for ACL_COPP_SRC_PORT_OPERATIONS_T";
    }

    typedef  acl_copp_dest_port_operations_t {
        type enumeration {
            enum eq {
                value 1;
                description "Dest. port Equal to";
            }
        }
        description "type definition for ACL_COPP_DEST_PORT_OPERATIONS_T";
    }

    typedef  acl_default_forwarding_action_t {
        type enumeration {
            enum deny-all {
                value 3;
                description "Specify all packets to reject";
            }
            enum permit-all {
                value 4;
                description "Specify all packets to forward";
            }
        }
        description "type definition for ACL_DEFAULT_FORWARDING_ACTION_T";
    }

    typedef  acl_arp_packet_type_t {
        type enumeration {
            enum none {
                value 0;
                description "Match any ARP packets";
            }
            enum request {
                value 1;
                if-feature feature-list:HAVE_CUSTOM1_ACL;
                description "Match ARP request packets";
            }
            enum response {
                value 2;
                if-feature feature-list:HAVE_CUSTOM1_ACL;
                description "Match ARP response packets";
            }
        }
        description "type definition for ACL_ARP_PACKET_TYPE_T";
    }

    typedef  acl_any_src_t {
        type enumeration {
            enum any {
                value 0;
                description "Any source address";
            }
        }
        description "type definition for ACL_ANY_SRC_T";
    }

    typedef  acl_ipv4_host_src_t {
        type string;
        description "type definition for ACL_IPV4_HOST_SRC_T";
    }

    typedef  acl_ipv4_prefix_src_t {
        type string {
            length 0..32;
        }
        description "type definition for ACL_IPV4_PREFIX_SRC_T";
    }

    typedef  acl_prefix_group_t {
        type string {
            length 1..64;
            pattern "[a-zA-Z0-9][^?' =,>|]*";
        }
        description "type definition for ACL_PREFIX_GROUP_T";
    }

    typedef  acl_any_ipv4_src_addr_t {
        type union {
            type acl_any_src_t {

            }
            type acl_ipv4_host_src_t {

            }
            type acl_ipv4_prefix_src_t {

            }
        }
        description "type definition for ACL_ANY_IPV4_SRC_ADDR_T";
    }

    typedef  acl_any_dest_t {
        type enumeration {
            enum any {
                value 0;
                description "Any destination address";
            }
        }
        description "type definition for ACL_ANY_DEST_T";
    }

    typedef  acl_ipv4_host_dest_t {
        type string;
        description "type definition for ACL_IPV4_HOST_DEST_T";
    }

    typedef  acl_ipv4_prefix_dest_t {
        type string {
            length 0..32;
        }
        description "type definition for ACL_IPV4_PREFIX_DEST_T";
    }

    typedef  acl_any_ipv4_dest_addr_t {
        type union {
            type acl_any_dest_t {

            }
            type acl_ipv4_host_dest_t {

            }
            type acl_ipv4_prefix_dest_t {

            }
        }
        description "type definition for ACL_ANY_IPV4_DEST_ADDR_T";
    }

    typedef  acl_ipv6_prefix_src_t {
        type string {
            length 0..92;
        }
        description "type definition for ACL_IPV6_PREFIX_SRC_T";
    }

    typedef  acl_ipv6_prefix_dest_t {
        type string {
            length 0..92;
        }
        description "type definition for ACL_IPV6_PREFIX_DEST_T";
    }

    typedef  acl_any_ipv6_src_addr_t {
        type union {
            type acl_any_src_t {

            }
            type acl_ipv6_prefix_src_t {

            }
        }
        description "type definition for ACL_ANY_IPV6_SRC_ADDR_T";
    }

    typedef  acl_any_ipv6_dest_addr_t {
        type union {
            type acl_any_dest_t {

            }
            type acl_ipv6_prefix_dest_t {

            }
        }
        description "type definition for ACL_ANY_IPV6_DEST_ADDR_T";
    }

    typedef  acl_copp_ipv6_prefix_src_t {
        type string {
            length 0..92;
        }
        description "type definition for ACL_COPP_IPV6_PREFIX_SRC_T";
    }

    typedef  acl_copp_ipv6_prefix_dest_t {
        type string {
            length 0..92;
        }
        description "type definition for ACL_COPP_IPV6_PREFIX_DEST_T";
    }

    typedef  acl_copp_any_ipv6_src_addr_t {
        type union {
            type acl_any_src_t {

            }
            type acl_copp_ipv6_prefix_src_t {

            }
        }
        description "type definition for ACL_COPP_ANY_IPV6_SRC_ADDR_T";
    }

    typedef  acl_copp_any_ipv6_dest_addr_t {
        type union {
            type acl_any_dest_t {

            }
            type acl_copp_ipv6_prefix_dest_t {

            }
        }
        description "type definition for ACL_COPP_ANY_IPV6_DEST_ADDR_T";
    }

    typedef  acl_udp_keyword_t {
        type enumeration {
            enum echo {
                value 7;
                description "Echo (7)";
            }
            enum discard {
                value 9;
                description "Discard (9)";
            }
            enum time {
                value 37;
                description "Time (37)";
            }
            enum nameserver {
                value 42;
                description "IEN116 name service (obsolete 42)";
            }
            enum tacacs {
                value 49;
                description "TAC Access Control System (49)";
            }
            enum domain {
                value 53;
                description "Domain Name Service (DNS 53)";
            }
            enum bootps {
                value 67;
                description "Bootstrap Protocol (BOOTP) server (67)";
            }
            enum bootpc {
                value 68;
                description "Bootstrap Protocol (BOOTP) client (68)";
            }
            enum tftp {
                value 69;
                description "Trivial File Transfer Protocol (69)";
            }
            enum sunrpc {
                value 111;
                description "Sun Remote Procedure Call (111)";
            }
            enum ntp {
                value 123;
                description "Network Time Protocol (123)";
            }
            enum netbios-ns {
                value 137;
                description "NetBIOS name service (137)";
            }
            enum netbios-dgm {
                value 138;
                description "NetBIOS datagram service (138)";
            }
            enum netbios-ss {
                value 139;
                description "NetBIOS session service (139)";
            }
            enum snmp {
                value 161;
                description "Simple Network Management Protocol (161)";
            }
            enum snmptrap {
                value 162;
                description "SNMP Traps (162)";
            }
            enum xdmcp {
                value 177;
                description "X Display Manager Control Protocol (177)";
            }
            enum dnsix {
                value 195;
                description "DNSIX security protocol auditing (195)";
            }
            enum mobile-ip {
                value 434;
                description "Mobile IP registration (434)";
            }
            enum pim-auto-rp {
                value 496;
                description "PIM Auto-RP (496)";
            }
            enum isakmp {
                value 500;
                description "Internet Security Association and Key Management Protocol (500)";
            }
            enum biff {
                value 512;
                description "Biff (mail notification comsat 512)";
            }
            enum who {
                value 513;
                description "Who service (rwho 513)";
            }
            enum syslog {
                value 514;
                description "System Logger (514)";
            }
            enum talk {
                value 517;
                description "Talk (517)";
            }
            enum rip {
                value 520;
                description "Routing Information Protocol (router in.routed 520)";
            }
            enum non500-isakmp {
                value 4500;
                description "Non500-Internet Security Association and Key Management Protocol (4500)";
            }
        }
        description "type definition for ACL_UDP_KEYWORD_T";
    }

    typedef  acl_udp_src_port_t {
        type union {
            type acl_udp_keyword_t {

            }
            type uint32 {
                range "0..65535";

            }
        }
        description "type definition for ACL_UDP_SRC_PORT_T";
    }

    typedef  acl_udp_dest_port_t {
        type union {
            type acl_udp_keyword_t {

            }
            type uint32 {
                range "0..65535";

            }
        }
        description "type definition for ACL_UDP_DEST_PORT_T";
    }

    typedef  acl_tcp_keyword_t {
        type enumeration {
            enum echo {
                value 7;
                description "Echo (7)";
            }
            enum discard {
                value 9;
                description "Discard (9)";
            }
            enum daytime {
                value 13;
                description "Daytime (13)";
            }
            enum chargen {
                value 19;
                description "Character generator (19)";
            }
            enum ftp-data {
                value 20;
                description "FTP data connections (20)";
            }
            enum ftp {
                value 21;
                description "File Transfer Protocol (21)";
            }
            enum ssh {
                value 22;
                description "Secure Shell (22)";
            }
            enum telnet {
                value 23;
                description "Telnet (23)";
            }
            enum smtp {
                value 25;
                description "Simple Mail Transport Protocol (25)";
            }
            enum time {
                value 37;
                description "Time (37)";
            }
            enum whois {
                value 43;
                description "WHOIS/NICNAME (43)";
            }
            enum tacacs {
                value 49;
                description "TAC Access Control System (49)";
            }
            enum domain {
                value 53;
                description "Domain Name Service (53)";
            }
            enum gopher {
                value 70;
                description "Gopher (70)";
            }
            enum finger {
                value 79;
                description "Finger (79)";
            }
            enum www {
                value 80;
                description "World Wide Web (HTTP 80)";
            }
            enum hostname {
                value 101;
                description "NIC hostname server (101)";
            }
            enum pop2 {
                value 109;
                description "Post Office Protocol v2 (109)";
            }
            enum pop3 {
                value 110;
                description "Post Office Protocol v3 (110)";
            }
            enum sunrpc {
                value 111;
                description "Sun Remote Procedure Call (111)";
            }
            enum ident {
                value 113;
                description "Ident Protocol (113)";
            }
            enum nntp {
                value 119;
                description "Network News Transport Protocol (119)";
            }
            enum bgp {
                value 179;
                description "Border Gateway Protocol (179)";
            }
            enum irc {
                value 194;
                description "Internet Relay Chat (194)";
            }
            enum pim-auto-rp {
                value 496;
                description "PIM Auto-RP (496)";
            }
            enum exec {
                value 512;
                description "EXEC (rsh 512)";
            }
            enum login {
                value 513;
                description "Login (rlogin 513)";
            }
            enum cmd {
                value 514;
                description "Remote commands (rcmd 514)";
            }
            enum lpd {
                value 515;
                description "Printer service (515)";
            }
            enum talk {
                value 517;
                description "Talk (517)";
            }
            enum uucp {
                value 540;
                description "UNIX-to-UNIX Copy Program (540)";
            }
            enum klogin {
                value 543;
                description "Kerberos login (543)";
            }
            enum kshell {
                value 544;
                description "Kerberos shell (544)";
            }
            enum netconf-ssh {
                value 830;
                description "Secure Shell Network Configuration (830)";
            }
            enum drip {
                value 3949;
                description "Dynamic Routing Information Protocol (3949)";
            }
            enum netconf-tls {
                value 6513;
                description "Transport Layer Security Network Configuration (6513)";
            }
        }
        description "type definition for ACL_TCP_KEYWORD_T";
    }

    typedef  acl_tcp_src_port_t {
        type union {
            type acl_tcp_keyword_t {

            }
            type uint32 {
                range "0..65535";

            }
        }
        description "type definition for ACL_TCP_SRC_PORT_T";
    }

    typedef  acl_tcp_dest_port_t {
        type union {
            type acl_tcp_keyword_t {

            }
            type uint32 {
                range "0..65535";

            }
        }
        description "type definition for ACL_TCP_DEST_PORT_T";
    }

    typedef  acl_ip_protocol_names_t {
        type enumeration {
            enum igmp {
                value 2;
                description "Internet Group Management Protocol (2)";
            }
            enum ipip {
                value 4;
                description "IPv4 Encapsulation within IPv4 packet (4)";
            }
            enum ipv6ip {
                value 41;
                description "IPv6 Encapsulation within IPv4 packet (41)";
            }
            enum rsvp {
                value 46;
                description "Resource ReSerVation Protocol (46)";
            }
            enum gre {
                value 47;
                description "Generic Routing Encapsulation (47)";
            }
            enum esp {
                value 50;
                description "Encapsulating Security Payload (50)";
            }
            enum ahp {
                value 51;
                description "Authentication Header Protocol (51)";
            }
            enum eigrp {
                value 88;
                description "Enhanced Interior Gateway Routing Protocol (88)";
            }
            enum ospf {
                value 89;
                description "Open Shortest Path First protocol (89)";
            }
            enum pim {
                value 103;
                description "Protocol Independent Multicast (103)";
            }
            enum ipcomp {
                value 108;
                description "IP payload COMPression Protocol (108)";
            }
            enum vrrp {
                value 112;
                description "Virtual Router Redundancy Protocol (112)";
            }
            enum any {
                value 256;
                description "Any IP protocol";
            }
        }
        description "type definition for ACL_IP_PROTOCOL_NAMES_T";
    }

    typedef  acl_ip_protocols_t {
        type union {
            type acl_ip_protocol_names_t {

            }
            type uint8 {
                range "0..255";

            }
        }
        description "type definition for ACL_IP_PROTOCOLS_T";
    }

    typedef  acl_ipv6_protocol_names_t {
        type enumeration {
            enum ipipv6 {
                value 4;
                description "IPv4 Encapsulation within IPv6 packet (4)";
            }
            enum ipv6ipv6 {
                value 41;
                description "IPv6 Encapsulation within IPv6 packet (41)";
            }
            enum rsvp {
                value 46;
                description "Resource ReSerVation Protocol (46)";
            }
            enum gre {
                value 47;
                description "Generic Routing Encapsulation (47)";
            }
            enum esp {
                value 50;
                description "Encapsulating Security Payload (50)";
            }
            enum ahp {
                value 51;
                description "Authentication Header Protocol (51)";
            }
            enum ospf {
                value 89;
                description "Open Shortest Path First protocol (89)";
            }
            enum pim {
                value 103;
                description "Protocol Independent Multicast (103)";
            }
            enum ipcomp {
                value 108;
                description "IP payload COMPression Protocol (108)";
            }
            enum vrrp {
                value 112;
                description "Virtual Router Redundancy Protocol (112)";
            }
            enum any {
                value 256;
                description "Any IPv6 protocol ";
            }
        }
        description "type definition for ACL_IPV6_PROTOCOL_NAMES_T";
    }

    typedef  acl_copp_ipv6_protocol_names_t {
        type enumeration {
            enum ipipv6 {
                value 4;
                description "IPv4 Encapsulation within IPv6 packet (4)";
            }
            enum ipv6ipv6 {
                value 41;
                description "IPv6 Encapsulation within IPv6 packet (41)";
            }
            enum ipv6-route-header {
                value 43;
                if-feature feature-list:HAVE_COPP_FILTER;
                description "Routing Header for IPv6 (43)";
            }
            enum rsvp {
                value 46;
                description "Resource ReSerVation Protocol (46)";
            }
            enum gre {
                value 47;
                description "Generic Routing Encapsulation (47)";
            }
            enum esp {
                value 50;
                description "Encapsulating Security Payload (50)";
            }
            enum ahp {
                value 51;
                description "Authentication Header Protocol (51)";
            }
            enum ipv6-opts {
                value 60;
                if-feature feature-list:HAVE_COPP_FILTER;
                description "Destination Options for IPv6 (60)";
            }
            enum ospf {
                value 89;
                description "Open Shortest Path First protocol (89)";
            }
            enum pim {
                value 103;
                description "Protocol Independent Multicast (103)";
            }
            enum ipcomp {
                value 108;
                description "IP payload COMPression Protocol (108)";
            }
            enum vrrp {
                value 112;
                description "Virtual Router Redundancy Protocol (112)";
            }
            enum any {
                value 256;
                description "Any IPv6 protocol ";
            }
        }
        description "type definition for ACL_COPP_IPV6_PROTOCOL_NAMES_T";
    }

    typedef  acl_ipv6_protocols_t {
        type union {
            type acl_ipv6_protocol_names_t {

            }
            type uint8 {
                range "0..255";

            }
        }
        description "type definition for ACL_IPV6_PROTOCOLS_T";
    }

    typedef  acl_copp_ipv6_protocols_t {
        type union {
            type acl_copp_ipv6_protocol_names_t {

            }
            type uint8 {
                range "0..255";

            }
        }
        description "type definition for ACL_COPP_IPV6_PROTOCOLS_T";
    }

    typedef  acl_dscp_class_type_t {
        type enumeration {
            enum default {
                value 0;
                description "Default dscp (000000) decimal value 0";
            }
            enum cs1 {
                value 8;
                description "CS1 (precedence 1) dscp (001000) decimal value 8";
            }
            enum af11 {
                value 10;
                description "AF11 dscp (001010) decimal value 10";
            }
            enum af12 {
                value 12;
                description "AF12 dscp (001100) decimal value 12";
            }
            enum af13 {
                value 14;
                description "AF13 dscp (001110) decimal value 14";
            }
            enum cs2 {
                value 16;
                description "CS2 (precedence 2) dscp (010000) decimal value 16";
            }
            enum af21 {
                value 18;
                description "AF21 dscp (010010) decimal value 18";
            }
            enum af22 {
                value 20;
                description "AF22 dscp (010100) decimal value 20";
            }
            enum af23 {
                value 22;
                description "AF23 dscp (010110) decimal value 22";
            }
            enum cs3 {
                value 24;
                description "CS3 (precedence 3) dscp (011000) decimal value 24";
            }
            enum af31 {
                value 26;
                description "AF31 dscp (011010) decimal value 26";
            }
            enum af32 {
                value 28;
                description "AF32 dscp (011100) decimal value 28";
            }
            enum af33 {
                value 30;
                description "AF33 dscp (011110) decimal value 30";
            }
            enum cs4 {
                value 32;
                description "CS4 (precedence 4) dscp (100000) decimal value 32";
            }
            enum af41 {
                value 34;
                description "AF41 dscp (100010) decimal value 34";
            }
            enum af42 {
                value 36;
                description "AF42 dscp (100100) decimal value 36";
            }
            enum af43 {
                value 38;
                description "AF43 dscp (100110) decimal value 38";
            }
            enum cs5 {
                value 40;
                description "CS5 (precedence 5) dscp (101000) decimal value 40";
            }
            enum ef {
                value 46;
                description "EF dscp (101110) decimal value 46";
            }
            enum cs6 {
                value 48;
                description "CS6 (precedence 6) dscp (110000) decimal value 48";
            }
            enum cs7 {
                value 56;
                description "CS7 (precedence 7) dscp (111000) decimal value 56";
            }
        }
        description "type definition for ACL_DSCP_CLASS_TYPE_T";
    }

    typedef  acl_dscp_t {
        type union {
            type acl_dscp_class_type_t {

            }
            type int8 {
                range "0..63";

            }
        }
        description "type definition for ACL_DSCP_T";
    }

    typedef  acl_precedence_type_t {
        type enumeration {
            enum routine {
                value 0;
                description "Match packets with routine precedence (0)";
            }
            enum priority {
                value 1;
                description "Match packets with priority precedence (1)";
            }
            enum immediate {
                value 2;
                description "Match packets with immediate precedence (2)";
            }
            enum flash {
                value 3;
                description "Match packets with flash precedence (3)";
            }
            enum flashoverride {
                value 4;
                description "Match packets with flash override precedence (4)";
            }
            enum critical {
                value 5;
                description "Match packets with critical precedence (5)";
            }
            enum internet {
                value 6;
                description "Match packets with internetwork control precedence (6)";
            }
            enum network {
                value 7;
                description "Match packets with network control precedence (7)";
            }
        }
        description "type definition for ACL_PRECEDENCE_TYPE_T";
    }

    typedef  acl_precedence_t {
        type union {
            type acl_precedence_type_t {

            }
            type int8 {
                range "0..7";

            }
        }
        description "type definition for ACL_PRECEDENCE_T";
    }

    typedef  acl_icmp_options_t {
        type enumeration {
            enum administratively-prohibited {
                value 1;
                description "Administratively Prohibited";
            }
            enum alternate-address {
                value 2;
                description "Alternate Address";
            }
            enum conversion-error {
                value 3;
                description "Datagram Conversion";
            }
            enum dod-host-prohibited {
                value 4;
                description "Host Prohibited";
            }
            enum dod-net-prohibited {
                value 5;
                description "Net Prohibited";
            }
            enum echo {
                value 6;
                description "Echo (Ping)";
            }
            enum echo-reply {
                value 7;
                description "Echo Reply";
            }
            enum general-parameter-problem {
                value 8;
                description "Parameter Problem";
            }
            enum host-isolated {
                value 9;
                description "Host Isolated";
            }
            enum host-precedence-unreachable {
                value 10;
                description "Host Unreachable for precedence";
            }
            enum host-redirect {
                value 11;
                description "Host Redirect";
            }
            enum host-tos-redirect {
                value 12;
                description "Host Redirect for ToS";
            }
            enum host-tos-unreachable {
                value 13;
                description "Host Unreachable for ToS";
            }
            enum host-unknown {
                value 14;
                description "Host Unknown";
            }
            enum host-unreachable {
                value 15;
                description "Host Unreachable";
            }
            enum information-reply {
                value 16;
                description "Information Replies";
            }
            enum information-request {
                value 17;
                description "Information Requests";
            }
            enum mask-reply {
                value 18;
                description "Mask Replies";
            }
            enum mask-request {
                value 19;
                description "Mask Requests";
            }
            enum mobile-redirect {
                value 20;
                description "Mobile host redirect";
            }
            enum net-redirect {
                value 21;
                description "Network Redirect";
            }
            enum net-tos-redirect {
                value 22;
                description "Network Redirect for Tos";
            }
            enum net-tos-unreachable {
                value 23;
                description "Network Unreachable for Tos";
            }
            enum net-unreachable {
                value 24;
                description "Network Unreachable";
            }
            enum network-unknown {
                value 25;
                description "Network Unknown";
            }
            enum no-room-for-option {
                value 26;
                description "Parameter required but no room";
            }
            enum option-missing {
                value 27;
                description "Parameter required but not present";
            }
            enum packet-too-big {
                value 28;
                description "Fragmentation needed and DF set";
            }
            enum parameter-problem {
                value 29;
                description "All Parameter Problems";
            }
            enum port-unreachable {
                value 30;
                description "Port Unreachable";
            }
            enum precedence-unreachable {
                value 31;
                description "Precedence cutoff";
            }
            enum protocol-unreachable {
                value 32;
                description "Protocol Unreachable";
            }
            enum reassembly-timeout {
                value 33;
                description "Reassembly Timeout";
            }
            enum redirect {
                value 34;
                description "All redirects";
            }
            enum router-advertisement {
                value 35;
                description "Router Discovery Advertisements";
            }
            enum router-solicitation {
                value 36;
                description "Router Discovery Solicitations";
            }
            enum source-quench {
                value 37;
                description "Source Quenches";
            }
            enum source-route-failed {
                value 38;
                description "Source Route Failed";
            }
            enum time-exceeded {
                value 39;
                description "All time-exceeded messages";
            }
            enum timestamp-reply {
                value 40;
                description "Time-stamp replies";
            }
            enum timestamp-request {
                value 41;
                description "Time-stamp requests";
            }
            enum traceroute {
                value 42;
                description "Traceroute";
            }
            enum ttl-exceeded {
                value 43;
                description "TTL Exceeded";
            }
            enum unreachable {
                value 44;
                description "All unreachables";
            }
        }
        description "type definition for ACL_ICMP_OPTIONS_T";
    }

    typedef  acl_icmpv6_options_t {
        type enumeration {
            enum beyond-scope {
                value 0;
                description "Destination beyond scope";
            }
            enum destination-unreachable {
                value 1;
                description "Destination address is unreachable";
            }
            enum echo-reply {
                value 2;
                description "Echo reply";
            }
            enum echo-request {
                value 3;
                description "Echo request (ping)";
            }
            enum header {
                value 4;
                description "Parameter header problems";
            }
            enum hop-limit {
                value 5;
                description "Hop limit exceeded in transit";
            }
            enum mld-query {
                value 6;
                description "Multicast Listener Discovery Query";
            }
            enum mld-reduction {
                value 7;
                description "Multicast Listener Discovery Reduction";
            }
            enum mld-report {
                value 8;
                description "Multicast Listener Discovery Report";
            }
            enum nd-na {
                value 9;
                description "Neighbor discovery neighbor advertisements";
            }
            enum nd-ns {
                value 10;
                description "Neighbor discovery neighbor solicitations";
            }
            enum next-header {
                value 11;
                description "Parameter next header problems";
            }
            enum no-admin {
                value 12;
                description "Administration prohibited destination";
            }
            enum no-route {
                value 13;
                description "No route to destination";
            }
            enum packet-too-big {
                value 14;
                description "Packet too big";
            }
            enum parameter-option {
                value 15;
                description "Parameter option problems";
            }
            enum parameter-problem {
                value 16;
                description "All parameter problems";
            }
            enum port-unreachable {
                value 17;
                description "Port unreachable";
            }
            enum reassembly-timeout {
                value 18;
                description "Reassembly timeout";
            }
            enum redirect {
                value 19;
                description "Neighbor redirect";
            }
            enum renum-command {
                value 20;
                description "Router renumbering command";
            }
            enum renum-result {
                value 21;
                description "Router renumbering result";
            }
            enum renum-seq-number {
                value 22;
                description "Router renumbering sequence number reset";
            }
            enum router-advertisement {
                value 23;
                description "Neighbor discovery router advertisements";
            }
            enum router-renumbering {
                value 24;
                description "All router renumbering";
            }
            enum router-solicitation {
                value 25;
                description "Neighbor discovery router solicitations";
            }
            enum time-exceeded {
                value 26;
                description "All time exceeded messages";
            }
            enum unreachable {
                value 27;
                description "All unreachable";
            }
        }
        description "type definition for ACL_ICMPV6_OPTIONS_T";
    }

    typedef  acl_tcp_flags_t {
        type bits {
            bit fin {
                position 0;
                description "Match on the Finish(fin) bit";
            }
            bit syn {
                position 1;
                description "Match on the Synchronize(syn) bit";
            }
            bit rst {
                position 2;
                description "Match on the Reset(rst) bit";
            }
            bit psh {
                position 3;
                description "Match on the Push(psh) bit";
            }
            bit ack {
                position 4;
                description "Match on the Acknowledgment(ack) bit";
            }
            bit urg {
                position 5;
                description "Match on the Urgent(urg) bit";
            }
            bit established {
                position 6;
                description "matches only packets that belong to an established TCP connection";
            }
        }
        description "type definition for ACL_TCP_FLAGS_T";
    }

    typedef  acl_arp_type_t {
        type enumeration {
            enum none {
                value 0;
                description "any ARP packets";
            }
            enum request {
                value 1;
                description "arp request";
            }
            enum response {
                value 2;
                description "arp response";
            }
        }
        description "type definition for ACL_ARP_TYPE_T";
    }

    typedef  acl_mac_addr_t {
        type string {
            pattern "[0-9a-fA-F]{1,4}\\.[0-9a-fA-F]{1,4}\\.[0-9a-fA-F]{1,4}|[0-9a-fA-F]{2}\\-[0-9a-fA-F]{2}\\-[0-9a-fA-F]{2}\\-[0-9a-fA-F]{2}\\-[0-9a-fA-F]{2}\\-[0-9a-fA-F]{2}|[0-9a-fA-F]{2}:[0-9a-fA-F]{2}:[0-9a-fA-F]{2}:[0-9a-fA-F]{2}:[0-9a-fA-F]{2}:[0-9a-fA-F]{2}";
        }
        description "type definition for ACL_MAC_ADDR_T";
    }

    typedef  acl_ether_type_val_t {
        type enumeration {
            enum ipv4 {
                value 2048;
                description "Ethertype 0x0800";
            }
            enum vines-echo {
                value 2991;
                description "Ethertype 0x0baf";
            }
            enum etype-6000 {
                value 24576;
                description "Ethertype 0x6000";
            }
            enum mop-dump {
                value 24577;
                description "Ethertype 0x6001";
            }
            enum mop-console {
                value 24578;
                description "Ethertype 0x6002";
            }
            enum decnet-iv {
                value 24579;
                description "Ethertype 0x6003";
            }
            enum lat {
                value 24580;
                description "Ethertype 0x6004";
            }
            enum diagnostic {
                value 24581;
                description "Ethertype 0x6005";
            }
            enum lavc-sca {
                value 24583;
                description "Ethertype 0x6007";
            }
            enum etype-8042 {
                value 32834;
                description "Ethertype 0x8042";
            }
            enum appletalk {
                value 32923;
                description "Ethertype 0x809b";
            }
            enum aarp {
                value 33011;
                description "Ethertype 0x80f3";
            }
            enum ipv6 {
                value 34525;
                description "Ethertype 0x86dd";
            }
            enum mpls {
                value 34887;
                description "Ethertype 0x8847";
            }
        }
        description "type definition for ACL_ETHER_TYPE_VAL_T";
    }

    typedef  acl_ether_hex_val_string_t {
        type string {
            length 5..6;
            pattern "0x[0-9a-fA-F]+";
        }
        description "type definition for ACL_ETHER_HEX_VAL_STRING_T";
    }

    typedef  acl_ether_type_t {
        type union {
            type acl_ether_type_val_t {

            }
            type acl_ether_hex_val_string_t {

            }
        }
        description "type definition for ACL_ETHER_TYPE_T";
    }

    typedef  acl_vty_types_t {
        type enumeration {
            enum ip {
                value 0;
                description "Internet Protocol (IP)";
            }
            enum ipv6 {
                value 1;
                description "Internet Protocol version 6 (IPv6)";
            }
        }
        description "type definition for ACL_VTY_TYPES_T";
    }

    typedef  acl_fragment_forwarding_action_t {
        type enumeration {
            enum deny-all {
                value 3;
                description "Specify all packets to reject";
            }
            enum permit-all {
                value 4;
                description "Specify all packets to forward";
            }
        }
        description "type definition for ACL_FRAGMENT_FORWARDING_ACTION_T";
    }

    typedef  acl_monitor_action_t {
        type enumeration {
            enum log {
                value 1;
                description "Log the packets matching the filter (in-direction only)";
            }
            enum sample {
                value 2;
                description "Sample the packets matching the filter (in-direction only)";
            }
        }
        description "type definition for ACL_MONITOR_ACTION_T";
    }

    typedef  acl_filter_direction_t {
        type bits {
            bit ingress {
                position 1;
                description "Inbound traffic";
            }
            bit egress {
                position 2;
                description "Outbound traffic";
            }
        }
        description "type definition for ACL_FILTER_DIRECTION_T";
    }

    typedef  acl_interface_type_t {
        type enumeration {
            enum router {
                value 0;
                description "Layer3 interface";
            }
            enum port {
                value 1;
                description "Layer2 interface";
            }
        }
        description "type definition for ACL_INTERFACE_TYPE_T";
    }

    typedef  acl_interface_status_t {
        type enumeration {
            enum inactive {
                value 0;
                description "Interface down";
            }
            enum active {
                value 1;
                description "Interface up and running";
            }
        }
        description "type definition for ACL_INTERFACE_STATUS_T";
    }

}
