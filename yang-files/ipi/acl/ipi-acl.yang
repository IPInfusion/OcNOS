/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-acl.yang
*
*/

module ipi-acl {

    yang-version 1.1;

    namespace   "http://www.ipinfusion.com/yang/ocnos/ipi-acl";

    prefix "ipi-acl";

    import ipi-acl-types {
        prefix ipi-acl-types;
        revision-date 2025-04-10;
    }

    import cml-data-types {
        prefix cml-data-types;
        revision-date 2026-05-15;
    }

    import ipi-acl-common {
        prefix ipi-acl-common;
        revision-date 2025-07-18;
    }

    import ietf-yang-types {
        prefix yang;
        revision-date 2013-07-15;
    }

    import feature-list {
        prefix feature-list;
        revision-date 2026-09-15;
    }

    include ipi-acl-arp { revision-date 2025-08-18;}
    include ipi-acl-copp { revision-date 2025-08-22;}
    include ipi-acl-ipv6 { revision-date 2025-08-08;}
    include ipi-acl-mac { revision-date 2025-09-15;}
    include ipi-acl-ports { revision-date 2025-12-29;}
    organization
        "IP Infusion Inc.";

    contact
        "Address: 3965 Freedom Circle, Suite 200, Santa Clara, CA 95054
         Phone: +1 408-400-1900
         E-mail: support@ipinfusion.com
         Web: http://www.ipinfusion.com/";

    description
        "Datamodel for Access Control List (ACL) object";


    revision "2025-12-29" {
        description "Fixed the time-range removal when the access-group is associated with the interface.";
        reference " 0.13.35.";
    }

    revision "2025-09-15" {
        description "learning disable option update";
        reference " 0.13.34.";
    }

    revision "2025-09-10" {
        description "Added when tag for encapsulation in egress-acl-set";
        reference " 0.13.33.";
    }

    revision "2025-09-08" {
        description "Inclusion of streaming telemetry yaml file for ACL counters";
        reference " 0.13.32.";
    }

    revision "2025-09-04" {
        description "Removed EVPN_IRB_IF_MODE while configuring IRB interface";
        reference " 0.13.31.";
    }

    revision "2025-08-22" {
        description "Inclusion of streaming telemetry yaml file for ACL COPP module";
        reference " 0.13.30.";
    }

    revision "2025-08-20" {
        description "Inclusion of streaming telemetry yaml file for ACL MAC module";
        reference " 0.13.29.";
    }

    revision "2025-08-18" {
        description "Inclusion of streaming telemetry yaml file for ACL ARP module";
        reference " 0.13.28.";
    }

    revision "2025-08-08" {
        description "Inclusion of streaming telemetry yaml file";
        reference " 0.13.27.";
    }

    revision "2025-07-31" {
        description "Added dependent obejct for standard acl before attaching the vty interface";
        reference " 0.13.26.";
    }

    revision "2025-06-22" {
        description "Compilation fix removing unsed import tag ";
        reference " 0.13.25.";
    }

    revision "2025-06-11" {
        description "Removing fragments permit-all/deny-all cli";
        reference " 0.13.24.";
    }

    revision "2025-06-08" {
        description "learning disable option for mac access control";
        reference " 0.13.23.";
    }

    revision "2025-05-15" {
        description "Adding remark support form CoPP access-lists";
        reference " 0.13.22.";
    }

    revision "2025-05-14" {
        description "Removed default value for log-action in copp access-list";
        reference " 0.13.21.";
    }

    revision "2025-05-08" {
        description "Blocked Fragment option for TD4";
        reference " 0.13.20.";
    }

    revision "2025-05-02" {
        description "Updated flags for CoPP log-action";
        reference " 0.13.19.";
    }

    revision "2025-04-28" {
        description "Updated flag with reset for CoPP log-action";
        reference " 0.13.18.";
    }

    revision "2025-04-22" {
        description "Added default values for resequence attributes";
        reference " 0.13.17.";
    }

    revision "2025-04-10" {
        description "Moved COPP IPv6 protocol types into a new type";
        reference " 0.13.16.";
    }

    revision "2025-04-08" {
        description "Added new types for copp including prefix groups";
        reference " 0.13.15.";
    }

    revision "2025-04-01" {
        description "Adding new flag to log-action in ipi-acl-copp";
        reference " 0.13.14.";
    }

    revision "2025-03-07" {
        description "New IPv6 CoPP ACL added";
        reference " 0.13.13.";
    }

    revision "2025-02-28" {
        description "Refactor upgrade functions";
        reference " 0.13.12.";
    }

    revision "2025-01-06" {
        description "ACL configuration should be removed from Db on mapping mlag";
        reference " 0.13.10.";
    }

    revision "2024-12-19" {
        description "Add dependency to line-vty for deletion of acl-sets";
        reference " 0.13.9.";
    }

    revision "2024-12-13" {
        description "Added new ACL of type copp";
        reference " 0.13.8.";
    }

    revision "2024-12-10" {
        description "Hitless merge is now skipped on all attributes";
        reference " 0.13.7.";
    }

    revision "2024-11-14" {
        description "Removed optional-attribute for time-range";
        reference " 0.13.6.";
    }

    revision "2024-10-06" {
        description "Removing neq option of L4 src/dst port from ip/ipv6 acl";
        reference " 0.13.5.";
    }

    revision "2024-05-02" {
        description "Add flag to support replace operation on acl match attributes";
        reference " 0.13.4.";
    }

    revision "2024-03-21" {
        description "Added ip acl support for IRB interface";
        reference " 0.13.3.";
    }

    revision "2024-01-13" {
        description "Some attributes removed from ipi-acl-copp";
        reference " 0.13.11.";
    }

    revision "2023-12-22" {
        description "Added when tag for encapsulation in ingress-acl-set(jira-75279)";
        reference " 0.13.2.";
    }

    revision "2023-07-07" {
        description "initialized flag is removed from attribute from non-presence container";
        reference " 0.13.1.";
    }

    revision "2023-06-12" {
        description "Implementing netconf port feature";
        reference " 0.13.0.";
    }

    revision "2023-04-10" {
        description "Reverting Fix for Supported the ETHTYPE for ARP protocol";
        reference " 0.12.1.";
    }

    revision "2023-02-22" {
        description "Enforce hexadecimal pattern for ACL_ETHER_HEX_VAL_STRING_T";
        reference " 0.12.0.";
    }

    revision "2022-11-24" {
        description "Removed empty container related table entries from trigger acl_ipv4_resequencing.";
        reference " 0.10.7.";
    }

    revision "2022-09-29" {
        description "Updated the name of mrib module in smi-server-modules tag";
        reference " 0.10.6.";
    }

    revision "2022-09-20" {
        description "Corrected IPv6 protocol name ipipv6";
        reference " 0.10.5.";
    }

    revision "2022-08-10" {
        description "Updated smi-server-modules tag paramters";
        reference " 0.10.4.";
    }

    revision "2022-08-08" {
        description "Add dependency to interfaces for deletion of acl-sets";
        reference " 0.10.3.";
    }

    revision "2022-07-30" {
        description "Updated when expressions in yang";
        reference " 0.10.2.";
    }

    revision "2022-07-28" {
        description "Updated smi-server-modules with restructured RIPng module name";
        reference " 0.10.1.";
    }

    revision "2022-07-26" {
        description "Corrected RIP datamodel as per Open Config style";
        reference " 0.10.0.";
    }

    revision "2022-07-08" {
        description "Updated IPv6 default ICMPv6 rule command";
        reference " 0.9.4.";
    }

    revision "2022-06-27" {
        description "Updated when expressions in yang file";
        reference " 0.9.3.";
    }

    revision "2022-06-01" {
        description "Updated the yang file with feature";
        reference " 0.9.2.";
    }

    revision "2022-02-12" {
        description "Updated acl-entry auto-deletion triggers";
        reference " 0.11.0.";
    }

    revision "2022-01-20" {
        description "Merged protocol-name and protocol-value into single attribute protocol-name";
        reference " 0.9.1.";
    }

    revision "2022-01-17" {
        description "Modified sub module";
        reference " 0.9.0.";
    }

    revision "2022-01-04" {
        description "Supported the ETHTYPE for ARP protocol";
        reference " 0.11.1.";
    }

    revision "2021-11-16" {
        description "Added some if-feature to fix customer SKU compilation";
        reference " 0.8.1.";
    }

    revision "2021-10-29" {
        description "Remove RDN from forwarding-action for IPv4 Standard ACLs";
        reference " 0.8.0.";
    }

    revision "2021-09-17" {
        description "Moved 'destination-mac-options' from ipi-acl-common module to ipi-acl-mac and ipi-acl-arp modules";
        reference " 0.7.0.";
    }

    revision "2021-09-03" {
        description "Update descriptions of attribute";
        reference " 0.6.0.";
    }

    revision "2021-08-18" {
        description "Updated sequence-id range to include the sequence-id of default icmpv6 entry, changed acl-entry to CONFIG_RUNTIME";
        reference " 0.5.0.";
    }

    revision "2021-08-16" {
        description "Added dependencies in acl-ports datamodel for correcting the order of API execution";
        reference " 0.4.0.";
    }

    revision "2021-08-02" {
        description "Changed acl-name as RDN in acl-ports datamodel";
        reference " 0.3.0.";
    }

    revision "2021-07-14" {
        description "Restructured module as per OpenConfig style";
        reference " 0.2.0.";
    }

    revision "2017-05-23" {
        description "Initial Version";
        reference " 0.1.0.";
    }

    grouping acl-set-config {
        description
            "Configuration data for ACL set";
        leaf name  {
            type  string {
                length "1..64";
                pattern "[a-zA-Z0-9][^?' =,>|]*";
            }
            description "The name of the access-list set";
        } // END of name definition.

        leaf type  {
            type  ipi-acl-types:acl_types_t;
            description "Type indicates the fields allowed in the ACL entries belonging to the
                        ACL set (e.g., ip, ipv6, etc.)";
        } // END of type definition.

        leaf description  {
            type  cml-data-types:cml_line_t {
                length "1..100";
            }
            description "Description, or comment, for the ACL set";
        } // END of description definition.

        leaf ipv6-disable-default-icmpv6-rule  {
            // when " ../type='ipv6' ";
            type  empty;
            description "Use this attribute to inform that the default icmpv6 rule is disable
                        for the IPv6 ACL.";
        } // END of ipv6-disable-default-icmpv6-rule definition.

    } // END of acl-set-config definition.
    grouping acl-resequence-config {
        description
            "Configuration data for ACL resequencing";
        leaf starting-sequence-number  {
            type  uint32 {
                 range "1..4294967295"  {
                    description "1..4294967295:Feature : HAVE_CUSTOM1_ACL Supported range 1 -
                            268435453Feature : HAVE_CUSTOM2_ACL Supported range 1 - 268435453Not
                            Feature : HAVE_CUSTOM1_ACL,HAVE_CUSTOM2_ACL  Supported range 1 -
                            4294967295";
                 }
            }
            mandatory true;
            description "Use this attribute to set starting sequence number for resequencing";
        } // END of starting-sequence-number definition.

        leaf increment-steps  {
            type  uint32 {
                 range "1..4294967295"  {
                    description "1..4294967295:Feature : HAVE_CUSTOM1_ACL Supported range 1 -
                            268435453Feature : HAVE_CUSTOM2_ACL Supported range 1 - 268435453Not
                            Feature : HAVE_CUSTOM1_ACL,HAVE_CUSTOM2_ACL  Supported range 1 -
                            4294967295";
                 }
            }
            mandatory true;
            description "Use this attribute to set increment steps for resequencing";
        } // END of increment-steps definition.

    } // END of acl-resequence-config definition.
    grouping acl-default-action-config {
        description
            "Configuration data for ACL default actions";
        leaf forwarding-action-default  {
            type  ipi-acl-types:acl_default_forwarding_action_t;
            description "Use this attribute to set default forwarding action";
        } // END of forwarding-action-default definition.

        leaf monitor-action-default  {
            if-feature feature-list:HAVE_SFLOW;
            if-feature feature-list:HAVE_CUSTOM1_ACL;
            type  ipi-acl-types:acl_monitor_action_t;
            description "Use this attribute to set default logging or sampling action";
        } // END of monitor-action-default definition.

    } // END of acl-default-action-config definition.
    grouping acl-default-counters {
        description
            "Default ACL entry counters";
        leaf matched-packets  {
            type  yang:counter64;
            config false;
            description "The number of packets that matched the default rule on the attached
                        interface.";
        } // END of matched-packets definition.

    } // END of acl-default-counters definition.
    grouping acl-sequence-id-config {
        description
            "sequence-id configuration for ACL entry";
        leaf sequence-id  {
            type  uint32 {
                 range "1..4294967295"  {
                    description "1..4294967295:Feature : HAVE_CUSTOM1_ACL Supported range 1 -
                            268435453Feature : HAVE_CUSTOM2_ACL Supported range 1 - 268435453Not
                            Feature : HAVE_CUSTOM1_ACL,HAVE_CUSTOM2_ACL  Supported range 1 -
                            4294967295";
                 }
            }
            description "The sequence id determines the order in which ACL entries are applied.
                        The sequence id must be unique for each entry in an ACL set.";
        } // END of sequence-id definition.

    } // END of acl-sequence-id-config definition.
    grouping acl-ipv4-tcp-config {
        description
            "Configuration data specific for IPV4 TCP ACL entry";
        leaf tcp-flags  {
            type  ipi-acl-types:acl_tcp_flags_t;
            description "List of TCP flags to match";
        } // END of tcp-flags definition.

    } // END of acl-ipv4-tcp-config definition.
    grouping acl-ipv4-icmp-config {
        description
            "Configuration data specific for IPV4 ICMP ACL entry";
        leaf protocol-icmp  {
            type  empty;
            description "Use this attribute to indicates that protocol carried in the IP packet
                        is icmp.";
        } // END of protocol-icmp definition.

        leaf icmp-message  {
            if-feature feature-list:HAVE_CUSTOM1_ACL;
            type  ipi-acl-types:acl_icmp_options_t;
            description "Use this attribute to set ICMP message type";
        } // END of icmp-message definition.

        leaf icmp-type  {
            if-feature feature-list:HAVE_CUSTOM1_ACL;
            type  uint8 {
                 range "0..255"  {
                    description "0..255: Supported range 0 - 255";
                 }
            }
            description "Use this attribute to set ICMP type";
        } // END of icmp-type definition.

        leaf icmp-code  {
            // when " ../icmp-type ";
            if-feature feature-list:HAVE_CUSTOM1_ACL;
            type  uint8 {
                 range "0..255"  {
                    description "0..255: Supported range 0 - 255";
                 }
            }
            description "Use this attribute to set ICMP sub-type";
        } // END of icmp-code definition.

    } // END of acl-ipv4-icmp-config definition.
    grouping acl-ipv4-config {
        description
            "Configuration data for IPV4 ACL entry";
        leaf source-address  {
            type  ipi-acl-types:acl_any_ipv4_src_addr_t;
            description "Source IPv4 address prefix.";
        } // END of source-address definition.

        leaf destination-address  {
            type  ipi-acl-types:acl_any_ipv4_dest_addr_t;
            description "Destination IPv4 address prefix.";
        } // END of destination-address definition.

        leaf dscp  {
            type  ipi-acl-types:acl_dscp_t;
            description "Use this attribute to set the value of Differentiated Services Code
                        Point.";
        } // END of dscp definition.

        leaf precedence  {
            type  ipi-acl-types:acl_precedence_t;
            description "Use this attribute to set the precedence value";
        } // END of precedence definition.

        leaf inner-vlan-id  {
            type  uint16 {
                 range "1..4094"  {
                    description "1..4094: Supported range 1 - 4094";
                 }
            }
            description "Use this attribute to set the inner-vlan-id";
        } // END of inner-vlan-id definition.

        choice protocol {
            description
                "Protocol Types";
            case tcp {

                description
                    "Transmission Control Protocol";

                uses ipi-acl-common:acl-tcp-config;
                uses acl-ipv4-tcp-config;
            }
            case udp {

                description
                    "User Datagram Protocol";

                uses ipi-acl-common:acl-udp-config;
            }
            case icmp {

                description
                    "Internet Control Message Protocol";

                uses acl-ipv4-icmp-config;
            }
            case other-protocols {

                description
                    "Other protocols";

                leaf protocol-name  {
                    type  ipi-acl-types:acl_ip_protocols_t;
                    description "Use this attribute to set the protocol carried in the IP packet,
                                expressed by its name.";
                } // END of protocol-name definition.

            }
        } // END of protocol-choice definition.
    } // END of acl-ipv4-config definition.
    grouping acl-standard-config {
        description
            "Configuration data for Standard ACL set";
        leaf name  {
            type  string {
                length "1..64";
                pattern "[a-zA-Z0-9][^?' =,>|]*";
            }
            description "The name of the access-list set";
        } // END of name definition.

        leaf type  {
            type  ipi-acl-types:acl_standard_types_t;
            description "Type indicates the fields allowed in the ACL entries belonging to the
                        ACL set (ip, ipv6)";
        } // END of type definition.

    } // END of acl-standard-config definition.
    grouping acl-standard-ipv4-config {
        description
            "Configuration data for Standard IPV4 ACL set";
        leaf source-address  {
            type  ipi-acl-types:acl_any_ipv4_src_addr_t;
            description "Source IPv4 address prefix.";
        } // END of source-address definition.

        leaf forwarding-action  {
            type  ipi-acl-types:acl_forwarding_action_t;
            mandatory true;
            description "Specifies the forwarding action. One forwarding action must be
                        specified for each ACL entry.";
        } // END of forwarding-action definition.

    } // END of acl-standard-ipv4-config definition.
    grouping acl-entries-top {
        description
            "Top level grouping for ACL entries";
        container acl-entries {
            description
                "Container for ACL entries";

            list acl-entry {
                key "sequence-id";
                description
                    "List of ACL entries comprising an ACL set";
                leaf sequence-id  {
                    type  leafref {
                        path  "../config/sequence-id";
                    }
                    description "The sequence id determines the order in which ACL entries are applied.
                                The sequence id must be unique for each entry in an ACL set.";
                } // END of sequence-id definition.

                container config {
                    description
                        "ACL sequence-id configuration";
                    uses acl-sequence-id-config;
                } // END of config-container definition.
                container state {
                    config false;
                    description
                        "ACL sequence-id configuration";
                    uses acl-sequence-id-config;
                } // END of state-container definition.
                container ipv4 {
                    description
                        "IPV4 ACL set configuration attributes";
                    container config {
                        description
                            "ACL global configuration attributes";
                        uses ipi-acl-common:acl-common-config;
                        uses acl-ipv4-config;
                        uses ipi-acl-common:acl-ip-config;
                    } // END of config-container definition.
                    container state {
                        config false;
                        description
                            "Global Operational data for ACL";
                        container counters {
                            config false;
                            description
                                "Counter data for ACL entries";
                            uses ipi-acl-common:acl-counters;
                        } // END of counters-container definition.
                        uses ipi-acl-common:acl-common-config;
                        uses acl-ipv4-config;
                        uses ipi-acl-common:acl-ip-config;
                    } // END of state-container definition.
                } // END of ipv4-container definition.
                uses ipv6-grouping;
                uses arp-grouping;
                uses mac-grouping;
                uses copp-grouping;
            } // End of acl-entry-list
        } // END of acl-entries-container definition.
    } // END of acl-entries-top definition.
    grouping acl-sets-top {
        description
            "Access list entries variables top level container";
        container acl-sets {
            description
                "Access list entries variables enclosing container";

            list acl-set {
                key "name type";
                description
                    "List of ACL sets, each comprising of a list of ACL entries";
                leaf name  {
                    type  leafref {
                        path  "../config/name";
                    }
                    description "The name of the access-list set";
                } // END of name definition.

                leaf type  {
                    type  leafref {
                        path  "../config/type";
                    }
                    description "Type indicates the fields allowed in the ACL entries belonging to the
                                ACL set (e.g., ip, ipv6, etc.)";
                } // END of type definition.

                container config {
                    description
                        "ACL set configuration attributes";
                    uses acl-set-config;
                } // END of config-container definition.
                container state {
                    config false;
                    description
                        "ACL set state information";
                    uses acl-set-config;
                } // END of state-container definition.
                container default-actions {
                    description
                        "Container for ACL default action related attributes";
                    container config {
                        description
                            "ACL default action related configuration attributes";
                        uses acl-default-action-config;
                    } // END of config-container definition.
                    container state {
                        config false;
                        description
                            "ACL default action related state information";
                        container counters {
                            config false;
                            description
                                "Counter data for Default ACL entry";
                            uses acl-default-counters;
                        } // END of counters-container definition.
                        uses acl-default-action-config;
                    } // END of state-container definition.
                } // END of default-actions-container definition.
                uses acl-entries-top;
                uses summary-info-grouping;
            } // End of acl-set-list
        } // END of acl-sets-container definition.
    } // END of acl-sets-top definition.
    grouping standard-acl-sets-top {
        description
            "Standard Access list entries variables top level container";
        container standard-acl-sets {
            description
                "Standard Access list entries variables enclosing container";

            list standard-acl-set {
                key "name type";
                description
                    "List of ACL sets, each comprising of a list of ACL entries";
                leaf name  {
                    type  leafref {
                        path  "../config/name";
                    }
                    description "The name of the access-list set";
                } // END of name definition.

                leaf type  {
                    type  leafref {
                        path  "../config/type";
                    }
                    description "Type indicates the fields allowed in the ACL entries belonging to the
                                standard ACL set (ip, ipv6)";
                } // END of type definition.

                container config {
                    description
                        "Standard ACL set configuration attributes";
                    uses acl-standard-config;
                } // END of config-container definition.
                container state {
                    config false;
                    description
                        "Standard ACL set state information";
                    uses acl-standard-config;
                } // END of state-container definition.
                container ipv4-acl-entries {
                    description
                        "Container for IPV4 Standard ACL entries";

                    list ipv4-acl-entry {
                        key "source-address";
                        description
                            "List of IPV4 ACL entries comprising an ACL set";
                        leaf source-address  {
                            type  leafref {
                                path  "../config/source-address";
                            }
                            description "Source IPv4 address prefix.";
                        } // END of source-address definition.

                        container config {
                            description
                                "Standard ACL set configuration attributes";
                            uses acl-standard-ipv4-config;
                        } // END of config-container definition.
                        container state {
                            config false;
                            description
                                "Standard ACL set state information";
                            uses acl-standard-ipv4-config;
                        } // END of state-container definition.
                    } // End of ipv4-acl-entry-list
                } // END of ipv4-acl-entries-container definition.
                uses ipv6-acl-entries-grouping;
            } // End of standard-acl-set-list
        } // END of standard-acl-sets-container definition.
    } // END of standard-acl-sets-top definition.

    grouping  acl-grouping {
    description
        "Top level container for ACL config and operational state data";
    container acl {
        if-feature feature-list:HAVE_ACL;
        description
            "Top level container for ACL config and operational state data";
        uses acl-sets-top;
        uses standard-acl-sets-top;
        uses interfaces-grouping;
        uses vty-line-grouping;
        uses global-grouping;
    } // END of acl-container definition.
    } // END of acl-grouping definition.

    uses acl-grouping;

    rpc clear-access-list-counters-all {
        if-feature feature-list:HAVE_ACL;
        description "Use this RPC to clear all access-list counters";
    }

    rpc clear-access-list-counters {
        if-feature feature-list:HAVE_ACL;
        description "Use this RPC to clear any specific ip access-list counter";
        input  {
            leaf name  {
                type string;
                mandatory true;
                description "The name of the access-list set";
            }
        }
    }

    rpc clear-ip-access-list-counters-all {
        if-feature feature-list:HAVE_ACL;
        description "Use this RPC to clear all ip access-list counters";
    }

    rpc clear-ip-access-list-counters {
        if-feature feature-list:HAVE_ACL;
        description "Use this RPC to clear any specific ip access-list counter";
        input  {
            leaf name  {
                type string;
                mandatory true;
                description "The name of the access-list set";
            }
        }
    }

    rpc clear-ipv6-access-list-counters-all {
        if-feature feature-list:HAVE_IPV6;
        if-feature feature-list:HAVE_ACL;
        description "Use this RPC to clear all ipv6 access-list counters";
    }

    rpc clear-ipv6-access-list-counters {
        if-feature feature-list:HAVE_IPV6;
        if-feature feature-list:HAVE_ACL;
        description "Use this RPC to clear any specific ipv6 access-list counter";
        input  {
            leaf name  {
                type string;
                mandatory true;
                description "The name of the access-list set";
            }
        }
    }

    rpc clear-mac-access-list-counters-all {
        if-feature feature-list:HAVE_ACL;
        description "Use this RPC to clear all mac access-list counters";
    }

    rpc clear-mac-access-list-counters {
        if-feature feature-list:HAVE_ACL;
        description "Use this RPC to clear any specific mac access-list counter";
        input  {
            leaf name  {
                type string;
                mandatory true;
                description "The name of the access-list set";
            }
        }
    }

    rpc clear-arp-access-list-counters-all {
        if-feature feature-list:HAVE_ACL;
        description "Use this RPC to clear all arp access-list counters";
    }

    rpc clear-arp-access-list-counters {
        if-feature feature-list:HAVE_ACL;
        description "Use this RPC to clear any specific arp access-list counter";
        input  {
            leaf name  {
                type string;
                mandatory true;
                description "The name of the access-list set";
            }
        }
    }

    notification acl-copp-ipv4-prefix-install-failure {
        if-feature feature-list:HAVE_ACL;
        if-feature feature-list:HAVE_COPP_FILTER;

        description "Indicates that an IPv4 prefix added to the prefix group was not installed successfully into the copp ACL.";

        leaf severity {
            type cml-data-types:cml_notif_severity_t;
            description "Notification severity level (value: CRITICAL)";
        }

        leaf eventClass {
            type cml-data-types:cml_notif_class_t;
            description "Notification event class (value: STATE)";
        }

        leaf name {
            type  string;
        description
            "The name of the access-list set";
        }

        leaf type {
            type ipi-acl-types:acl_types_t;
        description
            "Type indicates the fields allowed in the ACL entries belonging to the
                    ACL set (e.g., ip, ipv6, etc.)";
        }

        leaf sequence-id {
            type  uint32;
        description
            "The sequence id determines the order in which ACL entries are applied.
                    The sequence id must be unique for each entry in an ACL set.";
        }

        leaf source-address {
            type ipi-acl-types:acl_any_ipv4_src_addr_t;
        description
            "Source IPv4 address prefix.";
        }

        leaf destination-address {
            type ipi-acl-types:acl_any_ipv4_dest_addr_t;
        description
            "Destination IPv4 address prefix.";
        }
    }

    notification acl-copp-ipv6-prefix-install-failure {
        if-feature feature-list:HAVE_ACL;
        if-feature feature-list:HAVE_COPP_FILTER;

        description "Indicates that an IPv6 prefix added to the prefix group was not installed successfully into the copp ACL.";

        leaf severity {
            type cml-data-types:cml_notif_severity_t;
            description "Notification severity level (value: CRITICAL)";
        }

        leaf eventClass {
            type cml-data-types:cml_notif_class_t;
            description "Notification event class (value: STATE)";
        }

        leaf name {
            type  string;
        description
            "The name of the access-list set";
        }

        leaf type {
            type ipi-acl-types:acl_types_t;
        description
            "Type indicates the fields allowed in the ACL entries belonging to the
                    ACL set (e.g., ip, ipv6, etc.)";
        }

        leaf sequence-id {
            type  uint32;
        description
            "The sequence id determines the order in which ACL entries are applied.
                    The sequence id must be unique for each entry in an ACL set.";
        }

        leaf source-address {
            type ipi-acl-types:acl_copp_any_ipv6_src_addr_t;
        description
            "Source IPv6 address prefix.";
        }

        leaf destination-address {
            type ipi-acl-types:acl_copp_any_ipv6_dest_addr_t;
        description
            "Destination IPv6 address prefix.";
        }
    }

}
