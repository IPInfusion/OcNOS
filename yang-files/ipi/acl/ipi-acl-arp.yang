/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-acl-arp.yang
*
*/

submodule ipi-acl-arp {

    yang-version 1.1;

    belongs-to  ipi-acl { prefix ipi-acl; }

    import feature-list {
        prefix feature-list;
        revision-date 2026-09-15;
    }

    import ipi-acl-types {
        prefix ipi-acl-types;
        revision-date 2025-04-10;
    }

    import ipi-acl-common {
        prefix ipi-acl-common;
        revision-date 2025-07-18;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for ACL ARP object";


    revision "2025-08-18" {
        description "Inclusion of streaming telemetry yaml file";
        reference " 0.7.2.";
    }

    revision "2024-12-10" {
        description "Hitless merge is now skipped on all attributes";
        reference " 0.7.1.";
    }

    revision "2024-05-02" {
        description "Add flag to support replace operation on acl match attributes";
        reference " 0.7.0.";
    }

    revision "2023-07-07" {
        description "Removing the misplaced initialized from acl-arp-config";
        reference " 0.6.0.";
    }

    revision "2022-11-24" {
        description "Removed empty container related table entries from trigger acl_arp_resequencing.";
        reference " 0.5.5.";
    }

    revision "2022-09-29" {
        description "Updated the name of mrib module in smi-server-modules tag";
        reference " 0.5.4.";
    }

    revision "2022-08-10" {
        description "Updated smi-server-modules tag paramters";
        reference " 0.5.3.";
    }

    revision "2022-07-30" {
        description "Updated when expressions in yang";
        reference " 0.5.2.";
    }

    revision "2022-07-28" {
        description "Updated smi-server-modules with restructured RIPng module name";
        reference " 0.5.1.";
    }

    revision "2022-07-26" {
        description "Corrected RIP datamodel as per Open Config style";
        reference " 0.5.0.";
    }

    revision "2022-06-01" {
        description "Updated the yang file with feature";
        reference " 0.4.0.";
    }

    revision "2021-09-17" {
        description "Moved 'destination-mac-options' from ipi-acl-common module to ipi-acl-mac and ipi-acl-arp modules";
        reference " 0.3.0.";
    }

    revision "2021-09-03" {
        description "Update descriptions of attribute";
        reference " 0.2.0.";
    }

    revision "2021-07-14" {
        description "Restructured module as per OpenConfig style";
        reference " 0.1.0.";
    }

    grouping acl-arp-config {
        description
            "Configuration data for ARP ACL entry";
        leaf arp-packet-type  {
            type  ipi-acl-types:acl_arp_type_t;
            description "Use this attribute to set the arp packet type to match in packets";
        } // END of arp-packet-type definition.

        leaf source-ip-address  {
            type  ipi-acl-types:acl_any_ipv4_src_addr_t;
            description "Source IPv4 address prefix.";
        } // END of source-ip-address definition.

        leaf destination-ip-address  {
            // when " ipi-acl-arp:arp/config/arp-packet-type == '2' ";
            type  ipi-acl-types:acl_any_ipv4_dest_addr_t;
            description "Destination IPv4 address prefix.";
        } // END of destination-ip-address definition.

        choice destination-mac-options {
            description
                "Destination mac options";
            case any-mac {

                description
                    "Any destination mac address";

                leaf destination-mac-any  {
                    // when " ipi-acl-arp:arp/config/arp-packet-type == '2' ";
                    type  empty;
                    description "Use this attribute to indicate any destination address.";
                } // END of destination-mac-any definition.

            }
            case host-mac {

                description
                    "Host Mac Address";

                leaf destination-mac-host  {
                    // when " ipi-acl-arp:arp/config/arp-packet-type == '2' ";
                    type  ipi-acl-types:acl_mac_addr_t {
                        length "1..1965";
                    }
                    description "Use this attribute to set host destination address.";
                } // END of destination-mac-host definition.

            }
            case mac-with-mask {

                description
                    "Mac address with mask";

                leaf destination-mac-address  {
                    // when " ipi-acl-arp:arp/config/arp-packet-type == '2' ";
                    type  ipi-acl-types:acl_mac_addr_t {
                        length "1..1965";
                    }
                    description "Use this attribute to set destination mac address.";
                } // END of destination-mac-address definition.

                leaf destination-mac-mask  {
                    // when " ipi-acl-arp:arp/config/arp-packet-type == '2' ";
                    type  ipi-acl-types:acl_mac_addr_t {
                        length "1..1965";
                    }
                    description "Use this attribute to set destination wildcard mask.";
                } // END of destination-mac-mask definition.

            }
        } // END of destination-mac-options-choice definition.
    } // END of acl-arp-config definition.

    grouping  arp-grouping {
    description
        "ARP ACL set configuration attributes";
    container arp {
        if-feature feature-list:HAVE_ACL;
        description
            "ARP ACL set configuration attributes";
        container config {
            description
                "ACL global configuration attributes";
            uses ipi-acl-common:acl-common-config;
            uses ipi-acl-common:acl-mac-arp-config;
            uses acl-arp-config;
        } // END of config-container definition.
        container state {
            config false;
            description
                "Global Operational data for ACL";
            container counters {
                config false;
                description
                    "Counter data for ACL entries";
                uses ipi-acl-common:acl-counters;
            } // END of counters-container definition.
            uses ipi-acl-common:acl-common-config;
            uses ipi-acl-common:acl-mac-arp-config;
            uses acl-arp-config;
        } // END of state-container definition.
    } // END of arp-container definition.
    } // END of arp-grouping definition.


}
