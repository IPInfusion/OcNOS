/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-if-flowspec.yang
*
*/

module ipi-if-flowspec {

    yang-version 1.1;

    namespace   "http://www.ipinfusion.com/yang/ocnos/ipi-if-flowspec";

    prefix "ipi-if-flowspec";

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Interface level configurations for flowspec";


    revision "2024-09-30" {
        description "Support port-basis flowspec disable officially";
        reference " 0.2.0.";
    }

    revision "2021-03-08" {
        description "Initial Version";
        reference " 0.1.0.";
    }

    grouping ipv4-flowspec-if-config {
        description
            "IPv4 FLOWSPEC configuration data for the interface";
        leaf flowspec-disable  {
            type  empty;
            description "disable FLOWSPEC for an interface";
        } // END of flowspec-disable definition.

    } // END of ipv4-flowspec-if-config definition.

    grouping  interface-flowspec-grouping {
    description
        "NSM FLOWSPEC interface related operations";
    container interface-flowspec {
        if-feature feature-list:HAVE_BGP_FLOWSPEC;
        description
            "NSM FLOWSPEC interface related operations";
        container ipv4 {
            description
                "Configurable ipv4 items at the global, physical interface level";
            container config {
                description
                    "FLOWSPEC ipv4 interface confifiguration";
                uses ipv4-flowspec-if-config;
            } // END of config-container definition.
            container state {
                config false;
                description
                    "IPv4 FLOWSPEC interface operational information";
                uses ipv4-flowspec-if-config;
            } // END of state-container definition.
        } // END of ipv4-container definition.
    } // END of interface-flowspec-container definition.
    } // END of interface-flowspec-grouping definition.

    augment /ipi-interface:interfaces/ipi-interface:interface {
        description
            "NSM FLOWSPEC interface related operations";
        uses interface-flowspec-grouping;
    }


}
