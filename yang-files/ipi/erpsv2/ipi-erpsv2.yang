/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-erpsv2.yang
*
*/

module ipi-erpsv2 {

    yang-version 1.1;

    namespace   "http://www.ipinfusion.com/yang/ocnos/ipi-erpsv2";

    prefix "ipi-erpsv2";

    import ietf-yang-types {
        prefix yang;
        revision-date 2013-07-15;
    }

    import cml-data-types {
        prefix cml-data-types;
        revision-date 2026-05-15;
    }

    import ipi-erpsv2-types {
        prefix ipi-erpsv2-types;
        revision-date 2025-02-18;
    }

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module describes configuration and operational data model for
                ITU.T G.8032 Ethernet Ring Protection Switching (ERPS)";

    reference "Rec. ITU-T G.8032/Y.1344 (08/2015)";

    revision "2025-09-17" {
        description "Blocking Bridge-domain and cross-connect for all XGS (DC) platforms";
        reference " 0.14.1.";
    }

    revision "2025-02-18" {
        description "Getapi implementation for ERPS";
        reference " 0.14.0.";
    }

    revision "2025-02-10" {
        description "Removed 'CML_UNIQUE' support for aps-channel vlan-id and data-vlan";
        reference " 0.13.2.";
    }

    revision "2025-02-09" {
        description "Added CML_UNIQUE for assosicate ring";
        reference " 0.13.3.";
    }

    revision "2025-02-06" {
        description "Added 'CML_UNIQUE' support for aps-channel vlan-id";
        reference " 0.13.1.";
    }

    revision "2025-02-03" {
        description "Added 'CML_UNIQUE' support for data-vlan";
        reference " 0.13.0.";
    }

    revision "2023-12-12" {
        description "Added dependentObject tag under associate-ring";
        reference " 0.11.8.";
    }

    revision "2023-12-05" {
        description "Added interface state change notification";
        reference " 0.12.0.";
    }

    revision "2023-10-12" {
        description "Added dependentObject tag under associate-ring";
        reference " 0.11.7.";
    }

    revision "2023-08-16" {
        description "Updated subifp erp-instance options";
        reference " 0.11.6.";
    }

    revision "2023-08-11" {
        description "erps instance dependency for add vlan to port";
        reference " 0.11.5.";
    }

    revision "2023-07-28" {
        description "Added displayString with option all for clear g8032 erp-instance and g8032 erp-instance commands";
        reference " 0.11.4.";
    }

    revision "2023-07-27" {
        description "Added if-not-feature directive for bridge-domain when clause";
        reference " 0.11.3.";
    }

    revision "2023-07-24" {
        description "Remove implicit delete directives to erp-instance and erpsv2";
        reference " 0.11.2.";
    }

    revision "2023-07-17" {
        description "Added implicit_delete tag for objectlist subinterface and container config";
        reference " 0.11.1.";
    }

    revision "2023-06-13" {
        description "Added leafref for erpsv2-subinterface-config name attribute";
        reference " 0.11.0.";
    }

    revision "2023-06-01" {
        description "Add bridge and bridge-domain dependencies to the ring object";
        reference " 0.10.11.";
    }

    revision "2023-04-26" {
        description "Removed implicit delete tag for the objectlist profile";
        reference " 0.10.10.";
    }

    revision "2023-04-25" {
        description "Removed implicit delete tag for the objectlist ERPSv2 ring";
        reference " 0.10.9.";
    }

    revision "2023-04-18" {
        description "Added implicit delete tag on data config container";
        reference " 0.10.7.";
    }

    revision "2023-04-11" {
        description "Removed when tag for ring-type attribute";
        reference " 0.10.6.";
    }

    revision "2023-04-10" {
        description "ERPS over bridge-domain";
        reference " 0.10.6.";
    }

    revision "2023-04-04" {
        description "Added when tag for tcn-to-instances attribute";
        reference " 0.10.5.";
    }

    revision "2023-03-23" {
        description "Added implicit delete tag on debug config container";
        reference " 0.10.4.";
    }

    revision "2023-03-21" {
        description "Modified when tag for enable-tcn-propagation";
        reference " 0.10.3.";
    }

    revision "2023-03-13" {
        description "Added new sub-ring-vc for Ring types";
        reference " 0.10.2.";
    }

    revision "2023-03-06" {
        description "Added When tag for no-debug-all command";
        reference " 0.10.1.";
    }

    revision "2023-02-28" {
        description "Removing Bridge id dependency";
        reference " 0.10.0.";
    }

    revision "2023-01-24" {
        description "Change of hierarchy to add local interface list for erps instance";
        reference " 0.9.4.";
    }

    revision "2023-01-20" {
        description "Added enclosing container for port vlan object list";
        reference " 0.9.4.";
    }

    revision "2023-01-10" {
        description "Fix DB sync for erps instance";
        reference " 0.9.3.";
    }

    revision "2023-01-06" {
        description "Added new attribute for erps in the subinterface";
        reference " 0.9.2.";
    }

    revision "2022-12-12" {
        description "Reverting port-vlan enclosing container changes";
        reference " 0.9.1.";
    }

    revision "2022-12-09" {
        description "Added enclosing container for port vlan object list";
        reference " 0.9.0.";
    }

    revision "2022-10-18" {
        description "Added when tag to profile on profile-name and erp-instance on name to clean the DB from attributes";
        reference " 0.8.1.";
    }

    revision "2022-08-10" {
        description "Debug hierarchy change";
        reference " 0.8.0.";
    }

    revision "2022-06-28" {
        description "Changed validation of when tag on virtual-channel";
        reference " 0.7.0.";
    }

    revision "2022-06-06" {
        description "Added when tag to erp-instance on tcn-propagation, non-virtual-channel, virtual-channel and rpl";
        reference " 0.6.0.";
    }

    revision "2022-06-01" {
        description "Updated the yang file with feature";
        reference " 0.5.0.";
    }

    revision "2022-04-19" {
        description "Added debug support for g8032";
        reference " 0.4.0.";
    }

    revision "2022-03-09" {
        description "Range replaced by length in RPCs";
        reference " 0.3.0.";
    }

    revision "2022-02-09" {
        description "Restructured module in accordance with OpenConfig style";
        reference " 0.2.0.";
    }

    revision "2022-02-08" {
        description "Initial Version";
        reference " 0.1.0.";
    }

    grouping erpsv2-associate-ring-config {
        description
            "Grouping for ERPS Associate Ring configuration data";
        leaf associate-ring-name  {
            type  string {
                length "1..255";
                pattern "[^?' =,>|]+";
            }
            description "G.8032 ring name to be associate with.";
        } // END of associate-ring-name definition.

    } // END of erpsv2-associate-ring-config definition.
    grouping erpsv2-associate-ring-state {
        description
            "Grouping for ERPS Associate Ring state data";
        leaf data-vlan  {
            type  string {
                length "1..1965";
            }
            description "This attribute specifies the data VLAN for associate ring";
        } // END of data-vlan definition.

    } // END of erpsv2-associate-ring-state definition.
    grouping erpsv2-associate-ring-top {
        description
            "Grouping for ERPS Associate Rings";
        container associate-rings {
            description
                "Container for ERPS Associate Rings";

            list associate-ring {
            when " /ipi-erpsv2:erpsv2/ipi-erpsv2:erp-instances/ipi-erpsv2:erp-instance/ipi-erpsv2:config/ipi-erpsv2:ring-name ";
                key "associate-ring-name";
                description
                    "ERPS Associate Ring";
                leaf associate-ring-name  {
                    type  leafref {
                        path  "../config/associate-ring-name";
                    }
                    description "G.8032 ring name to be associate with.";
                } // END of associate-ring-name definition.

                container config {
                    description
                        "Configuration data for ERPS Associate Ring";
                    uses erpsv2-associate-ring-config;
                } // END of config-container definition.
                container state {
                    config false;
                    description
                        "Operational state data for ERPS Associate Ring";
                    uses erpsv2-associate-ring-config;
                    uses erpsv2-associate-ring-state;
                } // END of state-container definition.
            } // End of associate-ring-list
        } // END of associate-rings-container definition.
    } // END of erpsv2-associate-ring-top definition.
    grouping erpsv2-data-vlan-config {
        description
            "Grouping for ERPS data VLAN configuration data grouping";
        leaf data-vlan  {
            type  cml-data-types:cml_range_t;
            description "List of VLAN-IDs, protected by ring instance. For
                        example '2, 3-7, 9, 10-100'
                        VLAN-IDs MUST not overlap with VLAN-IDs of any other
                        instance of the same ring.";
        } // END of data-vlan definition.

    } // END of erpsv2-data-vlan-config definition.
    grouping erpsv2-data-vlan-top {
        description
            "Grouping for ERPS data VLAN";
        container data {
            when " /ipi-erpsv2:erpsv2/ipi-erpsv2:erp-instances/ipi-erpsv2:erp-instance/ipi-erpsv2:config/ipi-erpsv2:ring-name ";
            description
                "Container for ERPS data VLAN";
            container config {
                description
                    "Configuration data for ERPS data VLAN";
                uses erpsv2-data-vlan-config;
            } // END of config-container definition.
            container state {
                config false;
                description
                    "Operational state data for ERPS data VLAN";
                uses erpsv2-data-vlan-config;
            } // END of state-container definition.
        } // END of data-container definition.
    } // END of erpsv2-data-vlan-top definition.
    grouping erpsv2-aps-channel-vlan-config {
        description
            "Grouping for ERPS APS channel VLAN configuration data";
        leaf vlan-id  {
            when " /ipi-erpsv2:erpsv2/ipi-erpsv2:erp-instances/ipi-erpsv2:erp-instance/ipi-erpsv2:config/ipi-erpsv2:ring-name ";
            type  uint16 {
                 range "2..4094"  {
                    description "2..4094: Supported range 2 - 4094";
                 }
            }
            description "Ring wide control VLAN-ID used by ERPS instance to send and receive
                        the RAPS messages in the ring";
        } // END of vlan-id definition.

        leaf inner-vlan-id  {
            when " /ipi-erpsv2:erpsv2/ipi-erpsv2:erp-instances/ipi-erpsv2:erp-instance/ipi-erpsv2:config/ipi-erpsv2:ring-name ";
            type  uint16 {
                 range "2..4094"  {
                    description "2..4094: Supported range 2 - 4094";
                 }
            }
            description "Ring wide control inner VLAN-ID used by ERPS instance to send and
                        receive the RAPS messages in the ring";
        } // END of inner-vlan-id definition.

    } // END of erpsv2-aps-channel-vlan-config definition.
    grouping erpsv2-aps-channel-vlan-top {
        description
            "Grouping for ERPS APS channel VLAN";
        container aps-channel-vlans {
            description
                "Container for ERPS APS channel VLAN";

            list aps-channel-vlan {
            when " /ipi-erpsv2:erpsv2/ipi-erpsv2:erp-instances/ipi-erpsv2:erp-instance/ipi-erpsv2:config/ipi-erpsv2:ring-name ";
                key "vlan-id";
                max-elements 1;
                description
                    "List of ERPS APS channel VLANs";
                leaf vlan-id  {
                    type  leafref {
                        path  "../config/vlan-id";
                    }
                    description "Ring wide control vlan-id used by ERPS instance to send and receive
                                the RAPS messages in the ring";
                } // END of vlan-id definition.

                container config {
                    description
                        "Configuration data for ERPS APS channel VLAN";
                    uses erpsv2-aps-channel-vlan-config;
                } // END of config-container definition.
                container state {
                    config false;
                    description
                        "Operational state data for ERPS APS channel VLAN";
                    uses erpsv2-aps-channel-vlan-config;
                } // END of state-container definition.
            } // End of aps-channel-vlan-list
        } // END of aps-channel-vlans-container definition.
    } // END of erpsv2-aps-channel-vlan-top definition.
    grouping erpsv2-aps-channel-config {
        description
            "Grouping for ERPS APS channel configuration data";
        leaf level  {
            type  uint8 {
                 range "0..7"  {
                    description "0..7: Supported range 0 - 7";
                 }
            }
            description "Maintainance Endpoint Level (MEL) at which R-APS
                        PDU is transmitted. All nodes in the ring must be
                        configured with same APS level value.";
        } // END of level definition.

    } // END of erpsv2-aps-channel-config definition.
    grouping erpsv2-aps-channel-top {
        description
            "Grouping for ERPS APS channel";
        container aps-channel {
            description
                "Container for ERPS APS channel";
            container config {
                description
                    "Configuration data for ERPS APS channel";
                uses erpsv2-aps-channel-config;
            } // END of config-container definition.
            container state {
                config false;
                description
                    "Operational state data for ERPS APS channel";
                uses erpsv2-aps-channel-config;
            } // END of state-container definition.
        } // END of aps-channel-container definition.
    } // END of erpsv2-aps-channel-top definition.
    grouping erpsv2-ring-config {
        description
            "Grouping for ERPS ring configuration data";
        leaf ring-name  {
            type  string {
                length "1..255";
                pattern "[^?' =,>|]+";
            }
            description "G.8032 ring name. This attribute uniquely identifies a ring on the
                        network device.";
        } // END of ring-name definition.

        leaf east-interface  {
            type  leafref {
                path  "/ipi-interface:interfaces/ipi-interface:interface/ipi-interface:name";
            }
            description "East port associated to the protection ring";
        } // END of east-interface definition.

        leaf west-interface  {
            // when " ../east-interface ";
            type  leafref {
                path  "/ipi-interface:interfaces/ipi-interface:interface/ipi-interface:name";
            }
            description "West port associated to the protection ring";
        } // END of west-interface definition.

        leaf description  {
            type  cml-data-types:cml_line_t {
                length "1..255";
            }
            description "Textual description of the ring.";
        } // END of description definition.

    } // END of erpsv2-ring-config definition.
    grouping erpsv2-ring-top {
        description
            "Grouping for ERPS Ring";
        container rings {
            description
                "Container for ERPS rings";

            list ring {
                key "ring-name";
                description
                    "List of ERPS ring";
                leaf ring-name  {
                    type  leafref {
                        path  "../config/ring-name";
                    }
                    description "G.8032 ring name. This attribute uniquely identifies a ring on the
                                network device.";
                } // END of ring-name definition.

                container config {
                    description
                        "Configuration data for ERPS ring";
                    uses erpsv2-ring-config;
                } // END of config-container definition.
                container state {
                    config false;
                    description
                        "Operational state data for erpsv2 ring";
                    uses erpsv2-ring-config;
                } // END of state-container definition.
            } // End of ring-list
        } // END of rings-container definition.
    } // END of erpsv2-ring-top definition.
    grouping erpsv2-profile-config {
        description
            "Grouping for ERPS profile configuration data";
        leaf profile-name  {
            type  string {
                length "1..32";
                pattern "[^?' =,>|]+";
            }
            description "G.8032 ring profile name";
        } // END of profile-name definition.

        leaf wait-to-restore-timer  {
            type  uint8 {
                 range "1..12"  {
                    description "1..12: Supported range 1 - 12";
                 }
            }
            units "minutes";
            default "5";
            description "In revertive mode the 'wait to restore' (WTR) timer
                        is used to prevent frequent operation of the
                        protection switching due to intermittent signal
                        failure defects.
                        When recovering from a Signal fail, the delay timer
                        must be long enough to allow the recovering network to
                        become stable.
                        WTR timer is activated on RPL owner node. When WTR
                        timer is expired RPL owner node initiates the
                        reversion process by transmitting an R-APS (NR, RB)
                        message.";
        } // END of wait-to-restore-timer definition.

        leaf hold-off-timer  {
            type  uint16 {
                 range "0..10000"  {
                    description "0..10000: Supported range 0 - 10000";
                 }
            }
            units "milliseconds";
            default "0";
            description "The hold-off timer is used to coordinate the timing of
                        protection switches.
                        When a new defect or more severe defect occurs
                        (new SF), this event is not to be reported immediately
                        to protection switching if the provisioned hold-off
                        timer value is non-zero. Instead, the hold-off timer
                        is started. When the hold-off timer expires, the trail
                        that started the timer is checked as to whether a
                        defect still exists. If one does exist, that defect is
                        reported to protection switching.
                        Hold off timer values SHOULD be specified in multiple of
                        100.";
        } // END of hold-off-timer definition.

        leaf guard-time  {
            type  uint16 {
                 range "10..2000"  {
                    description "10..2000: Supported range 10 - 2000";
                 }
            }
            units "milliseconds";
            default "500";
            description "The guard time is used to prevent Ethernet ring nodes
                        from acting upon outdated R-APS messages and prevents
                        the possibility of forming a closed loop.
                        This timer period SHOULD be greater than the maximum
                        expected forwarding delay in which an R-APS message
                        traverses the entire ring.
                        The period of the guard timer MAY be configured by the
                        operator in 10 ms steps between 10 ms and 2 seconds.";
        } // END of guard-time definition.

        leaf protection-mode  {
            type  ipi-erpsv2-types:erpsv2_protection_mode_t;
            default "revertive";
            description "This leaf defines G.8032 ring protection mode. A ring
                        may operate in revertive or non-revertive mode.
                        In revertive operation, after the condition(s) causing a
                        switch has cleared, the traffic channel is restored to
                        the working transport entity, i.e., blocked on the RPL.
                        In non-revertive operation, the traffic channel
                        continues to use the RPL, if it has not failed, after a
                        switch condition has cleared.";
        } // END of protection-mode definition.

    } // END of erpsv2-profile-config definition.
    grouping erpsv2-profile-state {
        description
            "Grouping for ERPS profile operational state data";
        leaf wait-to-block-time  {
            type  uint32;
            units "milliseconds";
            description "The time period the RPL owner node waits efore reverting the
                        protection state to idle state when fault is recovered in the ring";
        } // END of wait-to-block-time definition.

    } // END of erpsv2-profile-state definition.
    grouping erpsv2-profiles-top {
        description
            "Grouping for ERPS profile";
        container profiles {
            description
                "Container for erpsv2 profiles";

            list profile {
                key "profile-name";
                description
                    "List of ERPS profile";
                leaf profile-name  {
                    type  leafref {
                        path  "../config/profile-name";
                    }
                    description "G.8032 ring profile name";
                } // END of profile-name definition.

                container config {
                    description
                        "Configuration data for ERPS profile";
                    uses erpsv2-profile-config;
                } // END of config-container definition.
                container state {
                    config false;
                    description
                        "Operational state data for ERPS profile";
                    uses erpsv2-profile-config;
                    uses erpsv2-profile-state;
                } // END of state-container definition.
            } // End of profile-list
        } // END of profiles-container definition.
    } // END of erpsv2-profiles-top definition.
    grouping erpsv2-instance-config {
        description
            "Grouping for ERPS instance configuration data";
        leaf name  {
            type  string {
                length "1..255";
                pattern "[^?' =,>|]+";
            }
            description "ERPS instance identifier";
        } // END of name definition.

        leaf ring-name  {
            type  leafref {
                path  "/erpsv2/rings/ring/ring-name";
            }
            description "This parameter specifies the ring instance to associated with the ERPS
                        instance";
        } // END of ring-name definition.

        leaf mapped-profile-name  {
            type  leafref {
                path  "/erpsv2/profiles/profile/profile-name";
            }
            description "G.8032 ring profile name. If this profile exists
                        in the profile configuration list, profile
                        parameters will be imported from it, default
                        values will be used otherwise.";
        } // END of mapped-profile-name definition.

        leaf ring-type  {
            type  ipi-erpsv2-types:erpsv2_ring_type_t;
            default "major-ring";
            description "Defines type of a ethernet ring. A ring can be configured as major
                        ring where ring nodes are connected in closed loop or as a sub-ring
                        when a ring may not have a complete closed loop";
        } // END of ring-type definition.

        leaf enable-tcn-propagation  {
            // when " ../ring-type='sub-ring' or ../ring-type='sub-ring-vc' + ../ring-name ";
            type  empty;
            description "Allows topology change notification (TCN) propagation to the ERPS ring
                        if it is enabled";
        } // END of enable-tcn-propagation definition.

        leaf-list tcn-to-instances  {
            // when " ../enable-tcn-propagation + ../non-virtual-channel ";
            type  string {
                length "1..255";
                pattern "[^?' =,>|]+";
            }
            description "List of Instance that are to be notified when TCN occurs for this
                        instance if topology change notification (TCN) propagation is enabled";
        } // END of tcn-to-instances definition.

        leaf non-virtual-channel  {
            // when " ../ring-type='sub-ring' + ../ring-name ";
            type  empty;
            description "Creates a non-virtual channel";
        } // END of non-virtual-channel definition.

        leaf ring-id  {
            type  uint8 {
                 range "1..239"  {
                    description "1..239: Supported range 1 - 239";
                 }
            }
            description "G.8032 ring instance identifier (Ring ID).";
        } // END of ring-id definition.

        leaf description  {
            type  cml-data-types:cml_line_t {
                length "1..255";
            }
            description "Textual description of the erps-instance.";
        } // END of description definition.

    } // END of erpsv2-instance-config definition.
    grouping erpsv2-instance-state {
        description
            "Grouping for erpsv2-instances-state operational state data";
        leaf instance-id  {
            type  uint8;
            description "This attribute specifies the ERPS instance id";
        } // END of instance-id definition.

        leaf node-id  {
            type  string {
                length "1..1965";
            }
            description "This attribute specifies the node id";
        } // END of node-id definition.

        leaf ring  {
            type  string {
                length "1..1965";
            }
            description "This attribute specifies the ring name";
        } // END of ring definition.

        leaf virtual  {
            type  string {
                length "1..1965";
            }
            description "This attribute specifies the attached instance VID and ring id";
        } // END of virtual definition.

        leaf attached  {
            type  string {
                length "1..1965";
            }
            description "This attribute specifies the ERPS instance on major ring";
        } // END of attached definition.

        leaf attached-to  {
            type  string {
                length "1..1965";
            }
            description "This attribute specifies the ring attached to ERP instance";
        } // END of attached-to definition.

        leaf tcn-propagation  {
            type  string {
                length "1..1965";
            }
            description "This attribute specifies the TCN propogation";
        } // END of tcn-propagation definition.

        leaf erp-state  {
            type  ipi-erpsv2-types:erpsv2_erp_state_t;
            description "This attribute specifies the ERPS state details";
        } // END of erp-state definition.

        leaf initial-timer-status  {
            type  string {
                length "1..1965";
            }
            description "This attribute specifies the initial timer status";
        } // END of initial-timer-status definition.

        leaf wait-to-restore-timer  {
            type  string {
                length "1..1965";
            }
            description "This attribute specifies the wait to restore timer";
        } // END of wait-to-restore-timer definition.

        leaf wait-to-block-timer  {
            type  uint32;
            units "seconds";
            description "This attribute specifies the wait to block timer";
        } // END of wait-to-block-timer definition.

        leaf hold-off-timer  {
            type  uint16;
            units "seconds";
            description "This attribute specifies the hold off timer details";
        } // END of hold-off-timer definition.

        leaf guard-timer  {
            type  uint16;
            units "seconds";
            description "This attribute specifies the gurad timer details";
        } // END of guard-timer definition.

        leaf east-if-name  {
            type  string {
                length "1..1965";
            }
            description "This attribute specifies the east interface name";
        } // END of east-if-name definition.

        leaf east-link-status  {
            type  ipi-erpsv2-types:erpsv2_link_status_t;
            description "This attribute specifies the east link status";
        } // END of east-link-status definition.

        leaf east-if-state  {
            type  ipi-erpsv2-types:erpsv2_interface_state_t;
            description "This attribute specifies east interface state";
        } // END of east-if-state definition.

        leaf east-bpr  {
            type  string {
                length "1..1965";
            }
            description "This attribute specifies the east Blocked port reference";
        } // END of east-bpr definition.

        leaf east-node-id  {
            type  string {
                length "1..1965";
            }
            description "This attribute specifies the east node id";
        } // END of east-node-id definition.

        leaf west-if-name  {
            type  string {
                length "1..1965";
            }
            description "This attribute specifies the west interface name";
        } // END of west-if-name definition.

        leaf west-link-status  {
            type  ipi-erpsv2-types:erpsv2_link_status_t;
            description "This attribute specifies the west interface link status";
        } // END of west-link-status definition.

        leaf west-if-state  {
            type  ipi-erpsv2-types:erpsv2_interface_state_t;
            description "This attribute specifies the west interface link state";
        } // END of west-if-state definition.

        leaf west-bpr  {
            type  string {
                length "1..1965";
            }
            description "This attribute specifies the west Blocked port reference";
        } // END of west-bpr definition.

        leaf west-node-id  {
            type  string {
                length "1..1965";
            }
            description "This attribute specifies the west node id";
        } // END of west-node-id definition.

        leaf east-cfm-mep-id  {
            type  uint16;
            description "This attribute specifies east CFM MEP id";
        } // END of east-cfm-mep-id definition.

        leaf east-cfm-cc-interval  {
            type  ipi-erpsv2-types:erpsv2_cfm_cc_interval_t;
            description "This attribute specifies the east CFM CC interval";
        } // END of east-cfm-cc-interval definition.

        leaf east-cfm-domain  {
            type  string {
                length "1..1965";
            }
            description "This attribute specifies the east CFM domain name";
        } // END of east-cfm-domain definition.

        leaf east-cfm-ma  {
            type  string {
                length "1..1965";
            }
            description "This attribute specifies east CFM Maintenance Association name";
        } // END of east-cfm-ma definition.

        leaf west-cfm-mep-id  {
            type  uint16;
            description "This attribute specifies west CFM MEP id";
        } // END of west-cfm-mep-id definition.

        leaf west-cfm-cc-interval  {
            type  ipi-erpsv2-types:erpsv2_cfm_cc_interval_t;
            description "This attribute specifies the west CFM CC interval";
        } // END of west-cfm-cc-interval definition.

        leaf west-cfm-domain  {
            type  string {
                length "1..1965";
            }
            description "This attribute specifies the west CFM domain name";
        } // END of west-cfm-domain definition.

        leaf west-cfm-ma  {
            type  string {
                length "1..1965";
            }
            description "This attribute specifies west CFM Maintenance Association name";
        } // END of west-cfm-ma definition.

        leaf aps-channel-level  {
            type  uint8;
            description "This attribte specifies the APS channel level";
        } // END of aps-channel-level definition.

        leaf aps-channel-vlan  {
            type  uint16;
            description "This attribute specifies the APS channel VLAN";
        } // END of aps-channel-vlan definition.

        leaf data-vlan  {
            type  string {
                length "1..1965";
            }
            description "This attribute specifies the data VLAN";
        } // END of data-vlan definition.

        leaf current-state  {
            type  ipi-erpsv2-types:erpsv2_ring_state_t;
            description "This attribute specifies the current state of the ERPS instance";
        } // END of current-state definition.

        leaf out-aps-pkts  {
            type  yang:counter32;
            description "This attribute specifies the APS transmitted packets";
        } // END of out-aps-pkts definition.

        leaf in-aps-pkts  {
            type  yang:counter32;
            description "This attribute specifies the APS received packets";
        } // END of in-aps-pkts definition.

    } // END of erpsv2-instance-state definition.
    grouping erpsv2-summary-state {
        description
            "Grouping for ERPSV2 summary state";
        leaf in-init-state  {
            type  uint16;
            description "This attribute specifies the number of ERP instances in initial state";
        } // END of in-init-state definition.

        leaf in-idle-state  {
            type  uint16;
            description "This attribute specifies the number of ERP instances in idle state";
        } // END of in-idle-state definition.

        leaf in-pending-state  {
            type  uint16;
            description "This attribute specifies the number of ERP instances in pending state";
        } // END of in-pending-state definition.

        leaf in-protection-state  {
            type  uint16;
            description "This attribute specifies the number of ERP instances in protection
                        state";
        } // END of in-protection-state definition.

        leaf in-fs-state  {
            type  uint16;
            description "This attribute specifies the number of ERP instances in Forced
                        switched state";
        } // END of in-fs-state definition.

        leaf in-ms-state  {
            type  uint16;
            description "This attribute specifies the number of ERP instances in manual
                        switched  state";
        } // END of in-ms-state definition.

        leaf installed-in-hw  {
            type  uint16;
            description "This attribute specifies the number of ERP instances installed in
                        hardware";
        } // END of installed-in-hw definition.

        leaf ring-configured  {
            type  uint16;
            description "This attribute specifies the number of ring configured";
        } // END of ring-configured definition.

        leaf associated-ring-configured  {
            type  uint16;
            description "This attribute specifies the number of associcated ring configured";
        } // END of associated-ring-configured definition.

        leaf instances-with-ring  {
            type  uint16;
            description "This attribute specifies the number of ERP instances configured with
                        ring";
        } // END of instances-with-ring definition.

        leaf instances-without-ring  {
            type  uint16;
            description "This attribute specifies the number of ERP instances configured
                        without ring";
        } // END of instances-without-ring definition.

    } // END of erpsv2-summary-state definition.
    grouping erpsv2-instance-summary-top {
        description
            "Top level grouping for ERPSV2 instance summary";
        container instances-summary {
            description
                "Container for ERPSv2 instances summary";
            container state {
                config false;
                description
                    "Operational state data for ERPSv2 summary";
                uses erpsv2-summary-state;
            } // END of state-container definition.
        } // END of instances-summary-container definition.
    } // END of erpsv2-instance-summary-top definition.
    grouping erpsv2-instance-previous-state {
        description
            "Grouping for erp-instance notifcation state data";
        leaf previous-state  {
            type  ipi-erpsv2-types:erpsv2_ring_state_t;
            description "The previous state of the ERPS instance";
        } // END of previous-state definition.

    } // END of erpsv2-instance-previous-state definition.
    grouping erpsv2-instance-role-config {
        description
            "Grouping for ERPS instance role configuration data";
        choice role-option {
            description
                "RPL role option";
            case owner {

                description
                    "Represents owner node in the ring.";

                leaf owner-port-id  {
                    type  ipi-erpsv2-types:erpsv2_port_id_t;
                    description "This identifies the ring port for which role is configured";
                } // END of owner-port-id definition.

            }
            case neighbor {

                description
                    "Represents neighbor node in the ring.";

                leaf neighbor-port-id  {
                    type  ipi-erpsv2-types:erpsv2_port_id_t;
                    description "This identifies the ring port for which role is configured";
                } // END of neighbor-port-id definition.

            }
            case next-neighbor {

                description
                    "Represents owner node in the ring.";

                leaf next-neighbor-port-id  {
                    type  ipi-erpsv2-types:erpsv2_port_id_t;
                    description "This identifies the ring port for which role is configured";
                } // END of next-neighbor-port-id definition.

            }
            case non-owner {

                description
                    "Represents normal node in the ring.";

                leaf non-owner  {
                    type  empty;
                    description "This identifies the ring port for which role is configured";
                } // END of non-owner definition.

            }
        } // END of role-option-choice definition.
    } // END of erpsv2-instance-role-config definition.
    grouping erpsv2-instance-role-top {
        description
            "Grouping for ERPS instance role";
        container instance-role {
            description
                "Container for instance-role";
            container config {
                description
                    "Configuration data for erpsv2-instance-role";
                uses erpsv2-instance-role-config;
            } // END of config-container definition.
            container state {
                config false;
                description
                    "Operational state data for erpsv2-instance-role";
                uses erpsv2-instance-role-config;
            } // END of state-container definition.
        } // END of instance-role-container definition.
    } // END of erpsv2-instance-role-top definition.
    grouping erpsv2-virtual-channel-config {
        description
            "Grouping for ERPS instance virtual channel configuration data";
        leaf channel-id  {
            type  uint16 {
                 range "2..4094"  {
                    description "2..4094: Supported range 2 - 4094";
                 }
            }
            mandatory true;
            description "Ring wide vlan-id used by ERPS instance to send and receive RAPS
                        message in the subring, by allowing the RAPS messages of the sub-ring
                        to flow through the major ring";
        } // END of channel-id definition.

        leaf attached-instance  {
            type  leafref {
                path  "/erpsv2/erp-instances/erp-instance/name";
            }
            mandatory true;
            description "This parameter specifies the ERPS instance on major ring which allows
                        the RAPS messages of Sub-ring, so RAPS message will be sent to other
                        nodes in the sub-ring";
        } // END of attached-instance definition.

    } // END of erpsv2-virtual-channel-config definition.
    grouping erpsv2-subinterface-config {
        description
            "Grouping for ERPS instance virtual channel configuration data";
        leaf name  {
            type  leafref {
                path  "/ipi-interface:interfaces/ipi-interface:interface/ipi-interface:name";
            }
            description "Subinterface name";
        } // END of name definition.

        leaf instance-name  {
            type  ipi-erpsv2-types:erpsv2_subinterface_instance_type_t;
            description "This parameter specifies the ERPS instance being configured in the
                        subinterface";
        } // END of instance-name definition.

    } // END of erpsv2-subinterface-config definition.
    grouping erpsv2-virtual-channel-top {
        description
            "Grouping for ERPS instance virtual channel";
        container virtual-channel {
            // when " ../config/ring-type='sub-ring-vc' ";
            description
                "Container for virtual-channel";
            container config {
                presence "yes";
                description
                    "Configuration data for erpsv2-virtual-channel";
                uses erpsv2-virtual-channel-config;
            } // END of config-container definition.
            container state {
                config false;
                description
                    "Operational state data for erpsv2-virtual-channel";
                uses erpsv2-virtual-channel-config;
            } // END of state-container definition.
        } // END of virtual-channel-container definition.
    } // END of erpsv2-virtual-channel-top definition.
    grouping erpsv2-link-state {
        description
            "Grouping for ERPS link operational state data";
        leaf link-name  {
            type  string {
                length "1..33";
                pattern "[^?' =,>|]+";
            }
            description "Name of West port associated with the ERPS instance";
        } // END of link-name definition.

        leaf link-state  {
            type  ipi-erpsv2-types:erpsv2_link_state_t;
            description "This parameter indicates the state of the west port associated with
                        the ERPS instance";
        } // END of link-state definition.

        leaf remote-node-id  {
            type  cml-data-types:cml_mac_addr_t {
                length "1..1965";
            }
            description "Node ID of the last R-APS message received over the ring port. During
                        initialization this value is set to 00:00:00:00:00:00 by ERP control
                        process.";
        } // END of remote-node-id definition.

        leaf remote-blocked-port-reference  {
            type  uint8 {
                 range "0..1"  {
                    description "0..1: Supported range 0 - 1";
                 }
            }
            description "Blocked port reference (BPR) of the last R-APS message received over
                        the ring port. During initialization this value is set to 0 by ERP
                        control process.";
        } // END of remote-blocked-port-reference definition.

    } // END of erpsv2-link-state definition.
    grouping erpsv2-east-link-top {
        description
            "Grouping for ERPS east link";
        container east-link {
            description
                "Container for ERPS east link state";
            container state {
                config false;
                description
                    "Operational state data for ERPS east link";
                uses erpsv2-link-state;
            } // END of state-container definition.
        } // END of east-link-container definition.
    } // END of erpsv2-east-link-top definition.
    grouping erpsv2-west-link-top {
        description
            "Grouping for ERPS west link";
        container west-link {
            description
                "Container for ERPS west link state";
            container state {
                config false;
                description
                    "Operational state data for ERPS west link";
                uses erpsv2-link-state;
            } // END of state-container definition.
        } // END of west-link-container definition.
    } // END of erpsv2-west-link-top definition.
    grouping erpsv2-aps-statistics-state {
        description
            "Grouping for ERPS RAPS statistics operational state data";
        leaf tx-ring-aps-messages  {
            type  yang:counter32;
            description "Number of R-APS messages transmitted";
        } // END of tx-ring-aps-messages definition.

        leaf rx-ring-aps-messages  {
            type  yang:counter32;
            description "Number of R-APS messages received";
        } // END of rx-ring-aps-messages definition.

    } // END of erpsv2-aps-statistics-state definition.
    grouping erpsv2-aps-statistics-top {
        description
            "Grouping for ERPS RAPS statistics";
        container aps-statistics {
            description
                "Container for aps-statistics";
            container state {
                config false;
                description
                    "Operational state data for aps-statistics";
                uses erpsv2-aps-statistics-state;
            } // END of state-container definition.
        } // END of aps-statistics-container definition.
    } // END of erpsv2-aps-statistics-top definition.
    grouping erpsv2-instance-top {
        description
            "Grouping for ERPS instance";
        container erp-instances {
            description
                "Container for ERPS instances";

            list erp-instance {
                key "name";
                description
                    "List of ERPS instances";
                leaf name  {
                    type  leafref {
                        path  "../config/name";
                    }
                    description "ERPS instance identifier";
                } // END of name definition.

                container config {
                    description
                        "Configuration data for ERPS instance";
                    uses erpsv2-instance-config;
                } // END of config-container definition.
                container state {
                    config false;
                    description
                        "Operational state data for ERPS instance";
                    uses erpsv2-instance-config;
                    uses erpsv2-instance-state;
                    uses erpsv2-instance-previous-state;
                } // END of state-container definition.
                uses erpsv2-associate-ring-top;
                uses erpsv2-instance-role-top;
                uses erpsv2-aps-channel-top;
                uses erpsv2-aps-channel-vlan-top;
                uses erpsv2-data-vlan-top;
                uses erpsv2-virtual-channel-top;
                uses erpsv2-east-link-top;
                uses erpsv2-west-link-top;
                uses erpsv2-aps-statistics-top;
            } // End of erp-instance-list
        } // END of erp-instances-container definition.
    } // END of erpsv2-instance-top definition.
    grouping erpsv2-debug-config {
        description
            "G8032 ERPS debug configuration attributes";
        leaf options  {
            type  ipi-erpsv2-types:erpsv2_debug_t;
            description "Supported debug options for G.8032";
        } // END of options definition.

    } // END of erpsv2-debug-config definition.
    grouping erpsv2-debug-terminal-top {
        description
            "G8032 ERPS debug state attributes";
        leaf terminal-debug-status  {
            type  ipi-erpsv2-types:erpsv2_debug_t;
            description "Supported debug options for G.8032";
        } // END of terminal-debug-status definition.

    } // END of erpsv2-debug-terminal-top definition.
    grouping erpsv2-debug-top {
        description
            "Grouping for g8032 debug";
        container debug {
            description
                "Container for g8032 debugging functions";
            container config {
                description
                    "Configuration data for g8032 debug";
                uses erpsv2-debug-config;
            } // END of config-container definition.
            container state {
                config false;
                description
                    "Operational state data for g8032 debug";
                uses erpsv2-debug-config;
                uses erpsv2-debug-terminal-top;
            } // END of state-container definition.
        } // END of debug-container definition.
    } // END of erpsv2-debug-top definition.
    grouping erpsv2-subinterface-top {
        description
            "Grouping for g8032 subinterfaces";
        container subinterfaces {
            description
                "Container for ERPS subinterface";

            list subinterface {
                if-feature feature-list:HAVE_SUBINTERFACE;
                if-feature feature-list:HAVE_G8032V2;
                key "name";
                description
                    "List of ERPS subinterfaces";
                leaf name  {
                    type  leafref {
                        path  "../config/name";
                    }
                    description "Subinterface name";
                } // END of name definition.

                container config {
                    description
                        "Configuration data for ERPS subinterface";
                    uses erpsv2-subinterface-config;
                } // END of config-container definition.
                container state {
                    config false;
                    description
                        "Operational state data for ERPS subinterface";
                    uses erpsv2-subinterface-config;
                } // END of state-container definition.
            } // End of subinterface-list
        } // END of subinterfaces-container definition.
    } // END of erpsv2-subinterface-top definition.

    grouping  erpsv2-grouping {
    description
        "Container for ERPS module";
    container erpsv2 {
        if-feature feature-list:HAVE_G8032V2;
        if-feature feature-list:HAVE_ONMD;
        description
            "Container for ERPS module";
        uses erpsv2-ring-top;
        uses erpsv2-profiles-top;
        uses erpsv2-instance-top;
        uses erpsv2-debug-top;
        uses erpsv2-subinterface-top;
        uses erpsv2-instance-summary-top;
    } // END of erpsv2-container definition.
    } // END of erpsv2-grouping definition.

    uses erpsv2-grouping;

    rpc erpsv2-switch-erp-instance {
        if-feature feature-list:HAVE_G8032V2;
        if-feature feature-list:HAVE_ONMD;
        description "Perform administrative action on the ring (instance).";
        input  {
            leaf instance-name  {
                type string {
                    length "1..255";
                }
                mandatory true;
                description "ERPS instance identifier";
            }
            leaf operation  {
                type ipi-erpsv2-types:erpsv2_switch_operation_t;
                mandatory true;
                description "G.8032 administrative operation types.";
            }
            leaf port-id  {
                type ipi-erpsv2-types:erpsv2_port_id_t;
                mandatory true;
                description "Ring port to perform switch operation.";
            }
        }
    }

    rpc erpsv2-clear-ring-erp-instance {
        if-feature feature-list:HAVE_G8032V2;
        if-feature feature-list:HAVE_ONMD;
        description "Clear an existing Forced-Switch (FS) or Manual-Switch (MS) condition
                    on the ring port.";
        input  {
            leaf instance-name  {
                type string {
                    length "1..255";
                }
                mandatory true;
                description "ERPS instance identifier";
            }
        }
    }

    rpc erpsv2-clear-aps-statistics {
        if-feature feature-list:HAVE_G8032V2;
        if-feature feature-list:HAVE_ONMD;
        description "Clear APS statistics";
        input  {
            leaf instance-name  {
                type string {
                    length "1..255";
                }
                mandatory true;
                description "ERPS instance identifier";
            }
        }
    }

    rpc erpsv2-terminal-debug-on {
        if-feature feature-list:HAVE_G8032V2;
        if-feature feature-list:HAVE_ONMD;
        description "Enable g8032 debugging functions";
        input  {
            leaf terminal-debug-options  {
                type ipi-erpsv2-types:erpsv2_debug_t;
                mandatory true;
                description "Use this attribute to debug g8032 feature.";
            }
        }
    }

    rpc erpsv2-terminal-debug-off {
        if-feature feature-list:HAVE_G8032V2;
        if-feature feature-list:HAVE_ONMD;
        description "Disable g8032 debugging functions";
        input  {
            leaf terminal-debug-options  {
                type ipi-erpsv2-types:erpsv2_debug_t;
                mandatory true;
                description "Use this attribute to debug g8032 feature.";
            }
        }
    }

    notification erpsv2-instance-state-change-notification {
        if-feature feature-list:HAVE_G8032V2;
        if-feature feature-list:HAVE_ONMD;

        description "This notification indicates state change of the instance per the G.8032 state machine.";

        leaf severity {
            type cml-data-types:cml_notif_severity_t;
            description "Notification severity level (value: INFO)";
        }

        leaf eventClass {
            type cml-data-types:cml_notif_class_t;
            description "Notification event class (value: STATE)";
        }

        leaf name {
            type  string;
        description
            "ERPS instance identifier";
        }

        leaf current-state {
            type ipi-erpsv2-types:erpsv2_ring_state_t;
        description
            "This attribute specifies the current state of the ERPS instance";
        }

        leaf previous-state {
            type ipi-erpsv2-types:erpsv2_ring_state_t;
        description
            "The previous state of the ERPS instance";
        }
    }

    notification erpsv2-east-interface-state-change-notification {
        if-feature feature-list:HAVE_G8032V2;
        if-feature feature-list:HAVE_ONMD;

        description "This notification indicates east interface state change of the ERPS instance.";

        leaf severity {
            type cml-data-types:cml_notif_severity_t;
            description "Notification severity level (value: INFO)";
        }

        leaf eventClass {
            type cml-data-types:cml_notif_class_t;
            description "Notification event class (value: STATE)";
        }

        leaf name {
            type  string;
        description
            "ERPS instance identifier";
        }

        leaf link-name {
            type  string;
        description
            "Name of West port associated with the ERPS instance";
        }

        leaf link-state {
            type ipi-erpsv2-types:erpsv2_link_state_t;
        description
            "This parameter indicates the state of the west port associated with
                    the ERPS instance";
        }
    }

    notification erpsv2-west-interface-state-change-notification {
        if-feature feature-list:HAVE_G8032V2;
        if-feature feature-list:HAVE_ONMD;

        description "This notification indicates west interface state change of the ERPS instance.";

        leaf severity {
            type cml-data-types:cml_notif_severity_t;
            description "Notification severity level (value: INFO)";
        }

        leaf eventClass {
            type cml-data-types:cml_notif_class_t;
            description "Notification event class (value: STATE)";
        }

        leaf name {
            type  string;
        description
            "ERPS instance identifier";
        }

        leaf link-name {
            type  string;
        description
            "Name of West port associated with the ERPS instance";
        }

        leaf link-state {
            type ipi-erpsv2-types:erpsv2_link_state_t;
        description
            "This parameter indicates the state of the west port associated with
                    the ERPS instance";
        }
    }

}
