/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-erpsv2-types.yang
*
*/

module ipi-erpsv2-types {

    yang-version 1.1;

    namespace   "http://www.ipinfusion.com/yang/ocnos/ipi-erpsv2-types";

    prefix "ipi-erpsv2-types";

    organization
        "IP Infusion Inc.";

    contact
        "Address: 3965 Freedom Circle, Suite 200, Santa Clara, CA 95054
         Phone: +1 408-400-1900
         E-mail: support@ipinfusion.com
         Web: http://www.ipinfusion.com/";

    description
        "ERPSv2 data types";


    revision "2025-02-18" {
        description "Getapi implementation for ERPS";
        reference " 0.6.0.";
    }

    revision "2023-08-16" {
        description "Updated subifp erp-instance options";
        reference " 0.5.0.";
    }

    revision "2023-03-13" {
        description "Added new sub-ring-vc for Ring types";
        reference " 0.4.0.";
    }

    revision "2023-01-10" {
        description "Added new datatype for erps instance in subinterface";
        reference " 0.3.2.";
    }

    revision "2022-06-28" {
        description "Fix description of rx and tx element on ERPSV2_DEBUG_T";
        reference " 0.3.1.";
    }

    revision "2022-06-01" {
        description "Updated the yang file with feature";
        reference " 0.3.0.";
    }

    revision "2021-04-18" {
        description "Added ERPSV2_DEBUG_T datatype";
        reference " 0.2.0.";
    }

    revision "2021-02-08" {
        description "Initial Version";
        reference " 0.1.0.";
    }



    typedef  erpsv2_protection_mode_t {
        type enumeration {
            enum revertive {
                value 0;
                description "Represents revertive mode operation of a G.8032 ethernet ring.";
            }
            enum non-revertive {
                value 1;
                description "Represents non-revertive mode operation of a G.8032 ethernet ring.";
            }
        }
        description "This typedef defines G.8032 ring protection operation mode.";
    }

    typedef  erpsv2_link_state_t {
        type enumeration {
            enum invalid {
                value 0;
                description "Represents Ring port is in initialization state.";
            }
            enum unblocked {
                value 1;
                description "Ring port is in normal state and ready to forward traffic ring controlled data traffic.";
            }
            enum blocked {
                value 2;
                description "Ring port is blocked and it is not forwarding any data traffic. In normal operations a port is blocked if it is a RPL port.";
            }
            enum failed {
                value 3;
                description "Ring port has local failure. Port is blocked and it is not forwarding any traffic.";
            }
            enum blocked-failed {
                value 4;
                description "Ring port has local failure. Port is blocked and it is not forwarding any traffic.";
            }
            enum local-ms {
                value 5;
                description "Ring port has been blocked by administrative manual switch action.";
            }
            enum local-fs {
                value 6;
                description "Ring port has been blocked by administrative force switch action.";
            }
        }
        description "This typedef defines G.8032 erps link operation state.";
    }

    typedef  erpsv2_ring_state_t {
        type enumeration {
            enum invalid-state {
                value 0;
                description "None";
            }
            enum initializing {
                value 1;
                description "Ring protocol state machine is initializing and it is not yet operational.";
            }
            enum pending {
                value 2;
                description "Ring does not have any failure or administrative condition however RPL is blocked. In case of revertive mode operation wait-to-restore timer is running.";
            }
            enum idle {
                value 3;
                description "Ring is operational in normal state RPL link is blocked and no failure or administrative condition exists. Owner node is transmitting R-APS (NR or RB) PDUs.";
            }
            enum force-switch {
                value 4;
                description "User has force-switched ring. This state overrides protection state.";
            }
            enum protection {
                value 5;
                description "One or more failure condition exists on the ring. Failed nodes are transmitting R-APS (SF) PDUs. Upon reaching to protection state ring unblocks RPL link to allow user traffic.";
            }
            enum manual-switch {
                value 6;
                description "User has manually switched ring. This is usually done to perform maintenance operation on the ring node.";
            }
        }
        description "Protocol states for a ring instance.";
    }

    typedef  erpsv2_ring_type_t {
        type enumeration {
            enum major-ring {
                value 1;
                description "G.8032 major ring. In this type of rings nodes are connected in full circular topology";
            }
            enum sub-ring {
                value 2;
                description "G.8032 sub-ring without virtual channel";
            }
            enum sub-ring-vc {
                value 3;
                description "G.8032 sub-ring with virtual channel";
            }
        }
        description "Ring types.";
    }

    typedef  erpsv2_switch_operation_t {
        type enumeration {
            enum force-switch {
                value 0;
                description "Trigger force switch. This operation overrides all other state of the ring.";
            }
            enum manual-switch {
                value 1;
                description "Trigger manual switch. This operation is allowed only when a ring instance is in idle or pending state. This action allows administrator to temporarily block another ring port and unblock RPL link to perform maintenance operation in the ring.";
            }
        }
        description "G.8032 administrative operation types.";
    }

    typedef  erpsv2_interface_state_t {
        type enumeration {
            enum UP {
                value 1;
                description "Interface state as Up";
            }
            enum DOWN {
                value 2;
                description "Interface state as Down";
            }
        }
        description "Specifies the east interface or west interface is up or down";
    }

    typedef  erpsv2_erp_state_t {
        type enumeration {
            enum UNKNOWN_STATE {
                value 0;
                description "Unknown state";
            }
            enum G8032_ST_INIT {
                value 1;
                description "Init state";
            }
            enum G8032_ST_PENDING {
                value 2;
                description "Pending state";
            }
            enum G8032_ST_IDLE {
                value 3;
                description "Idle state";
            }
            enum G8032_ST_FS {
                value 4;
                description "Forced Switch state";
            }
            enum G8032_ST_PROTECTION {
                value 5;
                description "Protection state";
            }
            enum G8032_ST_MS {
                value 6;
                description "Manual Switch state";
            }
        }
        description "Specifies the ERPS state details";
    }

    typedef  erpsv2_cfm_cc_interval_t {
        type enumeration {
            enum 3ms {
                value 1;
                description "3 milliseconds CFM CC Interval";
            }
            enum 10ms {
                value 2;
                description "10 milliseconds CFM CC Interval";
            }
            enum 100ms {
                value 3;
                description "100 milliseconds CFM CC Interval";
            }
            enum 1s {
                value 4;
                description "1 second CFM CC Interval";
            }
            enum 10s {
                value 5;
                description "10 seconds CFM CC Interval";
            }
            enum 1m {
                value 6;
                description "1 minute CFM CC Interval";
            }
            enum 10m {
                value 7;
                description "10 minutes CFM CC Interval";
            }
        }
        description "Specifies the ERPS CFM CC Interval";
    }

    typedef  erpsv2_link_status_t {
        type enumeration {
            enum - {
                value 0;
                description "Invalid state.";
            }
            enum Unblocked {
                value 1;
                description "Unblocked node.";
            }
            enum Blocked {
                value 2;
                description "Blocked state.";
            }
            enum Failed {
                value 3;
                description "Failed state.";
            }
            enum UNKNOWN {
                value 4;
                description "Unknown state.";
            }
        }
        description "Specify the interface link status for east interface and west
                    interface";
    }

    typedef  erpsv2_port_id_t {
        type enumeration {
            enum east-interface {
                value 1;
                description "East-interface of the ring node.";
            }
            enum west-interface {
                value 2;
                description "West-interface of the ring node.";
            }
        }
        description "Each ring instance has maximum of two ports. This definition
                    labels these ports as east or west for identifications.";
    }

    typedef  erpsv2_debug_t {
        type bits {
            bit tx {
                position 0;
                description "Transmitted PDUs";
            }
            bit rx {
                position 1;
                description "Received PDUs";
            }
            bit fsm {
                position 2;
                description "Instance Finite State Machine updates";
            }
            bit timers {
                position 3;
                description "Protocol timer events";
            }
            bit events {
                position 4;
                description "Protocol events";
            }
            bit external {
                position 5;
                description "External CFM and NSM events";
            }
            bit hal {
                position 6;
                description "HAL events";
            }
        }
        description "type definition for ERPSV2_DEBUG_T";
    }

    typedef  erpsv2_subinterface_instance_type_t {
        type union {
            type string {

            }
        }
        description "type definition for ERPSV2_SUBINTERFACE_INSTANCE_TYPE_T";
    }

}
