/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ospfv3.yang
*
*/

submodule ospfv3 {

    belongs-to  ZebOS { prefix ZebOS; }
    include vr;
    include interface;
    include vrf;


    import cml_data_types {
        prefix cml_data_types;
    }

    import feature_list {
        prefix feature_list;
    }

    description
        "Layer-3 OSPFv3 configurations";


    revision "2017-03-05" {
        description "Added implicit_delete for Interface tables.";
    }

    revision "2017-02-23" {
        description "Updated Summary address APIs.";
    }

    revision "2017-02-14" {
        description "Updated Runtime attributes.";
    }

    revision "2016-10-20" {
        description "Modified according to backend structures.";
    }



    grouping ospf6_master-grouping {
        list ospf6_master {
             
            description
                "OSPFv3 master for system wide configurations and variables.";

            config true;
            key "vrId";

            
            leaf vrId  {
                type  cml_data_types:CML_UINT32_T;  
            } // END of vrId definition.

            leaf displaySingleLine  {
                type  cml_data_types:CML_BOOL_T;  
            } // END of displaySingleLine definition.

            leaf gracePeriod  {
                if-feature feature_list:HAVE_RESTART;
                type  cml_data_types:CML_UINT16_T {
                     range "1..1800";
                }
            } // END of gracePeriod definition.

            leaf restartPlannedOnly  {
                if-feature feature_list:HAVE_RESTART;
                type  cml_data_types:CML_BOOL_T;  
            } // END of restartPlannedOnly definition.


            list ospf6 {
                 
                description
                    "OSPFv3 datastructure is for system-wide configuration and variables.";

                config true;
                key "ospf6ProcessTag";

                
                leaf ospf6ProcessTag  {
                    type  cml_data_types:CML_STRING_T {
                        length "0..255";
                    }
                    description "router ipv6 ospf";
                } // END of ospf6ProcessTag definition.

                leaf vrfName  {
                    if-feature feature_list:HAVE_VRF_OSPF6;
                    type  cml_data_types:CML_STRING_T {
                        length "0..255";
                    }
                } // END of vrfName definition.

                leaf routerId  {
                    type  cml_data_types:CML_IPV4_ADDR_T;  
                } // END of routerId definition.

                leaf config_frr  {
                    if-feature feature_list:HAVE_OSPF6_LFA;
                    type  cml_data_types:CML_BOOL_T;  
                } // END of config_frr definition.

                leaf abrType  {
                    type  cml_data_types:CML_OSPF6_ABR_TYPE_T;  
                } // END of abrType definition.

                leaf teEnabled  {
                    if-feature feature_list:HAVE_OSPF6_TE;
                    type  cml_data_types:CML_BOOL_T;  
                } // END of teEnabled definition.

                leaf restartMethod  {
                    if-feature feature_list:HAVE_RESTART;
                    type  cml_data_types:CML_BOOL_T;  
                } // END of restartMethod definition.

                leaf dbSummaryOpt  {
                    type  cml_data_types:CML_BOOL_T;  
                } // END of dbSummaryOpt definition.

                leaf bfdEnabled  {
                    if-feature feature_list:HAVE_BFD;
                    type  cml_data_types:CML_BOOL_T;  
                } // END of bfdEnabled definition.

                leaf floodReductionEnabled  {
                    if-feature feature_list:HAVE_OSPF6_OD;
                    type  cml_data_types:CML_BOOL_T;  
                } // END of floodReductionEnabled definition.

                leaf-list passiveIfName  {
                    type  cml_data_types:CML_STRING_T {
                        length "0..255";
                    }
                    description "passive-interface with interface name";
                } // END of passiveIfName definition.

                leaf defaultMetric  {
                    type  cml_data_types:CML_UINT32_T {
                         range "1..16777214";
                    }
                } // END of defaultMetric definition.

                leaf minspfDelay  {
                    type  cml_data_types:CML_UINT32_T {
                         range "0..2147483647";
                    }
                } // END of minspfDelay definition.

                leaf maxspfDelay  {
                    type  cml_data_types:CML_UINT32_T {
                         range "0..2147483647";
                    }
                } // END of maxspfDelay definition.

                leaf minDelay  {
                    type  cml_data_types:CML_UINT32_T {
                         range "0..2147483647";
                    }
                } // END of minDelay definition.

                leaf maxDelay  {
                    type  cml_data_types:CML_UINT32_T {
                         range "0..2147483647";
                    }
                    description "timers spf exp";
                } // END of maxDelay definition.

                leaf refBandwidth  {
                    type  cml_data_types:CML_UINT32_T {
                         range "1..4294967";
                    }
                } // END of refBandwidth definition.

                leaf maxConcurrentDd  {
                    type  cml_data_types:CML_UINT16_T {
                         range "1..65535";
                    }
                } // END of maxConcurrentDd definition.

                leaf maxUnusePacket  {
                    type  cml_data_types:CML_UINT32_T {
                         range "0..65535";
                    }
                } // END of maxUnusePacket definition.

                leaf maxUnuseLsa  {
                    type  cml_data_types:CML_UINT32_T {
                         range "0..65535";
                    }
                } // END of maxUnuseLsa definition.

                leaf distanceAll  {
                    type  cml_data_types:CML_UINT16_T {
                         range "1..254";
                    }
                } // END of distanceAll definition.

                leaf shutDown  {
                    type  cml_data_types:CML_BOOL_T;  
                } // END of shutDown definition.

                leaf logAdjChanges  {
                    type  cml_data_types:CML_BOOL_T;  
                } // END of logAdjChanges definition.

                leaf logAdjChangesDetail  {
                    type  cml_data_types:CML_BOOL_T;  
                } // END of logAdjChangesDetail definition.

                leaf ospfv3VersionNumber  {
                    type  cml_data_types:CML_UINT32_T;  
                    config false;
                } // END of ospfv3VersionNumber definition.

                leaf ospfv3AreaBdrRtrStatus  {
                    type  cml_data_types:CML_BOOL_T;  
                    config false;
                } // END of ospfv3AreaBdrRtrStatus definition.

                leaf ospfv3ASBdrRtrStatus  {
                    type  cml_data_types:CML_BOOL_T;  
                    config false;
                } // END of ospfv3ASBdrRtrStatus definition.

                leaf processUpTime  {
                    type  cml_data_types:CML_STRING_T {
                        length "0..255";
                    }
                    config false;
                } // END of processUpTime definition.

                leaf ddCountIn  {
                    type  cml_data_types:CML_UINT16_T;  
                    config false;
                } // END of ddCountIn definition.

                leaf ddCountOut  {
                    type  cml_data_types:CML_UINT16_T;  
                    config false;
                } // END of ddCountOut definition.

                leaf extenalLSACount  {
                    type  cml_data_types:CML_UINT32_T;  
                    config false;
                } // END of extenalLSACount definition.

                leaf lsdbChecksum  {
                    type  cml_data_types:CML_STRING_T {
                        length "0..255";
                    }
                    config false;
                } // END of lsdbChecksum definition.

                leaf unknownLSACount  {
                    type  cml_data_types:CML_UINT32_T;  
                    config false;
                } // END of unknownLSACount definition.

                leaf lSASelfCount  {
                    type  cml_data_types:CML_UINT32_T;  
                    config false;
                } // END of lSASelfCount definition.

                leaf lSARxCount  {
                    type  cml_data_types:CML_UINT32_T;  
                    config false;
                } // END of lSARxCount definition.

                leaf areaCount  {
                    type  cml_data_types:CML_UINT32_T;  
                    config false;
                } // END of areaCount definition.

                leaf isDsteEnabled  {
                    type  cml_data_types:CML_BOOL_T;  
                    config false;
                } // END of isDsteEnabled definition.


                list frr_pref {
                                         if-feature feature_list:HAVE_OSPF6_LFA;

                    description
                        "Keeps user preferences, lower index in the array is higher priority";

                    config true;
                    key "frrPrefIndex";

                    
                    leaf frrPrefIndex  {
                        type  cml_data_types:CML_UINT32_T {
                             range "1..4";
                        }
                    } // END of frrPrefIndex definition.

                    leaf frrPrefVal  {
                        mandatory true;
                        if-feature feature_list:HAVE_OSPF6_LFA;
                        type  cml_data_types:CML_OSPF_FRR_TIE_BREAK_VAL_T;  
                    } // END of frrPrefVal definition.

                } // End of frr_pref-list

                list area_table {
                     
                    description
                        "OSPFv3 area structure.";

                    config true;
                    key "areaId";

                    
                    leaf areaId  {
                        type  cml_data_types:CML_AREA_T;  
                    } // END of areaId definition.

                    leaf areaDefaultCost  {
                        type  cml_data_types:CML_UINT32_T {
                             range "0..16777215";
                        }
                        description "area default-cost";
                    } // END of areaDefaultCost definition.

                    leaf isAreaBackbone  {
                        type  cml_data_types:CML_BOOL_T;  
                        config false;
                    } // END of isAreaBackbone definition.

                    leaf isAreaActive  {
                        type  cml_data_types:CML_BOOL_T;  
                        config false;
                    } // END of isAreaActive definition.

                    leaf activeIfCount  {
                        type  cml_data_types:CML_UINT32_T;  
                        config false;
                    } // END of activeIfCount definition.

                    leaf areaIfCount  {
                        type  cml_data_types:CML_UINT32_T;  
                        config false;
                    } // END of areaIfCount definition.

                    leaf spfCalcCount  {
                        type  cml_data_types:CML_UINT32_T;  
                        config false;
                    } // END of spfCalcCount definition.

                    leaf lsaCount  {
                        type  cml_data_types:CML_UINT32_T;  
                        config false;
                    } // END of lsaCount definition.

                    leaf lsdbChecksum  {
                        type  cml_data_types:CML_STRING_T {
                            length "0..255";
                        }
                        config false;
                    } // END of lsdbChecksum definition.

                    leaf unknownLSACount  {
                        type  cml_data_types:CML_UINT32_T;  
                        config false;
                    } // END of unknownLSACount definition.

                    leaf isAreaAsbr  {
                        type  cml_data_types:CML_BOOL_T;  
                        config false;
                    } // END of isAreaAsbr definition.


                    list ospf6Vertex {
                         
                        description
                            "Shortest Path Tree/ABR table.";

                        config false;
                        key "vertexlinkId";

                        
                        leaf vertexlinkId  {
                            type  cml_data_types:CML_STRING_T {
                                length "0..255";
                            }
                        } // END of vertexlinkId definition.

                        leaf vertexDistance  {
                            type  cml_data_types:CML_UINT32_T;  
                        } // END of vertexDistance definition.

                        uses ospf6NextHop;
                    } // End of ospf6Vertex-list

                    list areaRangeIPv6 {
                         
                        description
                            "OSPFv3 Intra-area IPv4 routes";

                        config true;
                        key "rangeAddr";

                        
                        leaf rangeAddr  {
                            type  cml_data_types:CML_IPV6_PREFIX_T;  
                            description "area range";
                        } // END of rangeAddr definition.

                        leaf rangeStatus  {
                            type  cml_data_types:CML_OSPF6_AREA_RANGE_T;  
                        } // END of rangeStatus definition.

                    } // End of areaRangeIPv6-list

                    list areaVirtualLink {
                         
                        description
                            "OSPFv3 Area Virtual-link";

                        config true;
                        key "peerId";

                        
                        leaf peerId  {
                            type  cml_data_types:CML_IPV4_ADDR_T;  
                            description "area virtual-link";
                        } // END of peerId definition.

                        leaf helloInterval  {
                            type  cml_data_types:CML_UINT32_T {
                                 range "1..65535";
                            }
                        } // END of helloInterval definition.

                        leaf deadInterval  {
                            type  cml_data_types:CML_UINT32_T {
                                 range "1..65535";
                            }
                        } // END of deadInterval definition.

                        leaf retransmitInterval  {
                            type  cml_data_types:CML_UINT32_T {
                                 range "1..1800";
                            }
                        } // END of retransmitInterval definition.

                        leaf transmitDelay  {
                            type  cml_data_types:CML_UINT32_T {
                                 range "1..1800";
                            }
                        } // END of transmitDelay definition.

                        leaf fallOverBfd  {
                            if-feature feature_list:HAVE_BFD;
                            type  cml_data_types:CML_BOOL_T;  
                        } // END of fallOverBfd definition.

                        leaf instanceId  {
                            type  cml_data_types:CML_UINT32_T {
                                 range "0..31 | 64..95";
                            }
                        } // END of instanceId definition.

                        leaf vlinkName  {
                            type  cml_data_types:CML_STRING_T {
                                length "0..255";
                            }
                            config false;
                        } // END of vlinkName definition.

                        leaf vlinkInterfaceName  {
                            type  cml_data_types:CML_STRING_T {
                                length "0..255";
                            }
                            config false;
                        } // END of vlinkInterfaceName definition.

                        leaf vlinkInstanceId  {
                            type  cml_data_types:CML_UINT32_T;  
                            config false;
                        } // END of vlinkInstanceId definition.

                        leaf vlinkisHelloSupEnabled  {
                            type  cml_data_types:CML_BOOL_T;  
                            config false;
                        } // END of vlinkisHelloSupEnabled definition.

                        leaf vlinkIsDNAEnabled  {
                            type  cml_data_types:CML_BOOL_T;  
                            config false;
                        } // END of vlinkIsDNAEnabled definition.

                        leaf vlinkLocalAddress  {
                            type  cml_data_types:CML_STRING_T {
                                length "0..255";
                            }
                            config false;
                        } // END of vlinkLocalAddress definition.

                        leaf vlinkRemoteAddress  {
                            type  cml_data_types:CML_STRING_T {
                                length "0..255";
                            }
                            config false;
                        } // END of vlinkRemoteAddress definition.

                        leaf vlinkState  {
                            type  cml_data_types:CML_STRING_T {
                                length "0..255";
                            }
                            config false;
                        } // END of vlinkState definition.

                        leaf vlinkHelloDueTime  {
                            type  cml_data_types:CML_STRING_T {
                                length "0..255";
                            }
                            config false;
                        } // END of vlinkHelloDueTime definition.

                        leaf vlinkAdjacencyState  {
                            type  cml_data_types:CML_STRING_T {
                                length "0..255";
                            }
                            config false;
                        } // END of vlinkAdjacencyState definition.

                        uses lsdb;
                    } // End of areaVirtualLink-list
                    container area_table_stub {
                                                config true;

                        description
                            "OSPFv3 area structure.";

                        leaf isAreaStub  {
                            type  cml_data_types:CML_BOOL_T;  
                            description "area stub";
                        } // END of isAreaStub definition.

                        leaf isAreaStubNoSummary  {
                            type  cml_data_types:CML_BOOL_T;  
                            description "area stub no-summary";
                        } // END of isAreaStubNoSummary definition.

                        leaf isAreaNssa  {
                            if-feature feature_list:HAVE_NSSA;
                            type  cml_data_types:CML_BOOL_T;  
                        } // END of isAreaNssa definition.

                        leaf translator-role  {
                            type  cml_data_types:CML_OSPF6_TRANSLATOR_ROLE_T;  
                        } // END of translator-role definition.

                        leaf stability-interval  {
                            type  cml_data_types:CML_UINT32_T {
                                 range "0..2147483647";
                            }
                        } // END of stability-interval definition.

                        leaf no-redistribution  {
                            type  cml_data_types:CML_BOOL_T;  
                        } // END of no-redistribution definition.

                        leaf isAreaNoSummary  {
                            type  cml_data_types:CML_BOOL_T;  
                        } // END of isAreaNoSummary definition.

                        leaf translatorRole  {
                            type  cml_data_types:CML_OSPF6_NSSA_TRANSLATOR_ROLE_T;  
                        } // END of translatorRole definition.

                        leaf nssadefaultInformationOriginate  {
                            type  cml_data_types:CML_BOOL_T;  
                        } // END of nssadefaultInformationOriginate definition.

                        leaf nssaMetric  {
                            type  cml_data_types:CML_UINT32_T {
                                 range "0..16777214";
                            }
                        } // END of nssaMetric definition.

                        leaf nssaMetricType  {
                            type  cml_data_types:CML_OSPF_METRIC_TYPE_T;  
                        } // END of nssaMetricType definition.

                        leaf nssarouteMap  {
                            type  cml_data_types:CML_STRING_T {
                                length "0..255";
                            }
                        } // END of nssarouteMap definition.

                    } // END of area_table_stub-container definition.
                    uses lsdb;
                } // End of area_table-list

                list addressFamily {
                     
                    description
                        " OSPFv3 Address Family.";

                    config true;
                    key "isAddrFamily";

                    
                    leaf isAddrFamily  {
                        type  cml_data_types:CML_BOOL_T;  
                    } // END of isAddrFamily definition.


                    list area_table {
                         
                        description
                            "OSPFv3 area structure.";

                        config true;
                        key "areaId";

                        
                        leaf areaId  {
                            type  cml_data_types:CML_AREA_T;  
                        } // END of areaId definition.


                        list areaRangeIPv4 {
                             
                            description
                                "Area Range IPv4 address list";

                            config true;
                            key "rangeAddrIPV4";

                            
                            leaf rangeAddrIPV4  {
                                type  cml_data_types:CML_IPV4_ADDR_PREFIX_T;  
                            } // END of rangeAddrIPV4 definition.

                            leaf rangeStatusIPv4  {
                                type  cml_data_types:CML_OSPF6_AREA_RANGE_T;  
                            } // END of rangeStatusIPv4 definition.

                        } // End of areaRangeIPv4-list
                    } // End of area_table-list

                    list summaryAddressIpv4 {
                         
                        description
                            "OSPFv3 IPv4 Summary Address list";

                        config true;
                        key "summaryIpv4Addr";

                        
                        leaf summaryIpv4Addr  {
                            type  cml_data_types:CML_IPV4_PREFIX_T;  
                        } // END of summaryIpv4Addr definition.

                        leaf setTag  {
                            type  cml_data_types:CML_UINT32_T {
                                 range "0..4294967295";
                            }
                        } // END of setTag definition.

                        leaf not-advertise  {
                            type  cml_data_types:CML_BOOL_T;  
                            description "summary-address with not-advertise";
                        } // END of not-advertise definition.

                    } // End of summaryAddressIpv4-list
                    uses redistribute;
                    uses default-information-originate;
                } // End of addressFamily-list

                list distributeList {
                                         if-feature feature_list:HAVE_ACL;

                    description
                        "Distribute list for OSPFv3 Protocol";

                    config true;
                    key "accessListName";

                    
                    leaf accessListName  {
                        type  cml_data_types:CML_STRING_T {
                            length "0..255";
                        }
                    } // END of accessListName definition.

                    leaf ospf6DistIn  {
                        type  cml_data_types:CML_BOOL_T;  
                    } // END of ospf6DistIn definition.


                    list distributeListProtocol {
                         
                        description
                            "Distribute list for OSPFv3 Protocol";

                        config true;
                        key "ospf6distProtocol";

                        
                        leaf ospf6distProtocol  {
                            type  cml_data_types:CML_OSPF6_ROUTE_SOURCE_TYPE_T;  
                        } // END of ospf6distProtocol definition.

                    } // End of distributeListProtocol-list

                    list distributeListOspf {
                         
                        description
                            "Distribute list for OSPFv3 Protocol";

                        config true;
                        key "ospf6distOspfProtocol";

                        
                        leaf ospf6distOspfProtocol  {
                            type  cml_data_types:CML_OSPF_AREA_ID_T;  
                        } // END of ospf6distOspfProtocol definition.

                    } // End of distributeListOspf-list
                } // End of distributeList-list

                list summaryAddressIpv6 {
                     
                    description
                        "OSPFv3 IPv6 Summary Address";

                    config true;
                    key "summaryIpv6Addr";

                    
                    leaf summaryIpv6Addr  {
                        type  cml_data_types:CML_IPV6_PREFIX_T;  
                    } // END of summaryIpv6Addr definition.

                    leaf all-tag  {
                        type  cml_data_types:CML_UINT32_T {
                             range "0..4294967295";
                        }
                        default "0";
                        description "summary-address with all-tag ";
                    } // END of all-tag definition.

                    leaf not-advertise6  {
                        type  cml_data_types:CML_BOOL_T;  
                    } // END of not-advertise6 definition.

                    leaf translate-tag  {
                        type  cml_data_types:CML_UINT32_T {
                             range "0..4294967295";
                        }
                        default "0";
                        description "summary-address with translate-tag";
                    } // END of translate-tag definition.

                } // End of summaryAddressIpv6-list
                container cspf {
                                        config true;

                    description
                        "Constrained Shortest Path First (CSPF) Instance";

                    leaf cspfEnabled  {
                        if-feature feature_list:HAVE_OSPF6_CSPF;
                        type  cml_data_types:CML_BOOL_T;  
                    } // END of cspfEnabled definition.

                    leaf cspfTieBreak  {
                        if-feature feature_list:HAVE_OSPF6_CSPF;
                        type  cml_data_types:CML_OSPF6_CSPF_TYPE_T;  
                    } // END of cspfTieBreak definition.

                    leaf cspfDefRetryInterval  {
                        if-feature feature_list:HAVE_OSPF6_CSPF;
                        type  cml_data_types:CML_UINT16_T {
                             range "1..3600";
                        }
                    } // END of cspfDefRetryInterval definition.

                } // END of cspf-container definition.
                container distance {
                                        config true;

                    description
                        "Define an administrative distance";

                    leaf distanceIntra  {
                        type  cml_data_types:CML_UINT32_T {
                             range "1..254";
                        }
                    } // END of distanceIntra definition.

                    leaf distanceInter  {
                        type  cml_data_types:CML_UINT32_T {
                             range "1..254";
                        }
                    } // END of distanceInter definition.

                    leaf distanceExternal  {
                        type  cml_data_types:CML_UINT32_T {
                             range "1..254";
                        }
                    } // END of distanceExternal definition.

                } // END of distance-container definition.
                uses redistribute;
                uses default-information-originate;
                uses lsdb;
                uses Route;
            } // End of ospf6-list

            list ospf6Interface {
                 
                description
                    "OSPFv3 interface related operations";

                config true;
                key "ifName";

                
                leaf ifName  {
                    type  cml_data_types:CML_STRING_T {
                        length "0..255";
                    }
                } // END of ifName definition.

                leaf ifShutDown  {
                    type  cml_data_types:CML_BOOL_T;  
                } // END of ifShutDown definition.


                list ospf6IfinstanceId {
                     
                    description
                        "OSPFv3 instanceId of interface related operations";

                    config true;
                    key "instanceId6";

                    
                    leaf instanceId6  {
                        type  cml_data_types:CML_INT32_T {
                             range "0..31 | 64..95";
                        }
                    } // END of instanceId6 definition.

                    leaf networkType  {
                        type  cml_data_types:CML_OSPF6_NETWORK_T;  
                    } // END of networkType definition.

                    leaf cost  {
                        type  cml_data_types:CML_UINT32_T {
                             range "1..65535";
                        }
                    } // END of cost definition.

                    leaf teMetric  {
                        if-feature feature_list:HAVE_OSPF6_TE;
                        type  cml_data_types:CML_UINT32_T {
                             range "1..65535";
                        }
                    } // END of teMetric definition.

                    leaf ifHelloInterval  {
                        type  cml_data_types:CML_UINT32_T {
                             range "1..65535";
                        }
                    } // END of ifHelloInterval definition.

                    leaf ifDeadInterval  {
                        type  cml_data_types:CML_UINT32_T {
                             range "1..65535";
                        }
                    } // END of ifDeadInterval definition.

                    leaf ifRetransmitInterval  {
                        type  cml_data_types:CML_UINT32_T {
                             range "1..1800";
                        }
                    } // END of ifRetransmitInterval definition.

                    leaf ifPriority  {
                        type  cml_data_types:CML_UINT8_T {
                             range "0..255";
                        }
                    } // END of ifPriority definition.

                    leaf ifTransmitDelay  {
                        type  cml_data_types:CML_UINT32_T {
                             range "1..1800";
                        }
                    } // END of ifTransmitDelay definition.

                    leaf ifMtuIgnore  {
                        type  cml_data_types:CML_BOOL_T;  
                    } // END of ifMtuIgnore definition.

                    leaf ifDemandCircuit  {
                        if-feature feature_list:HAVE_OSPF6_OD;
                        type  cml_data_types:CML_BOOL_T;  
                    } // END of ifDemandCircuit definition.

                    leaf ifFloodReduction  {
                        if-feature feature_list:HAVE_OSPF6_OD;
                        type  cml_data_types:CML_BOOL_T;  
                    } // END of ifFloodReduction definition.

                    leaf ifFrrDisable  {
                        if-feature feature_list:HAVE_OSPF6_LFA;
                        type  cml_data_types:CML_BOOL_T;  
                    } // END of ifFrrDisable definition.

                    leaf ifAreaId  {
                        type  cml_data_types:CML_AREA_T;  
                    } // END of ifAreaId definition.

                    leaf ifTagId  {
                        type  cml_data_types:CML_STRING_T {
                            length "0..255";
                        }
                        default "NULL";
                    } // END of ifTagId definition.

                    leaf ifLinkLsaSuppression  {
                        type  cml_data_types:CML_OSPF6_LSA_SUPRESSION_STATE_T;  
                    } // END of ifLinkLsaSuppression definition.

                    leaf ifBfdEnable  {
                        if-feature feature_list:HAVE_BFD;
                        type  cml_data_types:CML_BOOL_T;  
                    } // END of ifBfdEnable definition.

                    leaf InterfaceLineProtocolState  {
                        type  cml_data_types:CML_INTERFACE_ADMIN_STATE_T;  
                        config false;
                    } // END of InterfaceLineProtocolState definition.

                    leaf InterfaceIfIndex  {
                        type  cml_data_types:CML_UINT32_T;  
                        config false;
                    } // END of InterfaceIfIndex definition.

                    leaf InterfaceIPV6Address  {
                        type  cml_data_types:CML_STRING_T {
                            length "0..255";
                        }
                        config false;
                    } // END of InterfaceIPV6Address definition.

                    leaf InterfaceIPV6LinkLocalAddress  {
                        type  cml_data_types:CML_STRING_T {
                            length "0..255";
                        }
                        config false;
                    } // END of InterfaceIPV6LinkLocalAddress definition.

                    leaf Ospfv3ProcessId  {
                        type  cml_data_types:CML_STRING_T {
                            length "0..255";
                        }
                        config false;
                    } // END of Ospfv3ProcessId definition.

                    leaf Ospfv3RouterId  {
                        type  cml_data_types:CML_STRING_T {
                            length "0..255";
                        }
                        config false;
                    } // END of Ospfv3RouterId definition.

                    leaf InterfaceState  {
                        type  cml_data_types:CML_OSPF_INTERFACE_STATE_MSG_T;  
                        config false;
                    } // END of InterfaceState definition.

                    leaf DesignatedRouter  {
                        type  cml_data_types:CML_STRING_T {
                            length "0..255";
                        }
                        config false;
                    } // END of DesignatedRouter definition.

                    leaf DRInterfaceAddr  {
                        type  cml_data_types:CML_STRING_T {
                            length "0..255";
                        }
                        config false;
                    } // END of DRInterfaceAddr definition.

                    leaf BackUpDesignatedRouter  {
                        type  cml_data_types:CML_STRING_T {
                            length "0..255";
                        }
                        config false;
                    } // END of BackUpDesignatedRouter definition.

                    leaf BackUpDRInterfaceAddr  {
                        type  cml_data_types:CML_STRING_T {
                            length "0..255";
                        }
                        config false;
                    } // END of BackUpDRInterfaceAddr definition.

                    leaf HelloDueIn  {
                        type  cml_data_types:CML_STRING_T {
                            length "0..255";
                        }
                        config false;
                    } // END of HelloDueIn definition.

                    leaf NeighborCount  {
                        type  cml_data_types:CML_UINT32_T;  
                        config false;
                    } // END of NeighborCount definition.

                    leaf AdjacentNeighborCount  {
                        type  cml_data_types:CML_UINT32_T;  
                        config false;
                    } // END of AdjacentNeighborCount definition.

                    leaf SuppressHelloCount  {
                        if-feature feature_list:HAVE_OSPF6_OD;
                        type  cml_data_types:CML_UINT32_T;  
                        config false;
                    } // END of SuppressHelloCount definition.

                    leaf HelloReceived  {
                        type  cml_data_types:CML_UINT32_T;  
                        config false;
                    } // END of HelloReceived definition.

                    leaf HelloSent  {
                        type  cml_data_types:CML_UINT32_T;  
                        config false;
                    } // END of HelloSent definition.

                    leaf DDReceived  {
                        type  cml_data_types:CML_UINT32_T;  
                        config false;
                    } // END of DDReceived definition.

                    leaf DDSent  {
                        type  cml_data_types:CML_UINT32_T;  
                        config false;
                    } // END of DDSent definition.

                    leaf LSReqReceived  {
                        type  cml_data_types:CML_UINT32_T;  
                        config false;
                    } // END of LSReqReceived definition.

                    leaf LSReqSent  {
                        type  cml_data_types:CML_UINT32_T;  
                        config false;
                    } // END of LSReqSent definition.

                    leaf LSUpdReceived  {
                        type  cml_data_types:CML_UINT32_T;  
                        config false;
                    } // END of LSUpdReceived definition.

                    leaf LSUpdSent  {
                        type  cml_data_types:CML_UINT32_T;  
                        config false;
                    } // END of LSUpdSent definition.

                    leaf LSAckReceived  {
                        type  cml_data_types:CML_UINT32_T;  
                        config false;
                    } // END of LSAckReceived definition.

                    leaf LSAckSent  {
                        type  cml_data_types:CML_UINT32_T;  
                        config false;
                    } // END of LSAckSent definition.

                    leaf LSAckDiscarded  {
                        type  cml_data_types:CML_UINT32_T;  
                        config false;
                    } // END of LSAckDiscarded definition.


                    list nbrStatic {
                         
                        description
                            "Static neighbor data structure.";

                        config true;
                        key "nbrStaticAddr";

                        
                        leaf nbrStaticAddr  {
                            type  cml_data_types:CML_IPV6_ADDR_T;  
                        } // END of nbrStaticAddr definition.

                        leaf nbrStaticPollInterval  {
                            type  cml_data_types:CML_UINT32_T {
                                 range "0..4294967295";
                            }
                        } // END of nbrStaticPollInterval definition.

                        leaf nbrStaticCost  {
                            type  cml_data_types:CML_UINT32_T {
                                 range "1..65535";
                            }
                        } // END of nbrStaticCost definition.

                        leaf nbrStaticPriority  {
                            type  cml_data_types:CML_UINT8_T {
                                 range "0..255";
                            }
                        } // END of nbrStaticPriority definition.

                        leaf nbrInterfaceState  {
                            type  cml_data_types:CML_STRING_T {
                                length "0..255";
                            }
                            config false;
                        } // END of nbrInterfaceState definition.

                        leaf nbrInterfaceDesc  {
                            type  cml_data_types:CML_STRING_T {
                                length "0..255";
                            }
                            config false;
                        } // END of nbrInterfaceDesc definition.

                    } // End of nbrStatic-list

                    list ospf6_neighbor {
                         
                        description
                            "Neighbor Data Structure";

                        config false;
                        key "nbrRouterId";

                        
                        leaf nbrRouterId  {
                            type  cml_data_types:CML_STRING_T {
                                length "0..255";
                            }
                        } // END of nbrRouterId definition.

                        leaf nbrInterfaceAddress  {
                            type  cml_data_types:CML_STRING_T {
                                length "0..255";
                            }
                        } // END of nbrInterfaceAddress definition.

                        leaf nbrAreaId  {
                            type  cml_data_types:CML_STRING_T {
                                length "0..255";
                            }
                        } // END of nbrAreaId definition.

                        leaf nbrTimerDump  {
                            type  cml_data_types:CML_STRING_T {
                                length "0..255";
                            }
                        } // END of nbrTimerDump definition.

                        leaf nbrState  {
                            type  cml_data_types:CML_STRING_T {
                                length "0..255";
                            }
                        } // END of nbrState definition.

                        leaf nbrStateMessage  {
                            type  cml_data_types:CML_STRING_T {
                                length "0..255";
                            }
                        } // END of nbrStateMessage definition.

                        leaf nbrStateChange  {
                            type  cml_data_types:CML_UINT32_T;  
                        } // END of nbrStateChange definition.

                        leaf nbrPriority  {
                            type  cml_data_types:CML_UINT8_T;  
                        } // END of nbrPriority definition.

                        leaf nbrisHelloSuppressed  {
                            type  cml_data_types:CML_BOOL_T;  
                        } // END of nbrisHelloSuppressed definition.

                        leaf nbrDRouter  {
                            type  cml_data_types:CML_STRING_T {
                                length "0..255";
                            }
                        } // END of nbrDRouter definition.

                        leaf nbrBDRouter  {
                            type  cml_data_types:CML_STRING_T {
                                length "0..255";
                            }
                        } // END of nbrBDRouter definition.

                        leaf nbrOptions  {
                            type  cml_data_types:CML_STRING_T {
                                length "0..255";
                            }
                        } // END of nbrOptions definition.

                        leaf nbrDeadTimer  {
                            type  cml_data_types:CML_STRING_T {
                                length "0..255";
                            }
                        } // END of nbrDeadTimer definition.

                        leaf nbrDbSummaryCount  {
                            type  cml_data_types:CML_UINT32_T;  
                        } // END of nbrDbSummaryCount definition.

                        leaf nbrLsRequestCount  {
                            type  cml_data_types:CML_UINT32_T;  
                        } // END of nbrLsRequestCount definition.

                        leaf nbrLsRetransmissionCount  {
                            type  cml_data_types:CML_UINT32_T;  
                        } // END of nbrLsRetransmissionCount definition.

                        leaf nbrBfdEnabled  {
                            type  cml_data_types:CML_BOOL_T;  
                        } // END of nbrBfdEnabled definition.

                        container asbr {
                                                        config false;

                            description
                                "ASBR routing table.";

                            uses Route;
                        } // END of asbr-container definition.
                        uses Route;
                    } // End of ospf6_neighbor-list
                    uses lsdb;
                } // End of ospf6IfinstanceId-list
            } // End of ospf6Interface-list
            container ospf6Helper {
                                config true;

                description
                    "OSPFv3 Restart module properties";

                uses helper;
            } // END of ospf6Helper-container definition.
            container ospf6HitlessRestartHelper {
                                config true;

                description
                    "OSPFv3 Restart module properties";

                uses helper;
            } // END of ospf6HitlessRestartHelper-container definition.
            container ospf6Debug {
                                config true;

                description
                    "OSPFv3 Debug Configurations";

                leaf debugIfsm  {
                    type  cml_data_types:CML_OSPF6_DEBUG_IFSM_T;  
                    default "status";
                } // END of debugIfsm definition.

                leaf debugNfsm  {
                    type  cml_data_types:CML_OSPF6_DEBUG_IFSM_T;  
                    default "status";
                } // END of debugNfsm definition.

                leaf debugLsa  {
                    type  cml_data_types:CML_OSPF6_DEBUG_LSA_T;  
                    default "generate";
                } // END of debugLsa definition.

                leaf debugNsm  {
                    type  cml_data_types:CML_OSPF6_DEBUG_RIB_T;  
                    default "interface";
                } // END of debugNsm definition.

                leaf debugRib  {
                    if-feature feature_list:HAVE_RIBD;
                    type  cml_data_types:CML_OSPF6_DEBUG_RIB_T;  
                    default "interface";
                } // END of debugRib definition.

                leaf debugRoute  {
                    type  cml_data_types:CML_OSPF6_DEBUG_ROUTE_T;  
                    default "spf";
                } // END of debugRoute definition.

                leaf debugRetransmission  {
                    type  cml_data_types:CML_BOOL_T;  
                    default false;
                } // END of debugRetransmission definition.

                leaf debugBfd  {
                    if-feature feature_list:HAVE_BFD;
                    type  cml_data_types:CML_BOOL_T;  
                } // END of debugBfd definition.

                leaf debugAll  {
                    type  cml_data_types:CML_BOOL_T;  
                } // END of debugAll definition.

                leaf debugEvent  {
                    type  cml_data_types:CML_OSPF6_DEBUG_EVENT_T;  
                    default "abr";
                } // END of debugEvent definition.

                leaf debugPacket  {
                    type  cml_data_types:CML_OSPF6_DEBUG_PACKET_TYPE_T;  
                } // END of debugPacket definition.

                leaf debugLfa  {
                    if-feature feature_list:HAVE_OSPF6_LFA;
                    type  cml_data_types:CML_BOOL_T;  
                    default false;
                } // END of debugLfa definition.

            } // END of ospf6Debug-container definition.
        } // End of ospf6_master-list
    } // END of ospf6_master-grouping definition.
    grouping lsdb {
                leaf lsdbIfName  {
            type  cml_data_types:CML_STRING_T {
                length "0..255";
            }
            config false;
        } // END of lsdbIfName definition.

        leaf lsdbAreaId  {
            type  cml_data_types:CML_STRING_T {
                length "0..255";
            }
            config false;
        } // END of lsdbAreaId definition.


        list lsdbSlot {
             
            description
                "LSDB of AS-external-LSAs.";

            config false;
            key "lsdbSlotType";

            
            leaf lsdbSlotType  {
                type  cml_data_types:CML_UINT32_T;  
            } // END of lsdbSlotType definition.


            list lsa {
                 
                description
                    "OSPFv3 Link State Advertisement (LSA) list";

                config false;
                key "lsaLinkId";

                
                leaf lsaLinkId  {
                    type  cml_data_types:CML_STRING_T {
                        length "0..255";
                    }
                } // END of lsaLinkId definition.

                leaf lsaAge  {
                    type  cml_data_types:CML_UINT32_T;  
                } // END of lsaAge definition.

                leaf lsaType  {
                    type  cml_data_types:CML_UINT32_T;  
                } // END of lsaType definition.

                leaf lsaLength  {
                    type  cml_data_types:CML_UINT32_T;  
                } // END of lsaLength definition.

                leaf lsaAdvRouter  {
                    type  cml_data_types:CML_STRING_T {
                        length "0..255";
                    }
                } // END of lsaAdvRouter definition.

                leaf lsaSeqNum  {
                    type  cml_data_types:CML_STRING_T {
                        length "0..255";
                    }
                } // END of lsaSeqNum definition.

                leaf lsaCheckSum  {
                    type  cml_data_types:CML_STRING_T {
                        length "0..255";
                    }
                } // END of lsaCheckSum definition.

                leaf isLsaInterRouter  {
                    type  cml_data_types:CML_BOOL_T;  
                } // END of isLsaInterRouter definition.

                leaf lsaRouterLinkCount  {
                    type  cml_data_types:CML_UINT32_T;  
                } // END of lsaRouterLinkCount definition.

                leaf lsaRefTypeStr  {
                    type  cml_data_types:CML_STRING_T {
                        length "0..255";
                    }
                } // END of lsaRefTypeStr definition.

            } // End of lsa-list
        } // End of lsdbSlot-list
    } // END of lsdb definition.
    grouping Route {
        
        list ospf6Route {
             
            description
                "OSPFv3 Route";

            config false;
            key "routeIPV6Prefix";

            
            leaf routeIPV6Prefix  {
                type  cml_data_types:CML_STRING_T {
                    length "0..255";
                }
            } // END of routeIPV6Prefix definition.

            leaf routeDistance  {
                type  cml_data_types:CML_UINT8_T;  
            } // END of routeDistance definition.

            container ospf6Path {
                                config false;

                description
                    "OSPFv3 path details for different routes";

                leaf pathType  {
                    type  cml_data_types:CML_OSPF6_PATH_TYPE_T;  
                } // END of pathType definition.

                leaf pathCode  {
                    type  cml_data_types:CML_STRING_T {
                        length "0..255";
                    }
                } // END of pathCode definition.

                leaf pathDiscardConnection  {
                    type  cml_data_types:CML_STRING_T {
                        length "0..255";
                    }
                } // END of pathDiscardConnection definition.

                leaf pathCost  {
                    type  cml_data_types:CML_UINT32_T;  
                } // END of pathCost definition.

                leaf pathType2Cost  {
                    type  cml_data_types:CML_UINT32_T;  
                } // END of pathType2Cost definition.

                leaf pathFlags  {
                    type  cml_data_types:CML_OSPF6_PATH_FLAGS_T;  
                } // END of pathFlags definition.

            } // END of ospf6Path-container definition.
            uses ospf6NextHop;
        } // End of ospf6Route-list
    } // END of Route definition.
    grouping ospf6NextHop {
        
        list nextHop {
             
            description
                "OSPFv3 next hop details";

            config false;
            key "nextHopAddr";

            
            leaf nextHopAddr  {
                type  cml_data_types:CML_STRING_T {
                    length "0..255";
                }
            } // END of nextHopAddr definition.

            leaf nextHopInterfaceName  {
                type  cml_data_types:CML_STRING_T {
                    length "0..255";
                }
            } // END of nextHopInterfaceName definition.

            leaf nextHopTransitAreaId  {
                type  cml_data_types:CML_STRING_T {
                    length "0..255";
                }
            } // END of nextHopTransitAreaId definition.

            leaf nextHopAreaId  {
                type  cml_data_types:CML_STRING_T {
                    length "0..255";
                }
            } // END of nextHopAreaId definition.

            leaf isNextHopConnected  {
                type  cml_data_types:CML_BOOL_T;  
            } // END of isNextHopConnected definition.

            leaf nextHopIsAreaTransit  {
                type  cml_data_types:CML_BOOL_T;  
            } // END of nextHopIsAreaTransit definition.

            leaf IsnextHopInvalid  {
                type  cml_data_types:CML_BOOL_T;  
            } // END of IsnextHopInvalid definition.

            leaf nextHopCode  {
                type  cml_data_types:CML_STRING_T {
                    length "0..255";
                }
            } // END of nextHopCode definition.

        } // End of nextHop-list
    } // END of ospf6NextHop definition.
    grouping helper {
                leaf restartHelperOnlyReload  {
            if-feature feature_list:HAVE_RESTART;
            type  cml_data_types:CML_BOOL_T;  
        } // END of restartHelperOnlyReload definition.

        leaf restartHelperOnlyGracePeriod  {
            if-feature feature_list:HAVE_RESTART;
            type  cml_data_types:CML_UINT16_T {
                 range "1..1800";
            }
        } // END of restartHelperOnlyGracePeriod definition.

        leaf restartHelperOnlyUpgrade  {
            if-feature feature_list:HAVE_RESTART;
            type  cml_data_types:CML_BOOL_T;  
        } // END of restartHelperOnlyUpgrade definition.

        leaf-list restartHelperRouterId  {
            if-feature feature_list:HAVE_RESTART;
            type  cml_data_types:CML_STRING_T {
                length "0..255";
            }
        } // END of restartHelperRouterId definition.

    } // END of helper definition.
    grouping default-information-originate {
        
        list default-information {
             
            description
                "Default external route Information";

            config true;
            key "defaultInformationOriginate";

            
            leaf defaultInformationOriginate  {
                type  cml_data_types:CML_BOOL_T;  
            } // END of defaultInformationOriginate definition.

            container default-information-always {
                                config true;

                description
                    "Default external route Information Always";

                leaf alwaysSet  {
                    type  cml_data_types:CML_BOOL_T;  
                } // END of alwaysSet definition.

                uses metric-group;
            } // END of default-information-always-container definition.
        } // End of default-information-list
    } // END of default-information-originate definition.
    grouping redistribute {
        
        list ospf6_redist_conf {
             
            description
                "Redistribute IPv4 routes ";

            config true;
            key "ospf6RedistProtocol";

            
            leaf ospf6RedistProtocol  {
                type  cml_data_types:CML_OSPF6_ROUTE_SOURCE_TYPE_T;  
            } // END of ospf6RedistProtocol definition.

            container redistribute-tag {
                                config true;

                description
                    "Redistribute IPv4 routes tag options";

                leaf ospf6RedistTagVal  {
                    type  cml_data_types:CML_UINT32_T {
                         range "0..4294967295";
                    }
                    default "0";
                } // END of ospf6RedistTagVal definition.

                uses metric-group;
            } // END of redistribute-tag-container definition.
        } // End of ospf6_redist_conf-list

        list ospf6_redist_ospf {
             
            description
                "Redistribute IPv4 routes for OSPF option";

            config true;
            key "ospf6RedistOspfProtocol";

            
            leaf ospf6RedistOspfProtocol  {
                type  cml_data_types:CML_OSPF_AREA_ID_T;  
            } // END of ospf6RedistOspfProtocol definition.

            container redistribute-tag {
                                config true;

                description
                    "Redistribute IPv4 routes for OSPF tag option";

                leaf ospf6RedistOspfTagVal  {
                    type  cml_data_types:CML_UINT32_T {
                         range "0..4294967295";
                    }
                    default "0";
                } // END of ospf6RedistOspfTagVal definition.

                uses metric-group;
            } // END of redistribute-tag-container definition.
        } // End of ospf6_redist_ospf-list
    } // END of redistribute definition.
    grouping metric-group {
                leaf metric  {
            type  cml_data_types:CML_UINT32_T {
                 range "0..16777214";
            }
        } // END of metric definition.

        leaf metricType  {
            type  cml_data_types:CML_OSPF_METRIC_TYPE_T;  
        } // END of metricType definition.

        leaf routeMap  {
            type  cml_data_types:CML_STRING_T {
                length "0..255";
            }
        } // END of routeMap definition.

    } // END of metric-group definition.


}
