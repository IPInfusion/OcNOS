/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : syslog.yang
*
*/

submodule syslog {

    belongs-to  ZebOS { prefix ZebOS; }
    include vrf;


    import cml_data_types {
        prefix cml_data_types;
    }

    import feature_list {
        prefix feature_list;
    }

    description
        "hostp syslog configurations";


    revision "2017-01-12" {
        description "Changed vrf name as normal attr as it is optional parameter.";
    }

    revision "2016-10-28" {
        description "Initial version of SYSLOG datamodel.";
    }


    grouping  hostpsyslog-grouping {
    container hostpsyslog {
                config true;

        description
            "syslog related operations";

        leaf defaultVrfSourceInterface  {
            type  cml_data_types:CML_STRING_T {
                length "0..255";
            }
        } // END of defaultVrfSourceInterface definition.

        leaf mgmtVrfSrcInterface  {
            type  cml_data_types:CML_STRING_T {
                length "0..255";
            }
        } // END of mgmtVrfSrcInterface definition.

        leaf debuglogging  {
            if-feature feature_list:HAVE_DEBUG_MODULE_SEVERITY;
            type  cml_data_types:CML_LEVEL_T;  
            default "debuglogging";
            description "debug logging";
        } // END of debuglogging definition.

        leaf debug  {
            type  cml_data_types:CML_BOOL_T;  
            description "debug logging";
        } // END of debug definition.


        list syslogServer {
             
            description
                "list of servers";

            config true;
            key "ServerAddr";

            
            leaf vrfName  {
                type  cml_data_types:CML_STRING_T {
                    length "0..255";
                }
                default "default";
            } // END of vrfName definition.

            leaf ServerAddr  {
                type  cml_data_types:CML_HOSTPNAME_T;  
                description "logging server";
            } // END of ServerAddr definition.

            leaf ServerSeverity  {
                type  cml_data_types:CML_INT8_T {
                     range "0..7";
                }
                default "7";
            } // END of ServerSeverity definition.

            leaf ServerFacility  {
                type  cml_data_types:CML_FACILITY_T;  
                default "local7";
            } // END of ServerFacility definition.

        } // End of syslogServer-list
    } // END of hostpsyslog-container definition.
    } // END of hostpsyslog-container definition.


}
