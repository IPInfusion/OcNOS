/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgp-types.yang
*
*/

module ipi-bgp-types {

    yang-version 1.1;

    namespace   "http://www.ipinfusion.com/yang/ocnos/ipi-bgp-types";

    prefix "ipi-bgp-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-bgp-types";


    revision "2022-09-08" {
        description "Updated the yang file for Large community feature";
        reference " 0.9.1.";
    }

    revision "2022-06-01" {
        description "Updated the yang file with feature";
        reference " 0.9.0.";
    }

    revision "2022-04-28" {
        description "Updated BGP clear RPCs to remove unwanted attributes";
        reference " 0.8.1.";
    }

    revision "2022-04-04" {
        description "Defined New Datatype for BGP AIGP";
        reference " 0.8.0.";
    }

    revision "2022-01-17" {
        description "Defined New Datatype";
        reference " 0.7.1.";
    }

    revision "2022-01-07" {
        description "Defined New Datatype";
        reference " 0.7.0.";
    }

    revision "2021-09-03" {
        description "Update descriptions of attribute";
        reference " 0.6.1.";
    }

    revision "2021-08-16" {
        description "Updated the datatype from enum to bits for the additional-paths-mode attribute";
        reference " 0.6.0.";
    }

    revision "2021-05-27" {
        description "Corrected typo error in BGP_PEERFLAG_SHUTDOWN_T enum datatype";
        reference " 0.5.1.";
    }

    revision "2021-05-05" {
        description "Change related to BGP Unnumbered";
        reference " 0.5.0.";
    }

    revision "2021-04-09" {
        description "Change related to Peer group remodelling";
        reference " 0.4.0.";
    }

    revision "2021-03-05" {
        description "Community-list related changes";
        reference " 0.3.0.";
    }

    revision "2020-12-15" {
        description "Change to have data-types in lower case instead of camel case";
        reference " 0.2.0.";
    }

    revision "2020-09-10" {
        description "Initial Version";
        reference " 0.1.0.";
    }



    typedef  bgp_aigp_metric_cost_community_poi_t {
        type enumeration {
            enum pre-bestpath {
                value 128;
                description "insert before pre-bestpath criteria";
            }
            enum igp-cost {
                value 129;
                description "insert before igp-cost criteria";
            }
        }
        description "type definition for BGP_AIGP_METRIC_COST_COMMUNITY_POI_T";
    }

    typedef  cml_ospf_string_t {
        type string {
            pattern "[^?' =,>|]*";
        }
        description "type definition for CML_OSPF_STRING_T";
    }

    typedef  cml_ospf_area_id_t {
        type union {
            type cml_ospf_string_t {

            }
            type uint16 {
                range "1..65535";

            }
        }
        description "type definition for CML_OSPF_AREA_ID_T";
    }

    typedef  bgp_hostname_t {
        type union {
            type bgp_ip_addr_t {

            }
            type string {

            }
        }
        description "type definition for BGP_HOSTNAME_T";
    }

    typedef  bgp_md5_password_t {
        type string {
            pattern "[^? ]*";
        }
        description "type definition for BGP_MD5_PASSWORD_T";
    }

    typedef  bgp_dampening_t {
        type enumeration {
            enum enable-dampening {
                value 1;
                description "enable-dampening";
            }
        }
        description "type definition for BGP_DAMPENING_T";
    }

    typedef  bgp_afi_type_t {
        type enumeration {
            enum ipv4 {
                value 1;
                description "Address family";
            }
            enum ipv6 {
                value 2;
                description "Address family";
            }
            enum vpnv4 {
                value 3;
                description "Address family";
            }
            enum vpnv6 {
                value 4;
                description "Address family";
            }
            enum rtfilter {
                value 5;
                description "Address family";
            }
            enum l2vpn {
                value 25;
                description "Address family";
            }
            enum link-state {
                value 16388;
                description "Address family";
            }
        }
        description "type definition for BGP_AFI_TYPE_T";
    }

    typedef  bgp_vrf_afi_type_t {
        type enumeration {
            enum ipv4 {
                value 1;
                description "Address family";
            }
            enum ipv6 {
                value 2;
                description "Address family";
            }
        }
        description "type definition for BGP_VRF_AFI_TYPE_T";
    }

    typedef  bgp_vrf_safi_type_t {
        type enumeration {
            enum unicast {
                value 1;
                description "Address family modifier";
            }
        }
        description "type definition for BGP_VRF_SAFI_TYPE_T";
    }

    typedef  bgp_safi_type_t {
        type enumeration {
            enum unicast {
                value 1;
                description "Address family modifier";
            }
            enum multicast {
                value 2;
                description "Address family modifier";
            }
            enum labeled-unicast {
                value 4;
                description "Address family modifier";
            }
            enum l2vpn-vpls {
                value 65;
                description "Address family modifier";
            }
            enum evpn {
                value 70;
                description "Address family modifier";
            }
            enum link-state {
                value 71;
                description "Address family modifier";
            }
            enum vpn-unicast {
                value 128;
                description "Address family modifier";
            }
            enum rtfilter-unicast {
                value 132;
                description "Address family modifier";
            }
        }
        description "type definition for BGP_SAFI_TYPE_T";
    }

    typedef  bgp_ip_network_t {
        type union {
            type inet:ipv4-address {

            }
            type inet:ipv4-prefix {

            }
            type inet:ipv6-prefix {

            }
        }
        description "type definition for BGP_IP_NETWORK_T";
    }

    typedef  bgp_route_target_t {
        type enumeration {
            enum rt {
                value 0;
                description "Specify route target";
            }
            enum soo {
                value 1;
                description "specify site of origin";
            }
        }
        description "type definition for BGP_ROUTE_TARGET_T";
    }

    typedef  bgp_config_t {
        type enumeration {
            enum standard {
                value 0;
                description "standard";
            }
            enum zebos {
                value 1;
                description "ZebOS";
            }
        }
        description "type definition for BGP_CONFIG_T";
    }

    typedef  bgp_af_config_t {
        type enumeration {
            enum all-afs {
                value 0;
                description "configure for all vpn address-families";
            }
            enum vpnv4 {
                value 1;
                description "Virtual Private Network version 4(VPNv4)";
            }
            enum vpnv6 {
                value 2;
                description "Virtual Private Network version 6(VPNv6)";
            }
        }
        description "type definition for BGP_AF_CONFIG_T";
    }

    typedef  bgp_all_vrf_t {
        type enumeration {
            enum all-vrfs {
                value 0;
                description "all-vrfs";
            }
        }
        description "type definition for BGP_ALL_VRF_T";
    }

    typedef  bgp_vrf_name_t {
        type string;
        description "type definition for BGP_VRF_NAME_T";
    }

    typedef  bgp_vrf_type_t {
        type union {
            type bgp_vrf_name_t {

            }
            type bgp_all_vrf_t {

            }
        }
        description "type definition for BGP_VRF_TYPE_T";
    }

    typedef  bgp_l3vpn_label_alloc_mode_t {
        type enumeration {
            enum per-prefix {
                value 0;
                description "configure mode to be per-prefix";
            }
            enum per-vrf {
                value 1;
                description "configure mode to be per-vrf";
            }
        }
        description "type definition for BGP_L3VPN_LABEL_ALLOC_MODE_T";
    }

    typedef  bgp_med_type_t {
        type bits {
            bit confed {
                position 0;
                description "Compare MED among confederation paths";
            }
            bit missing-as-worst {
                position 1;
                description "Treat missing MED as the least preferred one";
            }
            bit remove-recv-med {
                position 2;
                description "To remove rcvd MED attribute";
            }
            bit remove-send-med {
                position 3;
                description "To remove send MED attribute";
            }
        }
        description "type definition for BGP_MED_TYPE_T";
    }

    typedef  bgp_orf_prefix_type_t {
        type bits {
            bit receive {
                position 1;
                description "Capability to RECEIVE the ORF from this neighbor";
            }
            bit send {
                position 2;
                description "Capability to SEND the ORF to this neighbor";
            }
        }
        description "type definition for BGP_ORF_PREFIX_TYPE_T";
    }

    typedef  bgp_community_list_action_t {
        type enumeration {
            enum deny {
                value 1;
                description "Specify community to reject";
            }
            enum permit {
                value 2;
                description "Specify community to accept";
            }
        }
        description "type definition for BGP_COMMUNITY_LIST_ACTION_T";
    }

    typedef  bgp_community_list_type_t {
        type enumeration {
            enum standard {
                value 1;
                description "Specify standard community list";
            }
        }
        description "type definition for BGP_COMMUNITY_LIST_TYPE_T";
    }

    typedef  bgp_expanded_list_t {
        type enumeration {
            enum expanded {
                value 1;
                description "Specify expanded community list";
            }
        }
        description "type definition for BGP_EXPANDED_LIST_T";
    }

    typedef  bgp_expanded_list_type_t {
        type union {
            type uint32 {
                range "100..500";

            }
            type string {

            }
        }
        description "type definition for BGP_EXPANDED_LIST_TYPE_T";
    }

    typedef  bgp_additional_path_type_t {
        type bits {
            bit receive {
                position 1;
                description "Receive additional paths from neighbors";
            }
            bit send {
                position 2;
                description "Send additional paths to neighbors";
            }
        }
        description "type definition for BGP_ADDITIONAL_PATH_TYPE_T";
    }

    typedef  bgp_peer_additional_path_type_t {
        type bits {
            bit receive {
                position 1;
                description "Receive additional paths from neighbors";
            }
            bit send {
                position 2;
                description "Send additional paths to neighbors";
            }
            bit disable {
                position 4;
                description "disable additional-paths";
            }
        }
        description "type definition for BGP_PEER_ADDITIONAL_PATH_TYPE_T";
    }

    typedef  bgp_adv_rcv_type_t {
        type enumeration {
            enum advertise {
                value 1;
                description "advertised";
            }
            enum receive {
                value 2;
                description "received";
            }
            enum advertise-receive {
                value 3;
                description "advertised and received both";
            }
        }
        description "type definition for BGP_ADV_RCV_TYPE_T";
    }

    typedef  bgp_send_commu_type_t {
        type bits {
            bit standard {
                position 1;
                description "Send Standard Community attributes";
            }
            bit extended {
                position 2;
                description "Send Extended Community attributes";
            }
            bit large {
                position 3;
                description "Send Large Community attributes";
            }
        }
        description "type definition for BGP_SEND_COMMU_TYPE_T";
    }

    typedef  bgp_update_debug_type_t {
        type bits {
            bit in {
                position 8;
                description "Inbound updates";
            }
            bit out {
                position 9;
                description "Outbound updates";
            }
        }
        description "type definition for BGP_UPDATE_DEBUG_TYPE_T";
    }

    typedef  bgp_attribute_unchanged_type_t {
        type bits {
            bit as-path {
                position 1;
                description "As-path attribute";
            }
            bit next-hop {
                position 2;
                description "Next-hop attribute";
            }
            bit med {
                position 3;
                description "Med attribute";
            }
        }
        description "type definition for BGP_ATTRIBUTE_UNCHANGED_TYPE_T";
    }

    typedef  bgp_debug_type_t {
        type bits {
            bit nht {
                position 1;
                description "NHT message";
            }
            bit nsm {
                position 2;
                description "NSM message";
            }
            bit fsm {
                position 3;
                description "Finite state machine";
            }
            bit events {
                position 4;
                description "BGP events";
            }
            bit filters {
                position 5;
                description "BGP filter";
            }
            bit keepalives {
                position 6;
                description "BGP keepalives";
            }
            bit updates {
                position 7;
                description "BGP updates";
            }
            bit dampening {
                position 10;
                description "BGP Dampening";
            }
            bit bfd {
                position 11;
                description "Bidirectional Forwarding Detection (BFD)";
            }
            bit mpls {
                position 12;
                description "BGP mpls";
            }
            bit vpls {
                position 13;
                description "BGP vpls";
            }
            bit link-state {
                position 14;
                description "BGP Link State";
            }
        }
        description "type definition for BGP_DEBUG_TYPE_T";
    }

    typedef  bgp_distribute_list_direction_t {
        type enumeration {
            enum in {
                value 0;
                description "Filter incoming updates";
            }
            enum out {
                value 1;
                description "Filter outgoing updates";
            }
        }
        description "type definition for BGP_DISTRIBUTE_LIST_DIRECTION_T";
    }

    typedef  bgp_redistribute_type_t {
        type enumeration {
            enum kernel {
                value 1;
                description "Kernel routes";
            }
            enum connected {
                value 2;
                description "Connected";
            }
            enum static {
                value 3;
                description "Static routes";
            }
            enum rip {
                value 4;
                description "Routing Information Protocol(RIP)";
            }
            enum ospf {
                value 5;
                description "Kernel routes";
            }
            enum isis {
                value 6;
                description "ISO IS-IS";
            }
        }
        description "type definition for BGP_REDISTRIBUTE_TYPE_T";
    }

    typedef  bgp_peer_status_t {
        type enumeration {
            enum idle {
                value 1;
                description "Idle";
            }
            enum connect {
                value 2;
                description "Connect";
            }
            enum active {
                value 3;
                description "Active";
            }
            enum opensent {
                value 4;
                description "Opensent";
            }
            enum openconfirm {
                value 5;
                description "Openconfirm";
            }
            enum established {
                value 6;
                description "Established";
            }
        }
        description "type definition for BGP_PEER_STATUS_T";
    }

    typedef  bgp_peerflag_shutdown_t {
        type enumeration {
            enum idle {
                value 1;
                description "Idle";
            }
            enum connect {
                value 2;
                description "Connect";
            }
            enum active {
                value 3;
                description "Active";
            }
            enum opensent {
                value 4;
                description "Opensent";
            }
            enum openconfirm {
                value 5;
                description "Openconfirm";
            }
            enum established {
                value 6;
                description "Established";
            }
            enum idle-admin {
                value 7;
                description "Idle Admin";
            }
            enum idle-pfxct {
                value 8;
                description "Idle PfxCt";
            }
            enum idle-g-shut {
                value 9;
                description "Idle G-shut";
            }
        }
        description "type definition for BGP_PEERFLAG_SHUTDOWN_T";
    }

    typedef  bgp_prefix_entry_type_t {
        type enumeration {
            enum no_match {
                value 1;
                description "No match";
            }
            enum deny {
                value 2;
                description "Deny";
            }
            enum permit {
                value 3;
                description "Permit";
            }
        }
        description "type definition for BGP_PREFIX_ENTRY_TYPE_T";
    }

    typedef  bgp_ri_type_t {
        type enumeration {
            enum internal {
                value 1;
                description "internal";
            }
            enum confed-external {
                value 2;
                description "confed-external";
            }
            enum external {
                value 3;
                description "external";
            }
            enum aggregated-and-local {
                value 4;
                description "aggregated and local";
            }
            enum sourced {
                value 5;
                description "sourced";
            }
            enum sourced-and-local {
                value 6;
                description "sourced and local";
            }
        }
        description "type definition for BGP_RI_TYPE_T";
    }

    typedef  bgp_origin_t {
        type enumeration {
            enum igp {
                value 0;
                description "IGP";
            }
            enum egp {
                value 1;
                description "EGP";
            }
            enum incomplete {
                value 2;
                description "incomplete";
            }
        }
        description "type definition for BGP_ORIGIN_T";
    }

    typedef  bgp_link_type_t {
        type enumeration {
            enum internal {
                value 0;
                description "internal";
            }
            enum external {
                value 1;
                description "external";
            }
        }
        description "type definition for BGP_LINK_TYPE_T";
    }

    typedef  bgp_connection_type_t {
        type enumeration {
            enum shared {
                value 0;
                description "shared network";
            }
            enum non_shared {
                value 1;
                description "non shared network";
            }
        }
        description "type definition for BGP_CONNECTION_TYPE_T";
    }

    typedef  bgp_cluster_id_t {
        type union {
            type inet:ipv4-address {

            }
            type uint32 {
                range "1..4294967295";

            }
        }
        description "type definition for BGP_CLUSTER_ID_T";
    }

    typedef  bgp_md5_t {
        type enumeration {
            enum 0 {
                value 1;
                description "Unencrypted password (key)";
            }
            enum 1 {
                value 2;
                description "Encrypted password (key)";
            }
        }
        description "type definition for BGP_MD5_T";
    }

    typedef  bgp_target_route_type_t {
        type bits {
            bit import {
                position 0;
                description "import";
            }
            bit export {
                position 1;
                description "export";
            }
        }
        description "type definition for BGP_TARGET_ROUTE_TYPE_T";
    }

    typedef  bgp_aggregate_type_t {
        type enumeration {
            enum as-set {
                value 1;
                description "shared network";
            }
            enum summary-only {
                value 2;
                description "non shared network";
            }
            enum as-set-and-summary-only {
                value 3;
                description "non shared network";
            }
        }
        description "type definition for BGP_AGGREGATE_TYPE_T";
    }

    typedef  bgp_capability_type_t {
        type enumeration {
            enum advertised {
                value 1;
                description "Advertised Capability";
            }
            enum received {
                value 2;
                description "Received Capability";
            }
            enum advertised-and-received {
                value 3;
                description "Advertised and Received Capability";
            }
        }
        description "type definition for BGP_CAPABILITY_TYPE_T";
    }

    typedef  bgp_version_t {
        type enumeration {
            enum 4 {
                value 1;
                description "BGP Version 4";
            }
        }
        description "type definition for BGP_VERSION_T";
    }

    typedef  bgp_route_refresh_cap_type_t {
        type enumeration {
            enum advertised {
                value 1;
                description "advertised";
            }
            enum received-old {
                value 2;
                description "received old";
            }
            enum received-new {
                value 3;
                description "received new";
            }
            enum received-old-and-new {
                value 4;
                description "received old and new";
            }
            enum advertised-and-received-old {
                value 5;
                description "advertised and received old";
            }
            enum advertised-and-received-new {
                value 6;
                description "advertised and received new";
            }
            enum advertised-and-received-old-and-new {
                value 7;
                description "advertised and received old and new";
            }
        }
        description "type definition for BGP_ROUTE_REFRESH_CAP_TYPE_T";
    }

    typedef  bgp_vrf_rt_t {
        type string {
            pattern ".*:.*";
        }
        description "type definition for BGP_VRF_RT_T";
    }

    typedef  bgp_evpn_auto_rt_t {
        type enumeration {
            enum evpn-auto-rt {
                value 1;
                description "EVPN Auto RT";
            }
        }
        description "type definition for BGP_EVPN_AUTO_RT_T";
    }

    typedef  bgp_route_target_type_t {
        type union {
            type bgp_vrf_rt_t {

            }
            type bgp_evpn_auto_rt_t {

            }
        }
        description "type definition for BGP_ROUTE_TARGET_TYPE_T";
    }

    typedef  bgp_peer_group_static_t {
        type enumeration {
            enum static {
                value 0;
                description "static";
            }
        }
        description "type definition for BGP_PEER_GROUP_STATIC_T";
    }

    typedef  bgp_peer_group_range_t {
        type string;
        description "type definition for BGP_PEER_GROUP_RANGE_T";
    }

    typedef  bgp_peer_group_type_t {
        type union {
            type bgp_peer_group_range_t {

            }
            type bgp_peer_group_static_t {

            }
        }
        description "type definition for BGP_PEER_GROUP_TYPE_T";
    }

    typedef  bgp_as_t {
        type enumeration {
            enum internal {
                value -2;
                description "internal for iBGP peer";
            }
            enum external {
                value -1;
                description "external for eBGP peer";
            }
        }
        description "type definition for BGP_AS_T";
    }

    typedef  bgp_as_type_t {
        type union {
            type bgp_as_t {

            }
            type int64 {
                range "1..4294967295";

            }
        }
        description "type definition for BGP_AS_TYPE_T";
    }

    typedef  bgp_ip_addr_t {
        type union {
            type inet:ipv4-address {

            }
            type inet:ipv6-address {

            }
            type string {

            }
        }
        description "type definition for BGP_IP_ADDR_T";
    }

    typedef  bgp_sid_alloc_type_t {
        type enumeration {
            enum per-vrf {
                value 1;
                description "per-vrf";
            }
        }
        description "type definition for BGP_SID_ALLOC_TYPE_T";
    }

}
