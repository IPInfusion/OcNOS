/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgp-peer-group.yang
*
*/

submodule ipi-bgp-peer-group {

    yang-version 1.1;

    belongs-to  ipi-bgp { prefix ipi-bgp; }

    import feature-list {
        prefix feature-list;
        revision-date 2023-02-21;
    }

    import cml-data-types {
        prefix cml-data-types;
        revision-date 2022-09-30;
    }

    import ipi-bgp-types {
        prefix ipi-bgp-types;
        revision-date 2022-09-08;
    }

    include ipi-bgp-common { revision-date 2022-07-06;}
    include ipi-bgp-address-family { revision-date 2022-07-16;}
    organization
        "IP Infusion Inc.";

    contact
        "Address: 3965 Freedom Circle, Suite 200, Santa Clara, CA 95054
         Phone: +1 408-400-1900
         E-mail: support@ipinfusion.com
         Web: http://www.ipinfusion.com/";

    description
        "";


    revision "2022-07-06" {
        description "Skipped dependency validation for a composite constraint of peer-as and peer-group-tag for BGP peer";
        reference " 0.7.2.";
    }

    revision "2022-06-20" {
        description "Added new attribute 'de-activate' for BGP Peer-group feature.";
        reference " 0.7.1.";
    }

    revision "2022-06-01" {
        description "Updated the yang file with feature";
        reference " 0.7.0.";
    }

    revision "2022-04-19" {
        description "Added new attribute 'peer-shutdown-description' for support of BGP Administrative Shutdown Communication feature.";
        reference " 0.5.1.";
    }

    revision "2022-03-10" {
        description "New attribute add for RFC 9072";
        reference " 0.6.0.";
    }

    revision "2022-01-07" {
        description "Modified Data Type";
        reference " 0.5.0.";
    }

    revision "2021-11-15" {
        description "Moved BFD depenedecies under HAVE_BFD";
        reference " 0.4.0.";
    }

    revision "2021-09-15" {
        description "removed the yang drop element for the additional-path attributes for the bgp-add-path feature.";
        reference " 0.3.2.";
    }

    revision "2021-08-26" {
        description "Added dependency constraint between auth-key-encrypt and password attrs for the peer authentication password CLI";
        reference " 0.3.1.";
    }

    revision "2021-08-16" {
        description "Removed the Yang drop element for the additional-paths-mode attribute";
        reference " 0.3.0.";
    }

    revision "2021-07-05" {
        description "Remodelled BGP peer group authentication password object list";
        reference " 0.2.0.";
    }

    revision "2021-06-11" {
        description "Added dependency constraint between name and direction attrs for the distribute-list, prefix-list, filter-list and route-map CLI's";
        reference " 0.1.5.";
    }

    revision "2021-06-09" {
        description "Removal of default ipv4 unicast activate and fix for DB sync issues";
        reference " 0.1.4.";
    }

    revision "2021-06-07" {
        description "Deprecated 'connect-retry-interval', duplicate of 'peer-connect-interval'";
        reference " 0.1.3.";
    }

    revision "2021-05-31" {
        description "Added length for route map name";
        reference " 0.1.2.";
    }

    revision "2021-05-13" {
        description "Removed dependency validation on AF activate for allow-ebgp-vpn attribute";
        reference " 0.1.1.";
    }

    revision "2021-04-09" {
        description "Initial Version";
        reference " 0.1.0.";
    }



    grouping peer-group-grouping {
    description
        "List of BGP Peer groups configured";
        list peer-group {
            if-feature feature-list:HAVE_BGPD;
            key "peer-group-tag";
            description
                "List of BGP Peer groups configured";
            leaf peer-group-tag  {
                type  leafref {
                    path  "../config/peer-group-tag";
                }
                description "Creates a peer-group group. Neighbors with the same update policies
                            are grouped into peer-group groups. This facilitates the updates of
                            various policies, such as distribute and filter lists. The peer-group
                            group is then configured easily with any of the neighbor attributes.
                            Any changes made to the peer-group group affect all members.";
            } // END of peer-group-tag definition.


            list bgp-password {
            when " /bgp/bgp-instance/peer-group/bgp-password/config/auth-key-encrypt and /bgp/bgp-instance/peer-group/config/peer-as ";
                key "password";
                max-elements 1;
                description
                    "list for BGP password";
                leaf password  {
                    type  leafref {
                        path  "../config/password";
                    }
                    description "Use this attribute to enable authentication-key";
                } // END of password definition.

                container config {
                    description
                        "Configuration parameters relating to the BGP password";
                    uses bgp-password-config;
                } // END of config-container definition.
                container state {
                    config false;
                    description
                        "State parameters relating to the BGP password";
                    uses bgp-password-config;
                } // END of state-container definition.
            } // End of bgp-password-list
            container config {
                description
                    "Configuration parameters relating to the BGP Peer Group";
                uses bgp-peer-group-common-config;
                uses bgp-peer-group-config;
            } // END of config-container definition.
            container state {
                config false;
                description
                    "State parameters relating to the BGP";
                uses bgp-peer-group-common-config;
                uses bgp-peer-group-config;
            } // END of state-container definition.
            container timers {
                when " /bgp/bgp-instance/peer-group/config/peer-as ";
                description
                    "container for bgp timers";
                container config {
                    presence "To configure timers";
                    description
                        "configuration parameters relating to timers";
                    uses bgp-peer-timers-config;
                } // END of config-container definition.
                container state {
                    config false;
                    description
                        "state parameters relating to timers";
                    uses bgp-peer-timers-config;
                } // END of state-container definition.
            } // END of timers-container definition.
            container optional-as-lists {
                description
                    "Container for List of optional AS";

                list optional-as-list {
                when " /bgp/bgp-instance/peer-group/config/peer-as ";
                    key "optional-as";
                    description
                        "List of optional AS";
                    leaf optional-as  {
                        type  leafref {
                            path  "../config/optional-as";
                        }
                        description "Use this attribute to specify optional AS number of BGP dynamic
                                    peer-group";
                    } // END of optional-as definition.

                    container config {
                        description
                            "Configuration of optional as list";
                        uses bgp-optional-as-list-config;
                    } // END of config-container definition.
                    container state {
                        config false;
                        description
                            "State parameters of optional as list";
                        uses bgp-optional-as-list-config;
                    } // END of state-container definition.
                } // End of optional-as-list-list
            } // END of optional-as-lists-container definition.
            container address-families {
                description
                    "Container for list of address-families for BGP Peer";

                list address-family {
                when " /bgp/bgp-instance/address-family/afi and /bgp/bgp-instance/address-family/safi ";
                    key "afi safi";
                    description
                        "List for address-family for BGP Peer";
                    leaf afi  {
                        type  leafref {
                            path  "../config/afi";
                        }
                        description "BGP address family identifier";
                    } // END of afi definition.

                    leaf safi  {
                        type  leafref {
                            path  "../config/safi";
                        }
                        description "BGP sub address family identifier";
                    } // END of safi definition.


                    list maximum-prefixes {
                    when " /bgp/bgp-instance/peer-group/address-families/address-family/config/activate ";
                        key "prefix-count";
                        max-elements 1;
                        description
                            "list for Prefix related configuration";
                        leaf prefix-count  {
                            type  leafref {
                                path  "../config/prefix-count";
                            }
                            description "Use this attribute to specify maximum number of prefixes that can be
                                        received from a neighbor";
                        } // END of prefix-count definition.

                        container config {
                            description
                                "Configuration parameters relating to the number of prefixes that can
                                        be received from a neighbor";
                            uses bgp-address-family-maximum-prefixes-config;
                        } // END of config-container definition.
                        container state {
                            config false;
                            description
                                "State parameters relating to the VRF address family";
                            uses bgp-address-family-maximum-prefixes-config;
                        } // END of state-container definition.
                    } // End of maximum-prefixes-list
                    container config {
                        description
                            "Configuration parameters relating to the address-family for BGP Peer";
                        uses bgp-address-family-peer-group-config;
                        uses bgp-peer-group-address-family-common-config;
                    } // END of config-container definition.
                    container state {
                        config false;
                        description
                            "State parameters relating to the address-family for BGP Peer";
                        uses bgp-address-family-peer-group-config;
                        uses bgp-peer-group-address-family-common-config;
                    } // END of state-container definition.
                    container distribute-list-filters {
                        description
                            "Container for distribute list filters";

                        list distribute-list-filter {
                        when " /bgp/bgp-instance/peer-group/address-families/address-family/distribute-list-filters/distribute-list-filter/config/access-list-identifier ";
                            key "filter-direction";
                            description
                                "List of Distribute list Filter";
                            leaf filter-direction  {
                                type  leafref {
                                    path  "../config/filter-direction";
                                }
                                description "Use this attribute to specify distribute list filter direction";
                            } // END of filter-direction definition.

                            container config {
                                description
                                    "Configuration parameters relating to BGP Distribute list Filter";
                                uses bgp-distribute-list-filter-config;
                            } // END of config-container definition.
                            container state {
                                config false;
                                description
                                    "State parameters relating to BGP Distribute list Filter";
                                uses bgp-distribute-list-filter-config;
                            } // END of state-container definition.
                        } // End of distribute-list-filter-list
                    } // END of distribute-list-filters-container definition.
                    container as-list-filters {
                        description
                            "Container for  AS list Filters";

                        list as-list-filter {
                        when " /bgp/bgp-instance/peer-group/address-families/address-family/as-list-filters/as-list-filter/config/as-access-list-identifier ";
                            key "as-list-direction";
                            description
                                "List of AS list Filter";
                            leaf as-list-direction  {
                                type  leafref {
                                    path  "../config/as-list-direction";
                                }
                                description "Use this attribute to specify access list filter direction";
                            } // END of as-list-direction definition.

                            container config {
                                description
                                    "Configuration parameters relating to BGP AS list Fileter";
                                uses bgp-as-list-filter-config;
                            } // END of config-container definition.
                            container state {
                                config false;
                                description
                                    "State parameters relating to BGP AS list Fileter";
                                uses bgp-as-list-filter-config;
                            } // END of state-container definition.
                        } // End of as-list-filter-list
                    } // END of as-list-filters-container definition.
                    container prefix-list-filters {
                        description
                            "Container for Prefix list Filters";

                        list prefix-list-filter {
                        when " /bgp/bgp-instance/peer-group/address-families/address-family/prefix-list-filters/prefix-list-filter/config/prefix-list-name ";
                            key "prefix-filter-direction";
                            description
                                "List of Prefix list Filter";
                            leaf prefix-filter-direction  {
                                type  leafref {
                                    path  "../config/prefix-filter-direction";
                                }
                                description "Use this attribute to specify prefix list filter direction";
                            } // END of prefix-filter-direction definition.

                            container config {
                                description
                                    "Configuration parameters relating to BGP Prefix list Filter";
                                uses bgp-prefix-list-filter-config;
                            } // END of config-container definition.
                            container state {
                                config false;
                                description
                                    "State parameters relating to BGP Prefix list Filter";
                                uses bgp-prefix-list-filter-config;
                            } // END of state-container definition.
                        } // End of prefix-list-filter-list
                    } // END of prefix-list-filters-container definition.
                    container route-map-filters {
                        description
                            "Container for Route map Filters";

                        list route-map-filter {
                        when " /bgp/bgp-instance/peer-group/address-families/address-family/config/activate and /bgp/bgp-instance/peer-group/address-families/address-family/route-map-filters/route-map-filter/config/route-map-name ";
                            key "route-map-direction";
                            description
                                "List of Route map Filter";
                            leaf route-map-direction  {
                                type  leafref {
                                    path  "../config/route-map-direction";
                                }
                                description "Use this attribute to specify route-map direction";
                            } // END of route-map-direction definition.

                            container config {
                                description
                                    "Configuration parameters relating to BGP Route map Filter";
                                uses bgp-route-map-filter-config;
                            } // END of config-container definition.
                            container state {
                                config false;
                                description
                                    "State parameters relating to BGP Route map Filter";
                                uses bgp-route-map-filter-config;
                            } // END of state-container definition.
                        } // End of route-map-filter-list
                    } // END of route-map-filters-container definition.
                } // End of address-family-list
            } // END of address-families-container definition.
        } // End of peer-group-list
    } // END of peer-group-grouping definition.
    grouping bgp-peer-group-config {
        description
            "Configuration parameters for BGP peer-group groups";
        leaf peer-group-tag  {
            type  string {
                length "1..255";
                pattern "[^?' =,>|]+";
            }
            description "This attribute creates a peer-group group. Neighbors with the same
                        update policies are grouped into peer-group groups. This facilitates
                        the updates of various policies, such as distribute and filter lists.
                        Any changes made to the peer-group group affect all members.";
        } // END of peer-group-tag definition.

        leaf peer-group-range  {
            type  ipi-bgp-types:bgp_peer_group_type_t;
            mandatory true;
            description "Use this attribute to specify maximum peer-group group range";
        } // END of peer-group-range definition.

        leaf group-limit  {
            type  uint8 {
                 range "1..200"  {
                    description "1..200: Supported range 1 - 200";
                 }
            }
            description "This attribute specifies maximum number of peer-groups in a dynamic
                        peer-group";
        } // END of group-limit definition.

    } // END of bgp-peer-group-config definition.
    grouping bgp-address-family-peer-group-config {
        description
            "Configuration parameters for peer";
        leaf bgp-port  {
            when " /bgp/bgp-instance/peer-group/address-families/address-family/config/activate ";
            type  uint16 {
                 range "0..65535"  {
                    description "0..65535: Supported range 0 - 65535";
                 }
            }
            default "179";
            description "The BGP port number of a neighbor";
        } // END of bgp-port definition.

        leaf activate  {
            when " /bgp/bgp-instance/peer-group/config/peer-as ";
            type  empty;
            description "Activate/Deactivate neighbor. This attribute enables or disables the
                        exchange of AF information with a neighboring router.";
        } // END of activate definition.

        leaf default-peer-route-map-name  {
            when " /bgp/bgp-instance/peer-group/address-families/address-family/config/activate  and not(/bgp/bgp-instance/peer-group/address-families/address-family/config/peer-route-map-orig-name) ";
            type  empty;
            description "This attribute allows a BGP local router to send the default route
                        0.0.0.0 to a neighbor for use as a default route for specified
                        address-family.";
        } // END of default-peer-route-map-name definition.

        leaf peer-route-map-orig-name  {
            when " /bgp/bgp-instance/peer-group/address-families/address-family/config/activate  and not(/bgp/bgp-instance/peer-group/address-families/address-family/config/default-peer-route-map-name) ";
            type  string {
                length "1..63";
                pattern "[^?' =,>|]+";
            }
            description "This attribute configures route map to be used for a BGP local router
                        to send the default route 0.0.0.0 to a neighbor for use as a default
                        route for specified address-family. This attribute can be used with
                        standard or extended access lists.";
        } // END of peer-route-map-orig-name definition.

        leaf soft-reconfig-inbound  {
            when " /bgp/bgp-instance/peer-group/address-families/address-family/config/activate ";
            type  empty;
            description "This attribute stores updates for inbound soft reconfiguration for
                        specified address-family. Soft-reconfiguration may be used in lieu of
                        BGP route refresh capability. Using this attribute enables local
                        storage of all the received routes and their attributes. This requires
                        additional memory. When a soft reset (inbound) is done on this
                        neighbor, the locally stored routes are re-processed according to the
                        inbound policy. The BGP neighbor connection is not affected.";
        } // END of soft-reconfig-inbound definition.

        leaf weight  {
            when " /bgp/bgp-instance/peer-group/address-families/address-family/config/activate ";
            type  uint16 {
                 range "0..65535"  {
                    description "0..65535: Supported range 0 - 65535";
                 }
            }
            default "0";
            description "This attribute specifies a weight value, for specified address-family,
                        to all routes learned from a neighbor for specified address-family.
                        The route with the highest weight gets preference when the same prefix
                        is learned from more than one peer. Unlike the local-preference
                        attribute, the weight attribute is relevant only to the local router.
                        When the weight is set for a peer group, all members of the peer group
                        get the same weight. This attribute can also be used to assign a
                        different weight to an individual peer-group member. When an
                        individually-configured weight of a peer-group member is removed, its
                        weight is reset to its peer groups weight.";
        } // END of weight definition.

        leaf peer-route-reflector  {
            when " /bgp/bgp-instance/peer-group/address-families/address-family/config/activate ";
            type  empty;
            description "This attribute configures the router as a BGP route reflector and
                        configure the specified neighbor as its client for specified
                        address-family.
                        Route reflectors are a solution for the explosion of iBGP peering
                        within an autonomous system. By route reflection the number of iBGP
                        peers within an AS is reduced. Use this attribute to configure the
                        local router as the route reflector and specify neighbors as its
                        client. An AS can have more than one route reflector. One route
                        reflector treats the other route reflector as another iBGP speaker.";
        } // END of peer-route-reflector definition.

        leaf peer-remove-private-as  {
            when " /bgp/bgp-instance/peer-group/address-families/address-family/config/activate ";
            type  empty;
            description "This attribute removes the private Autonomous System (AS) number from
                        outbound updates. Private AS numbers are not advertised to the
                        Internet. This attribute is used with external BGP peers only. The
                        router removes the AS numbers only if the update includes private AS
                        numbers. If the update includes both private and public AS numbers,
                        the system treats it as an error.";
        } // END of peer-remove-private-as definition.

        leaf no-send-community  {
            when " /bgp/bgp-instance/peer-group/address-families/address-family/config/activate ";
            type  empty;
            description "This attribute specifies if a community attribute should be sent to a
                        BGP neighbor for specified address-family. The community attribute
                        groups destinations in a certain community and applies routing
                        decisions according to those communities. By default, both standard
                        and extended community attributes are sent to a neighbor";
        } // END of no-send-community definition.

        leaf no-send-community-type  {
            when " /bgp/bgp-instance/peer-group/address-families/address-family/config/activate ";
            type  ipi-bgp-types:bgp_send_commu_type_t;
            description "This attribute specifies the type of community attribute to be sent to
                        a BGP neighbor.";
        } // END of no-send-community-type definition.

        leaf neighbor-attribute-unchanged  {
            when " /bgp/bgp-instance/peer-group/address-families/address-family/config/activate ";
            type  ipi-bgp-types:bgp_attribute_unchanged_type_t;
            description "This attribute advertises unchanged BGP AS path, next hop and med to
                        the specified neighbor.";
        } // END of neighbor-attribute-unchanged definition.

        leaf orf-prefix-capability  {
            when " /bgp/bgp-instance/peer-group/address-families/address-family/config/activate ";
            type  ipi-bgp-types:bgp_orf_prefix_type_t;
            description "This attribute enables Outbound Router Filtering (ORF), and advertise
                        the ORF capability to its neighbors. The ORFs send and receive
                        capabilities to lessen the number of updates exchanged between
                        neighbors. By filtering updates, this option minimizes generating and
                        processing of updates. The two routers exchange updates to maintain
                        the ORF for each router.";
        } // END of orf-prefix-capability definition.

        leaf peer-allow-ebgp-vpn  {
            if-feature feature-list:HAVE_VRF;
            type  empty;
            description "This attribute allows an eBGP neighbor to be a VPN peer. By default,
                        BGP VPN functionality is allowed only for iBGP peers. Using the
                        peer-allow-ebgp-vpn attribute allows the VPN connection to be
                        established to an eBGP peer.";
        } // END of peer-allow-ebgp-vpn definition.

        leaf allow-as-number  {
            when " /bgp/bgp-instance/peer-group/address-families/address-family/config/activate ";
            type  uint32 {
                 range "1..10"  {
                    description "1..10: Supported range 1 - 10";
                 }
            }
            default "3";
            description "This attribute advertises prefixes (routes) even when the source of
                        the prefixes is from the same Autonomous System (AS) number for
                        specified address-family.
                        Use this attribute in a scenario where two routers at different
                        locations use the same Autonomous System number and are connected via
                        an ISP. Once prefixes arrive from one branch at the ISP, they are
                        tagged with the customers AS number. By default, when the ISP passes
                        the prefixes to the other router, the prefixes are dropped if the
                        other router uses the same AS number. Use this attribute to advertise
                        the prefixes at the other side. Control the number of times an AS
                        number is advertised by specifying a number.
                        In a hub and spoke configuration in a VPN, a PE (Provider Edge) router
                        advertises all prefixes containing duplicate AS numbers. Use this
                        attribute to configure two VRFs on each PE router to receive and
                        advertise prefixes. One of the VRFs receives prefixes with AS numbers
                        from all PE routers and then advertises them to neighboring PE
                        routers. The other VRF receives prefixes with AS numbers from the CE
                        (Customer Edge) router and advertises them to all PE routers in the
                        hub and spoke configuration.";
        } // END of allow-as-number definition.

        leaf capability-graceful-restart  {
            when " /bgp/bgp-instance/peer-group/address-families/address-family/config/activate ";
            type  empty;
            description "This attribute configures the router to advertise the Graceful Restart
                        Capability to the neighbors. This configuration indicates that the BGP
                        speaker has the ability to preserve its forwarding state for the
                        address family when BGP restarts. Use this attribute to advertise to
                        the neighbor routers the capability of graceful restart.";
        } // END of capability-graceful-restart definition.

        leaf unsuppress-route-map-name  {
            when " /bgp/bgp-instance/peer-group/address-families/address-family/config/activate ";
            type  string {
                length "1..1965";
                pattern "[^?' =,>|]+";
            }
            description "unsuppress map name. This attribute is used to selectively leak
                        more-specific routes to a particular neighbor.";
        } // END of unsuppress-route-map-name definition.

    } // END of bgp-address-family-peer-group-config definition.
    grouping bgp-peer-group-common-config {
        description
            "Configuration parameters common for BGP groups";
        leaf peer-as  {
            type  uint32 {
                 range "1..4294967295"  {
                    description "1..4294967295: Supported range 1 - 4294967295";
                 }
            }
            description "Autonomous system number of a neighbor.  If the specified ASN matches
                        the ASN number specified in the router bgp global configuration, the
                        neighbor is identified as internal. If the ASN does no match, it is
                        identified as external to the local AS.";
        } // END of peer-as definition.

        leaf graceful-shut  {
            type  empty;
            description "Use this attribute to start a graceful shutdown for the BGP session of
                        the specified BGP neighbor. The BGP session for this neighbor is shut
                        down after the graceful shutdown timer expires.
                        If there is no alternate path available for traffic to flow prior the
                        actual shutdown of the BGP session, this path is made available for 60
                        seconds or for configured time after which the path is no longer
                        available and traffic is dropped.";
        } // END of graceful-shut definition.

        leaf enable-peer-bfd  {
            when " /bgp/bgp-instance/peer-group/config/peer-as ";
            if-feature feature-list:HAVE_BFD;
            type  empty;
            description "Enable bidirectional forwarding detection (BFD) for the BGP peer-group";
        } // END of enable-peer-bfd definition.

        leaf enable-peer-bfd-multihop  {
            when " /bgp/bgp-instance/peer-group/config/enable-peer-bfd ";
            if-feature feature-list:HAVE_BFD;
            type  empty;
            description "Enable bidirectional forwarding detection (BFD) for the BGP peer-group
                        with multihop";
        } // END of enable-peer-bfd-multihop definition.

        leaf graceful-shutdown-timer  {
            when " /bgp/bgp-instance/peer-group/config/peer-as ";
            type  uint32 {
                 range "10..65535"  {
                    description "10..65535: Supported range 10 - 65535";
                 }
            }
            description "Configure the value of the graceful shutdown timer. After the timer
                        expires, the BGP session initiated for graceful shutdown is shut down.";
        } // END of graceful-shutdown-timer definition.

        leaf peer-restart-time  {
            when " /bgp/bgp-instance/peer-group/config/peer-as ";
            if-feature feature-list:HAVE_RESTART;
            type  uint32 {
                 range "1..3600"  {
                    description "1..3600: Supported range 1 - 3600";
                 }
            }
            description "Sets a different restart-time other than the global restart-time. This
                        attribute takes precedence over the restart-time value specified using
                        the grstSet attribute. The restart-time value is the maximum time that
                        a graceful-restart neighbor waits to come back up after a restart. The
                        default value is 120 seconds.";
        } // END of peer-restart-time definition.

        leaf peer-local-as  {
            when " /bgp/bgp-instance/peer-group/config/peer-as ";
            type  uint32 {
                 range "1..4294967295"  {
                    description "1..4294967295: Supported range 1 - 4294967295";
                 }
            }
            description "Specifies an AS (autonomous system) number to use with BGP neighbor.";
        } // END of peer-local-as definition.

        leaf peer-description  {
            when " /bgp/bgp-instance/peer-group/config/peer-as ";
            type  cml-data-types:cml_line_t {
                length "1..1965";
            }
            description "Associates a description with a neighbor. This helps in identifying a
                        neighbor quickly. It is useful for an ISP that has multiple neighbor
                        relationships.";
        } // END of peer-description definition.

        leaf enable-ebgp-multihop  {
            when " not(/bgp/bgp-instance/peer-group/config/ebgp-maximum-hop-count) and /bgp/bgp-instance/peer-group/config/peer-as ";
            type  empty;
            description "Accept and attempt BGP connections to external peer-groups on
                        indirectly connected networks. Multihop is not established if the only
                        route to the multihop peer-group is a default route. This avoids loop
                        formation.";
        } // END of enable-ebgp-multihop definition.

        leaf ebgp-maximum-hop-count  {
            when " not(/bgp/bgp-instance/peer-group/config/enable-ebgp-multihop) and /bgp/bgp-instance/peer-group/config/peer-as ";
            type  uint8 {
                 range "1..255"  {
                    description "1..255: Supported range 1 - 255";
                 }
            }
            default "255";
            description "Configures maximum hop count for the BGP neighbor ebgp-multihop
                        configuration.";
        } // END of ebgp-maximum-hop-count definition.

        leaf peer-connect-interval  {
            when " /bgp/bgp-instance/peer-group/config/peer-as ";
            type  uint32 {
                 range "1..65535"  {
                    description "1..65535: Supported range 1 - 65535";
                 }
            }
            default "1";
            description "This attribute sets the timers for a specific BGP neighbor. Keepalive
                        messages are sent by a router to inform another router that the BGP
                        connection between the two is still active. The keepalive interval is
                        the period of time between each keepalive message sent by the router.
                        The holdtime interval is the time the router waits to receive a
                        keepalive message and if it does not receive a message for this period
                        it declares the neighbor dead.";
        } // END of peer-connect-interval definition.

        leaf peer-as-origin-interval  {
            when " /bgp/bgp-instance/peer-group/config/peer-as ";
            type  uint32 {
                 range "1..65535"  {
                    description "1..65535: Supported range 1 - 65535";
                 }
            }
            default "1";
            description "Configures the minimum interval between the sending of AS-origination
                        routing updates.";
        } // END of peer-as-origin-interval definition.

        leaf min-route-advertisement-interval  {
            when " /bgp/bgp-instance/peer-group/config/peer-as ";
            type  uint32 {
                 range "0..65535"  {
                    description "0..65535: Supported range 0 - 65535";
                 }
            }
            default "0";
            description "Sets a minimum route advertisement interval between the sending of BGP
                        routing updates. To reduce the flapping of routes to internet, a
                        minimum advertisement interval is set, so that the BGP routing updates
                        are sent only per interval seconds.";
        } // END of min-route-advertisement-interval definition.

        leaf enable-dynamic-capability  {
            when " /bgp/bgp-instance/peer-group/config/peer-as ";
            type  empty;
            description "Use this attribute to enable the dynamic capability for a specific
                        peer-group. This attribute allows a BGP speaker to advertise or
                        withdraw an address family capability to a peer-group in a
                        non-disruptive manner.";
        } // END of enable-dynamic-capability definition.

        leaf collide-established  {
            when " /bgp/bgp-instance/peer-group/config/peer-as ";
            type  empty;
            description "Include a neighbor already in an established state for conflict
                        resolution when a TCP connection collision is detected.";
        } // END of collide-established definition.

        leaf source-identifier  {
            when " /bgp/bgp-instance/peer-group/config/peer-as ";
            type  string {
                length "1..1965";
                pattern "[^?' =,>|]+";
            }
            default "NULL";
            description "Allows internal BGP sessions to use any operational interface for TCP
                        connections. This attribute can be used in conjunction with any
                        specified interface on the router. The loopback interface is the
                        interface that is most commonly used with this attribute. The use of
                        loopback interface eliminates a dependency and BGP does not have to
                        rely on the availability of a particular interface for making TCP
                        connections.";
        } // END of source-identifier definition.

        leaf enforce-multi-hop  {
            when " /bgp/bgp-instance/peer-group/config/peer-as ";
            type  empty;
            description "Turns on the enforcement of eBGP neighbors perform multihop.";
        } // END of enforce-multi-hop definition.

        leaf neighbor-override-capability  {
            when " /bgp/bgp-instance/peer-group/config/peer-as ";
            type  empty;
            description "Override a capability negotiation result and use locally configured
                        values.";
        } // END of neighbor-override-capability definition.

        leaf neighbor-strict-capability-match  {
            when " /bgp/bgp-instance/peer-group/config/peer-as ";
            type  empty;
            description "Close the BGP connection if capability value does not match the remote
                        peer-group.";
        } // END of neighbor-strict-capability-match definition.

        leaf disallow-infinite-hold-time  {
            when " /bgp/bgp-instance/peer-group/config/peer-as ";
            type  empty;
            description "Disallow configuration of infinite hold-time. A hold-time of 0 seconds
                        from the peer-group (during exchange of open messages) or the user
                        (during configuration) will be rejected.";
        } // END of disallow-infinite-hold-time definition.

        leaf disable-capability-negotiation  {
            when " /bgp/bgp-instance/peer-group/config/peer-as ";
            type  empty;
            description "Disable the capability negotiation. It allows compatibility with older
                        BGP versions that have no capability parameters used in open messages
                        between peer-groups.";
        } // END of disable-capability-negotiation definition.

        leaf neighbor-passive  {
            when " /bgp/bgp-instance/peer-group/config/peer-as ";
            type  empty;
            description "Sets a BGP neighbor as passive.";
        } // END of neighbor-passive definition.

        leaf peer-shutdown  {
            when " /bgp/bgp-instance/peer-group/config/peer-as ";
            type  empty;
            description "Disables a neighbor administratively. It will terminate any active
                        session for a specified neighbor and clear all related routing
                        information. In case a peer-group group is specified for shutdown, a
                        large number of peer-grouping sessions could be terminated.";
        } // END of peer-shutdown definition.

        leaf peer-shutdown-description  {
            when " /bgp/bgp-instance/peer-group/config/peer-as ";
            // when " ipi-bgp-peer-group:peer-group/config/peer-shutdown ";
            type  cml-data-types:cml_line_t {
                length "1..255";
            }
            description "Use this attribute to send shutdown communication message to inform
                        peer the reason for the shutdown of the BGP session.";
        } // END of peer-shutdown-description definition.

        leaf peer-port  {
            when " /bgp/bgp-instance/peer-group/config/peer-as ";
            type  uint16 {
                 range "0..65535"  {
                    description "0..65535: Supported range 0 - 65535";
                 }
            }
            default "179";
            description "Sets the BGP port number of a neighbor.";
        } // END of peer-port definition.

        leaf bgp-version  {
            when " /bgp/bgp-instance/peer-group/config/peer-as ";
            type  uint8;
            default "4";
            description "Configure router to accept only a particular BGP version. By default,
                        the system uses BGP version 4 and on request dynamically negotiates
                        down to version 2. Disables the routers version-negotiation capability
                        and forces the router to use only a specified version with the
                        neighbor.";
        } // END of bgp-version definition.

        leaf enable-ext-opt-param-len  {
            when " /bgp/bgp-instance/peer-group/config/peer-as ";
            type  empty;
            description "Use this attribute for a specific peer to encode extended optional
                        parameter length.";
        } // END of enable-ext-opt-param-len definition.

    } // END of bgp-peer-group-common-config definition.
    grouping bgp-peer-group-address-family-common-config {
        description
            "Configuration parameters common for BGP address family";
        leaf afi  {
            type  ipi-bgp-types:bgp_afi_type_t;
            description "BGP address family identifier";
        } // END of afi definition.

        leaf safi  {
            type  ipi-bgp-types:bgp_safi_type_t;
            description "BGP sub address family identifier";
        } // END of safi definition.

        leaf additional-paths-mode  {
            when " /bgp/bgp-instance/peer-group/address-families/address-family/config/activate ";
            if-feature feature-list:HAVE_BGP_ADD_PATH;
            type  ipi-bgp-types:bgp_peer_additional_path_type_t;
            description "Adds additional paths in the BGP table";
        } // END of additional-paths-mode definition.

        leaf additional-path-select-all  {
            when " /bgp/bgp-instance/peer-group/address-families/address-family/config/activate ";
            if-feature feature-list:HAVE_BGP_ADD_PATH;
            type  empty;
            description "Attribute to select advertise additional path";
        } // END of additional-path-select-all definition.

        leaf additional-paths-best-select-count  {
            when " /bgp/bgp-instance/peer-group/address-families/address-family/config/activate ";
            if-feature feature-list:HAVE_BGP_ADD_PATH;
            type  uint8 {
                 range "2..3"  {
                    description "2..3: Supported range 2 - 3";
                 }
            }
            description "Attribute to select best advertise additional path";
        } // END of additional-paths-best-select-count definition.

        leaf route-server-client  {
            when " /bgp/bgp-instance/peer-group/address-families/address-family/config/activate ";
            type  empty;
            description "This attribute configures a neighbor as the route server client for
                        specified address-family.";
        } // END of route-server-client definition.

        leaf next-hop-self  {
            when " /bgp/bgp-instance/peer-group/address-families/address-family/config/activate ";
            type  empty;
            description "This attribute configure the router as the next hop for a BGP-speaking
                        neighbor or peer-group group. This attribute allows a BGP router to
                        change the nexthop information that is sent to the iBGP peer-group.
                        The nexthop information is set to the IP address of the interface used
                        to communicate with the neighbor.";
        } // END of next-hop-self definition.

    } // END of bgp-peer-group-address-family-common-config definition.


}
