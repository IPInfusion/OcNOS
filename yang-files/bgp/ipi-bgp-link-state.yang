/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgp-link-state.yang
*
*/

submodule ipi-bgp-link-state {

    yang-version 1.1;

    belongs-to  ipi-bgp { prefix ipi-bgp; }

    import feature-list {
        prefix feature-list;
        revision-date 2023-02-21;
    }

    import cml-data-types {
        prefix cml-data-types;
        revision-date 2022-09-30;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "This module defines a BGP link        state datamodel";


    revision "2022-06-01" {
        description "Updated the yang file with feature";
        reference " 0.2.0.";
    }

    revision "2021-10-03" {
        description "Adding Link State EPE attributes";
        reference " 0.1.2.";
    }

    revision "2021-09-03" {
        description "Update descriptions of attribute";
        reference " 0.1.1.";
    }

    revision "2021-07-27" {
        description "Initial Version";
        reference " 0.1.0.";
    }

    grouping bgp-ls-nlri-common-state {
        description
            "State attributes common to BGP-LS NLRIs";
        leaf nlri-key  {
            type  string {
                length "1..1965";
            }
            description "BGP link-state NLRI key. The sole function of this leaf is to act as
                        the key in the list. This field shouldn't be interpreted by Netconf
                        client";
        } // END of nlri-key definition.

        leaf nlri-origin  {
            type  string {
                length "1..1965";
                pattern "[^?' =,>|]+";
            }
            description "BGP link-state NLRI origin";
        } // END of nlri-origin definition.

        leaf protocol  {
            type  cml-data-types:cml_line_t {
                length "1..1965";
            }
            description "protocol type";
        } // END of protocol definition.

        leaf nlri-identifier  {
            type  string {
                length "1..1965";
                pattern "[^?' =,>|]+";
            }
            description "BGP link-state identifier";
        } // END of nlri-identifier definition.

        leaf nlri-bgp-as  {
            type  uint32;
            description "BGP AS number";
        } // END of nlri-bgp-as definition.

        leaf bgp-router-id  {
            type  inet:ipv4-address;
            description "BGP router ID";
        } // END of bgp-router-id definition.

        leaf local-bgp-router-id  {
            if-feature feature-list:HAVE_BGP_EPE;
            type  inet:ipv4-address;
            description "Local BGP router ID";
        } // END of local-bgp-router-id definition.

        leaf local-bgp-as  {
            if-feature feature-list:HAVE_BGP_EPE;
            type  uint32;
            description "Local BGP AS number";
        } // END of local-bgp-as definition.

        leaf ospf-area-id  {
            type  inet:ipv4-address;
            description "OSPF area ID";
        } // END of ospf-area-id definition.

        leaf ospf-router-id  {
            type  inet:ipv4-address;
            description "OSPF router Id";
        } // END of ospf-router-id definition.

        leaf isis-lsp-identifier  {
            type  string {
                length "1..1965";
                pattern "[^?' =,>|]+";
            }
            description "LSP identifier";
        } // END of isis-lsp-identifier definition.

    } // END of bgp-ls-nlri-common-state definition.
    grouping bgp-ls-node-nlri-state {
        description
            "State attributes for BGP-LS node NLRI";
        leaf designated-router-id  {
            type  inet:ipv4-address;
            description "designated router ID";
        } // END of designated-router-id definition.

        leaf range-size  {
            type  uint32;
            description "Segment routing global block range size";
        } // END of range-size definition.

        leaf base-segment-identifier  {
            type  uint32;
            description "base segment identifier";
        } // END of base-segment-identifier definition.

    } // END of bgp-ls-node-nlri-state definition.
    grouping bgp-ls-link-nlri-state {
        description
            "BGP-LS link NLRI attributes";
        leaf designated-router-id  {
            type  inet:ipv4-address;
            description "designated router ID";
        } // END of designated-router-id definition.

        leaf ospf-remote-area-id  {
            type  inet:ipv4-address;
            description "OSPF remote area ID";
        } // END of ospf-remote-area-id definition.

        leaf ospf-remote-router-id  {
            type  inet:ipv4-address;
            description "OSPF remote router ID";
        } // END of ospf-remote-router-id definition.

        leaf remote-designated-router-id  {
            type  inet:ipv4-address;
            description "remote designated router ID";
        } // END of remote-designated-router-id definition.

        leaf remote-isis-lsp-id  {
            type  string {
                length "1..1965";
                pattern "[^?' =,>|]+";
            }
            description "remote ISIS LSP ID";
        } // END of remote-isis-lsp-id definition.

        leaf remote-bgp-as  {
            if-feature feature-list:HAVE_BGP_EPE;
            type  uint32;
            description "Remote BGP AS number";
        } // END of remote-bgp-as definition.

        leaf remote-bgp-router-id  {
            if-feature feature-list:HAVE_BGP_EPE;
            type  inet:ipv4-address;
            description "Remote BGP router ID";
        } // END of remote-bgp-router-id definition.

        leaf local-interface-ip  {
            type  inet:ipv4-address;
            description "local interface IP";
        } // END of local-interface-ip definition.

        leaf remote-interface-ip  {
            type  inet:ipv4-address;
            description "remote interface IP";
        } // END of remote-interface-ip definition.

        leaf igp-metric-id  {
            type  uint8;
            description "IGP metric ID";
        } // END of igp-metric-id definition.

        leaf te-metric-id  {
            type  uint8;
            description "TE metric ID";
        } // END of te-metric-id definition.

        leaf adjacent-segment-identifier  {
            type  uint32;
            description "adjacent segment identifier";
        } // END of adjacent-segment-identifier definition.

    } // END of bgp-ls-link-nlri-state definition.
    grouping bgp-ls-epe-nlri-state {
        description
            "BGP LS Egress Peer Engineering       NLRI attributes";
        leaf peer-node-segment-identifier  {
            if-feature feature-list:HAVE_BGP_EPE;
            type  uint32;
            description "peer-node segment identifier";
        } // END of peer-node-segment-identifier definition.

        leaf peer-set-segment-identifier  {
            if-feature feature-list:HAVE_BGP_EPE;
            type  uint32;
            description "peer-set segment identifier";
        } // END of peer-set-segment-identifier definition.

        leaf peer-adjacency-segment-identifier  {
            if-feature feature-list:HAVE_BGP_EPE;
            type  uint32;
            description "peer-adjacency segment identifier";
        } // END of peer-adjacency-segment-identifier definition.

    } // END of bgp-ls-epe-nlri-state definition.
    grouping bgp-ls-prefix-nlri-state {
        description
            "BGP-LS prefix NLRI attributes";
        leaf ospf-route-type  {
            type  cml-data-types:cml_line_t {
                length "1..1965";
            }
            description "OSPF route type";
        } // END of ospf-route-type definition.

        leaf prefix  {
            type  inet:ipv4-address;
            description "BGP link state prefix";
        } // END of prefix definition.

        leaf prefix-length  {
            type  uint32;
            description "BGP link state prefix length";
        } // END of prefix-length definition.

        leaf prefix-metric  {
            type  uint32;
            description "IGP advertised prefix metric value";
        } // END of prefix-metric definition.

        leaf N-absolute-bit-flag  {
            type  boolean;
            description "N absolute flag bit set";
        } // END of N-absolute-bit-flag definition.

        leaf prefix-segment-identifier  {
            type  uint32;
            description "prefix segment ID";
        } // END of prefix-segment-identifier definition.

    } // END of bgp-ls-prefix-nlri-state definition.

    grouping  link-state-grouping {
    description
        "Container for BGP link-state";
    container link-state {
        if-feature feature-list:HAVE_BGP_LS;
        if-feature feature-list:HAVE_BGPD;
        config false;
        description
            "Container for BGP link-state";
        container node-nlris {
            config false;
            description
                "Enclosing container for the list of BGP link-state node NLRIs";

            list node-nlri {
                key "nlri-key";
                config false;
                description
                    "List of node NLRIs.It is keyed by nlri-key, whose format is internal
                                to the implementation exposing this information";
                leaf nlri-key  {
                    type  leafref {
                        path  "../state/nlri-key";
                    }
                    description "BGP link-state NLRI key. The sole function of this leaf is to act as
                                the key in the list. This field shouldn't be interpreted by Netconf
                                client";
                } // END of nlri-key definition.

                container state {
                    config false;
                    description
                        "BGP link-state state";
                    uses bgp-ls-nlri-common-state;
                    uses bgp-ls-node-nlri-state;
                } // END of state-container definition.
            } // End of node-nlri-list
        } // END of node-nlris-container definition.
        container link-nlris {
            config false;
            description
                "Enclosing container for the list of BGP link-state link NLRIs";

            list link-nlri {
                key "nlri-key";
                config false;
                description
                    "List of link NLRIs. It is keyed by nlri-key, whose format is internal
                                to the implementation exposing this information";
                leaf nlri-key  {
                    type  leafref {
                        path  "../state/nlri-key";
                    }
                    description "BGP link-state NLRI key. The sole function of this leaf is to act as
                                the key in the list. This field shouldn't be interpreted by Netconf
                                client";
                } // END of nlri-key definition.

                container state {
                    config false;
                    description
                        "BGP link-state state";
                    uses bgp-ls-nlri-common-state;
                    uses bgp-ls-link-nlri-state;
                    uses bgp-ls-epe-nlri-state;
                } // END of state-container definition.
            } // End of link-nlri-list
        } // END of link-nlris-container definition.
        container prefix-nlris {
            config false;
            description
                "Enclosing container for the list of BGP link-state prefix NLRIs";

            list prefix-nlri {
                key "nlri-key";
                config false;
                description
                    "List of prefix NLRIs. It is keyed by nlri-key, whose format is
                                internal to the implementation exposing this information";
                leaf nlri-key  {
                    type  leafref {
                        path  "../state/nlri-key";
                    }
                    description "BGP link-state NLRI key. The sole function of this leaf is to act as
                                the key in the list. This field shouldn't be interpreted by Netconf
                                client";
                } // END of nlri-key definition.

                container state {
                    config false;
                    description
                        "BGP link-state state";
                    uses bgp-ls-nlri-common-state;
                    uses bgp-ls-prefix-nlri-state;
                } // END of state-container definition.
            } // End of prefix-nlri-list
        } // END of prefix-nlris-container definition.
    } // END of link-state-container definition.
    } // END of link-state-grouping definition.


}
