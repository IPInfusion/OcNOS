/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgp-peer.yang
*
*/

submodule ipi-bgp-peer {

    yang-version 1.1;

    belongs-to  ipi-bgp { prefix ipi-bgp; }

    import feature-list {
        prefix feature-list;
        revision-date 2023-02-21;
    }

    import cml-data-types {
        prefix cml-data-types;
        revision-date 2022-09-30;
    }

    import ipi-bgp-types {
        prefix ipi-bgp-types;
        revision-date 2022-09-08;
    }

    include ipi-bgp-common { revision-date 2022-07-06;}
    include ipi-bgp-address-family { revision-date 2022-07-16;}
    include ipi-bgp-epe { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "";


    revision "2022-07-06" {
        description "Skipped dependency validation for a composite constraint of peer-as and peer-group-tag for BGP peer";
        reference " 0.11.4.";
    }

    revision "2022-06-27" {
        description "Added support for 'allow-as-number' in 'address-family ipv4 labeled-unicast' mode.";
        reference " 0.11.3.";
    }

    revision "2022-06-21" {
        description "Updated when tag constraints for peer's mapped peer-group tag attribute";
        reference " 0.11.2.";
    }

    revision "2022-06-20" {
        description "Added new attribute 'de-activate' for BGP Peer-group feature.";
        reference " 0.11.1.";
    }

    revision "2022-06-01" {
        description "Updated the yang file with feature";
        reference " 0.11.0.";
    }

    revision "2022-04-04" {
        description "Added support for BGP AIGP feature";
        reference " 0.9.1.";
    }

    revision "2022-03-29" {
        description "Added new attribute 'peer-shutdown-description' for support of BGP Administrative Shutdown Communication feature.";
        reference " 0.9.2.";
    }

    revision "2022-03-20" {
        description "Added new attribute for RFC-9072";
        reference " 0.10.0.";
    }

    revision "2022-01-17" {
        description "Modified data type";
        reference " 0.9.1.";
    }

    revision "2022-01-07" {
        description "Modified Data Type";
        reference " 0.9.0.";
    }

    revision "2021-11-15" {
        description "Moved BFD depenedecies under HAVE_BFD";
        reference " 0.8.0.";
    }

    revision "2021-09-15" {
        description "removed the yang drop element for the additional-path attributes for the bgp-add-path feature.";
        reference " 0.7.2.";
    }

    revision "2021-08-26" {
        description "Added dependency constraint between auth-key-encrypt and password attrs for the peer authentication password CLI";
        reference " 0.7.1.";
    }

    revision "2021-08-16" {
        description "Removed the Yang drop element for the additional-paths-mode attribute";
        reference " 0.7.0.";
    }

    revision "2021-07-05" {
        description "Remodelled BGP peer authentication password object list";
        reference " 0.6.0.";
    }

    revision "2021-06-11" {
        description "Added dependency constraint between name and direction attrs for the distribute-list, prefix-list, filter-list and route-map CLI's";
        reference " 0.5.4.";
    }

    revision "2021-06-09" {
        description "Removal of default ipv4 unicast activate and fix for DB sync issues";
        reference " 0.5.3.";
    }

    revision "2021-06-07" {
        description "Deprecated 'connect-retry-interval', duplicate of 'peer-connect-interval'";
        reference " 0.5.2.";
    }

    revision "2021-05-31" {
        description "Added length for route map name";
        reference " 0.5.1.";
    }

    revision "2021-05-05" {
        description "Change related to BGP unnumbered feature";
        reference " 0.5.0.";
    }

    revision "2021-04-09" {
        description "Change related to Peer group remodelling";
        reference " 0.4.0.";
    }

    revision "2021-03-05" {
        description "Excluded yang generation for BGP Add path attributes";
        reference " 0.3.0.";
    }

    revision "2020-12-15" {
        description "Change to have data-types in lower case instead of camel case";
        reference " 0.2.0.";
    }

    revision "2020-09-10" {
        description "Initial Version";
        reference " 0.1.0.";
    }



    grouping peer-grouping {
    description
        "List of BGP neighbors configured on the local system, uniquely
                    identified by peer IPv[46] address";
        list peer {
            if-feature feature-list:HAVE_BGPD;
            key "peer-address";
            description
                "List of BGP neighbors configured on the local system, uniquely
                            identified by peer IPv[46] address";
            leaf peer-address  {
                type  leafref {
                    path  "../config/peer-address";
                }
                description "Reference to the address of the BGP peer used as a key in the peer
                            list";
            } // END of peer-address definition.


            list bgp-password {
            when " /bgp/bgp-instance/peer/bgp-password/config/auth-key-encrypt and /bgp/bgp-instance/peer/config/peer-as  or /bgp/bgp-instance/peer/config/mapped-peer-group-tag ";
                key "password";
                max-elements 1;
                description
                    "list for BGP password";
                leaf password  {
                    type  leafref {
                        path  "../config/password";
                    }
                    description "Use this attribute to enable authentication-key";
                } // END of password definition.

                container config {
                    description
                        "Configuration parameters relating to the BGP password";
                    uses bgp-password-config;
                } // END of config-container definition.
                container state {
                    config false;
                    description
                        "State parameters relating to the BGP password";
                    uses bgp-password-config;
                } // END of state-container definition.
            } // End of bgp-password-list

            list address-family {
            when " /bgp/bgp-instance/address-family/afi and /bgp/bgp-instance/address-family/safi ";
                key "afi safi";
                description
                    "Container for address-family for BGP Peer";
                leaf afi  {
                    type  leafref {
                        path  "../config/afi";
                    }
                    description "BGP address family identifier";
                } // END of afi definition.

                leaf safi  {
                    type  leafref {
                        path  "../config/safi";
                    }
                    description "BGP sub address family identifier";
                } // END of safi definition.


                list maximum-prefixes {
                    key "prefix-count";
                    max-elements 1;
                    description
                        "list for Prefix related configuration";
                    leaf prefix-count  {
                        type  leafref {
                            path  "../config/prefix-count";
                        }
                        description "Use this attribute to specify maximum number of prefixes that can be
                                    received from a neighbor";
                    } // END of prefix-count definition.

                    container config {
                        description
                            "Configuration parameters relating to the number of prefixes that can
                                    be received from a neighbor";
                        uses bgp-address-family-maximum-prefixes-config;
                    } // END of config-container definition.
                    container state {
                        config false;
                        description
                            "State parameters relating to the VRF address family";
                        uses bgp-address-family-maximum-prefixes-config;
                    } // END of state-container definition.
                } // End of maximum-prefixes-list

                list distribute-list-filter {
                when " /bgp/bgp-instance/peer/address-family/distribute-list-filter/config/access-list-identifier ";
                    key "filter-direction";
                    description
                        "List of Distribute list Filter";
                    leaf filter-direction  {
                        type  leafref {
                            path  "../config/filter-direction";
                        }
                        description "Use this attribute to specify distribute list filter direction";
                    } // END of filter-direction definition.

                    container config {
                        description
                            "Configuration parameters relating to BGP Distribute list Filter";
                        uses bgp-distribute-list-filter-config;
                    } // END of config-container definition.
                    container state {
                        config false;
                        description
                            "State parameters relating to BGP Distribute list Filter";
                        uses bgp-distribute-list-filter-config;
                    } // END of state-container definition.
                } // End of distribute-list-filter-list

                list as-list-filter {
                when " /bgp/bgp-instance/peer/address-family/as-list-filter/config/as-access-list-identifier ";
                    key "as-list-direction";
                    description
                        "List of AS list Filter";
                    leaf as-list-direction  {
                        type  leafref {
                            path  "../config/as-list-direction";
                        }
                        description "Use this attribute to specify access list filter direction";
                    } // END of as-list-direction definition.

                    container config {
                        description
                            "Configuration parameters relating to BGP AS list Fileter";
                        uses bgp-as-list-filter-config;
                    } // END of config-container definition.
                    container state {
                        config false;
                        description
                            "State parameters relating to BGP AS list Fileter";
                        uses bgp-as-list-filter-config;
                    } // END of state-container definition.
                } // End of as-list-filter-list

                list prefix-list-filter {
                when " /bgp/bgp-instance/peer/address-family/prefix-list-filter/config/prefix-list-name ";
                    key "prefix-filter-direction";
                    description
                        "List of Prefix list Filter";
                    leaf prefix-filter-direction  {
                        type  leafref {
                            path  "../config/prefix-filter-direction";
                        }
                        description "Use this attribute to specify prefix list filter direction";
                    } // END of prefix-filter-direction definition.

                    container config {
                        description
                            "Configuration parameters relating to BGP Prefix list Filter";
                        uses bgp-prefix-list-filter-config;
                    } // END of config-container definition.
                    container state {
                        config false;
                        description
                            "State parameters relating to BGP Prefix list Filter";
                        uses bgp-prefix-list-filter-config;
                    } // END of state-container definition.
                } // End of prefix-list-filter-list

                list route-map-filter {
                when " /bgp/bgp-instance/peer/address-family/route-map-filter/config/route-map-name ";
                    key "route-map-direction";
                    description
                        "List of Route map Filter";
                    leaf route-map-direction  {
                        type  leafref {
                            path  "../config/route-map-direction";
                        }
                        description "Use this attribute to specify route-map direction";
                    } // END of route-map-direction definition.

                    container config {
                        description
                            "Configuration parameters relating to BGP Route map Filter";
                        uses bgp-route-map-filter-config;
                    } // END of config-container definition.
                    container state {
                        config false;
                        description
                            "State parameters relating to BGP Route map Filter";
                        uses bgp-route-map-filter-config;
                    } // END of state-container definition.
                } // End of route-map-filter-list

                list peer-adj-out-route {
                    key "network-address";
                    config false;
                    description
                        "List of BGP Peer adj out route";
                    leaf network-address  {
                        type  leafref {
                            path  "../state/network-address";
                        }
                        description "Peer Adj-Out Network address";
                    } // END of network-address definition.


                    list next-hop {
                        key "next-hop-address";
                        config false;
                        description
                            "List of next-hop address and state parameters";
                        leaf next-hop-address  {
                            type  leafref {
                                path  "../state/next-hop-address";
                            }
                            description "Peer Adj-Out Nexthop address";
                        } // END of next-hop-address definition.

                        container state {
                            config false;
                            description
                                "State attributes for next-hop";
                            uses bgp-next-hop-state;
                        } // END of state-container definition.
                    } // End of next-hop-list
                    container state {
                        config false;
                        description
                            "State parameters relating to Adj out route";
                        uses bgp-peer-adj-out-route-state;
                    } // END of state-container definition.
                } // End of peer-adj-out-route-list

                list peer-adj-in-route {
                    key "network-address";
                    config false;
                    description
                        "List of BGP Peer adj  in route";
                    leaf network-address  {
                        type  leafref {
                            path  "../state/network-address";
                        }
                        description "Peer Adj-In Network address";
                    } // END of network-address definition.


                    list next-hop {
                        key "next-hop-address";
                        config false;
                        description
                            "List of next-hop address and state parameters";
                        leaf next-hop-address  {
                            type  leafref {
                                path  "../state/next-hop-address";
                            }
                            description "Peer Adj-In Nexthop address";
                        } // END of next-hop-address definition.

                        container state {
                            config false;
                            description
                                "State attributes for next-hop";
                            uses bgp-next-hop-state;
                        } // END of state-container definition.
                    } // End of next-hop-list
                    container state {
                        config false;
                        description
                            "State parameters relating to Adj In route";
                        uses bgp-peer-adj-in-route-state;
                    } // END of state-container definition.
                } // End of peer-adj-in-route-list
                container config {
                    description
                        "Configuration parameters relating to the address-family for BGP Peer";
                    uses bgp-peer-address-family-common-config;
                    uses bgp-address-family-peer-config;
                } // END of config-container definition.
                container state {
                    config false;
                    description
                        "State parameters relating to the address-family for BGP Peer";
                    container counters {
                        config false;
                        description
                            "Container for the peer runtime counters";
                        uses bgp-peer-run-time-counters-state;
                    } // END of counters-container definition.
                    uses bgp-peer-address-family-common-config;
                    uses bgp-address-family-peer-config;
                    uses bgp-peer-run-time-attribute-state;
                } // END of state-container definition.
                container outbound-route-filter {
                    config false;
                    description
                        "Container for the peer runtime outbound route filter";
                    container state {
                        config false;
                        description
                            "State parameters relating to outbound route filter";
                        uses bgp-peer-run-time-orf-state;
                    } // END of state-container definition.
                } // END of outbound-route-filter-container definition.
                container peer-prefix {
                    config false;
                    description
                        "Container for peer prefix attributes";
                    container state {
                        config false;
                        description
                            "State parameters relating to prefix attributes";
                        uses bgp-peer-run-time-attribute-prefix-state;
                    } // END of state-container definition.
                } // END of peer-prefix-container definition.
                container peer-index {
                    config false;
                    description
                        "Container for peer index attributes";
                    container state {
                        config false;
                        description
                            "State parameters relating to peer index attributes";
                        uses bgp-peer-run-time-attribute-index-state;
                    } // END of state-container definition.
                } // END of peer-index-container definition.
                uses bgp-peer-address-family-aigp-config-top;
            } // End of address-family-list
            container config {
                description
                    "Configuration parameters relating to the BGP Peer";
                uses bgp-peer-common-config;
            } // END of config-container definition.
            container state {
                config false;
                description
                    "State parameters relating to the BGP";
                uses bgp-peer-common-config;
                uses bgp-peer-common-state;
            } // END of state-container definition.
            container timers {
                when " /bgp/bgp-instance/peer/config/peer-as  and not(/bgp/bgp-instance/peer/config/mapped-peer-group-tag) ";
                description
                    "container for bgp timers";
                container config {
                    presence "To configure timers";
                    description
                        "configuration parameters relating to timers";
                    uses bgp-peer-timers-config;
                } // END of config-container definition.
                container state {
                    config false;
                    description
                        "state parameters relating to timers";
                    uses bgp-peer-timers-config;
                } // END of state-container definition.
            } // END of timers-container definition.
            uses egress-engineering-grouping;
        } // End of peer-list
    } // END of peer-grouping definition.
    grouping bgp-peer-common-config {
        description
            "Configuration parameters common for BGP peers";
        leaf peer-address  {
            type  ipi-bgp-types:bgp_ip_addr_t;
            description "Address of the BGP peer, either in IPv4 or IPv6. The specified
                        neighbor exchanges routing information only if the neighbor is also
                        activated using the activate attribute.";
        } // END of peer-address definition.

        leaf peer-as  {
            type  ipi-bgp-types:bgp_as_type_t;
            description "Autonomous system number of a neighbor.  If the specified ASN matches
                        the ASN number specified in the router bgp global configuration, the
                        neighbor is identified as internal. If the ASN does no match, it is
                        identified as external to the local AS.";
        } // END of peer-as definition.

        leaf graceful-shut  {
            type  empty;
            description "Use this attribute to start a graceful shutdown for the BGP session of
                        the specified BGP neighbor. The BGP session for this neighbor is shut
                        down after the graceful shutdown timer expires.
                        If there is no alternate path available for traffic to flow prior the
                        actual shutdown of the BGP session, this path is made available for 60
                        seconds or for configured time after which the path is no longer
                        available and traffic is dropped.";
        } // END of graceful-shut definition.

        leaf enable-peer-bfd  {
            when " /bgp/bgp-instance/peer/config/peer-as  and not(/bgp/bgp-instance/peer/config/mapped-peer-group-tag) ";
            if-feature feature-list:HAVE_BFD;
            type  empty;
            description "Enable bidirectional forwarding detection (BFD) for the BGP peer";
        } // END of enable-peer-bfd definition.

        leaf enable-peer-bfd-multihop  {
            when " /bgp/bgp-instance/peer/config/enable-peer-bfd ";
            if-feature feature-list:HAVE_BFD;
            type  empty;
            description "Enable bidirectional forwarding detection (BFD) for the BGP peer with
                        multihop";
        } // END of enable-peer-bfd-multihop definition.

        leaf graceful-shutdown-timer  {
            when " /bgp/bgp-instance/peer/config/peer-as  or /bgp/bgp-instance/peer/config/mapped-peer-group-tag ";
            type  uint32 {
                 range "10..65535"  {
                    description "10..65535: Supported range 10 - 65535";
                 }
            }
            description "Configure the value of the graceful shutdown timer. After the timer
                        expires, the BGP session initiated for graceful shutdown is shut down.";
        } // END of graceful-shutdown-timer definition.

        leaf peer-restart-time  {
            when " /bgp/bgp-instance/peer/config/peer-as  or /bgp/bgp-instance/peer/config/mapped-peer-group-tag ";
            if-feature feature-list:HAVE_RESTART;
            type  uint32 {
                 range "1..3600"  {
                    description "1..3600: Supported range 1 - 3600";
                 }
            }
            description "Sets a different restart-time other than the global restart-time. This
                        attribute takes precedence over the restart-time value specified using
                        the grstSet attribute. The restart-time value is the maximum time that
                        a graceful-restart neighbor waits to come back up after a restart. The
                        default value is 120 seconds.";
        } // END of peer-restart-time definition.

        leaf peer-local-as  {
            when " /bgp/bgp-instance/peer/config/peer-as  and not(/bgp/bgp-instance/peer/config/mapped-peer-group-tag) ";
            type  uint32 {
                 range "1..4294967295"  {
                    description "1..4294967295: Supported range 1 - 4294967295";
                 }
            }
            description "Specifies an AS (autonomous system) number to use with BGP neighbor.";
        } // END of peer-local-as definition.

        leaf peer-description  {
            when " /bgp/bgp-instance/peer/config/peer-as  or /bgp/bgp-instance/peer/config/mapped-peer-group-tag ";
            type  cml-data-types:cml_line_t {
                length "1..1965";
            }
            description "Associates a description with a neighbor. This helps in identifying a
                        neighbor quickly. It is useful for an ISP that has multiple neighbor
                        relationships.";
        } // END of peer-description definition.

        leaf enable-ebgp-multihop  {
            when " /bgp/bgp-instance/peer/config/peer-as  and not(/bgp/bgp-instance/peer/config/ebgp-maximum-hop-count) ";
            type  empty;
            description "Accept and attempt BGP connections to external peers on indirectly
                        connected networks. Multihop is not established if the only route to
                        the multihop peer is a default route. This avoids loop formation.";
        } // END of enable-ebgp-multihop definition.

        leaf ebgp-maximum-hop-count  {
            when " /bgp/bgp-instance/peer/config/peer-as  and not(/bgp/bgp-instance/peer/config/enable-ebgp-multihop) ";
            type  uint8 {
                 range "1..255"  {
                    description "1..255: Supported range 1 - 255";
                 }
            }
            default "255";
            description "Configures maximum hop count for the BGP neighbor ebgp-multihop
                        configuration.";
        } // END of ebgp-maximum-hop-count definition.

        leaf peer-connect-interval  {
            when " /bgp/bgp-instance/peer/config/peer-as  and not(/bgp/bgp-instance/peer/config/mapped-peer-group-tag) ";
            type  uint32 {
                 range "1..65535"  {
                    description "1..65535: Supported range 1 - 65535";
                 }
            }
            default "1";
            description "This attribute sets the timers for a specific BGP neighbor. Keepalive
                        messages are sent by a router to inform another router that the BGP
                        connection between the two is still active. The keepalive interval is
                        the period of time between each keepalive message sent by the router.
                        The holdtime interval is the time the router waits to receive a
                        keepalive message and if it does not receive a message for this period
                        it declares the neighbor dead.";
        } // END of peer-connect-interval definition.

        leaf peer-as-origin-interval  {
            when " /bgp/bgp-instance/peer/config/peer-as  and not(/bgp/bgp-instance/peer/config/mapped-peer-group-tag) ";
            type  uint32 {
                 range "1..65535"  {
                    description "1..65535: Supported range 1 - 65535";
                 }
            }
            default "1";
            description "Configures the minimum interval between the sending of AS-origination
                        routing updates.";
        } // END of peer-as-origin-interval definition.

        leaf min-route-advertisement-interval  {
            when " /bgp/bgp-instance/peer/config/peer-as  and not(/bgp/bgp-instance/peer/config/mapped-peer-group-tag) ";
            type  uint32 {
                 range "0..65535"  {
                    description "0..65535: Supported range 0 - 65535";
                 }
            }
            default "0";
            description "Sets a minimum route advertisement interval between the sending of BGP
                        routing updates. To reduce the flapping of routes to internet, a
                        minimum advertisement interval is set, so that the BGP routing updates
                        are sent only per interval seconds.";
        } // END of min-route-advertisement-interval definition.

        leaf enable-dynamic-capability  {
            when " /bgp/bgp-instance/peer/config/peer-as  or /bgp/bgp-instance/peer/config/mapped-peer-group-tag ";
            type  empty;
            description "Use this attribute to enable the dynamic capability for a specific
                        peer. This attribute allows a BGP speaker to advertise or withdraw an
                        address family capability to a peer in a non-disruptive manner.";
        } // END of enable-dynamic-capability definition.

        leaf collide-established  {
            when " /bgp/bgp-instance/peer/config/peer-as  or /bgp/bgp-instance/peer/config/mapped-peer-group-tag ";
            type  empty;
            description "Include a neighbor already in an established state for conflict
                        resolution when a TCP connection collision is detected.";
        } // END of collide-established definition.

        leaf source-identifier  {
            type  string {
                length "1..1965";
                pattern "[^?' =,>|]+";
            }
            default "NULL";
            description "Allows internal BGP sessions to use any operational interface for TCP
                        connections. This attribute can be used in conjunction with any
                        specified interface on the router. The loopback interface is the
                        interface that is most commonly used with this attribute. The use of
                        loopback interface eliminates a dependency and BGP does not have to
                        rely on the availability of a particular interface for making TCP
                        connections.";
        } // END of source-identifier definition.

        leaf enforce-multi-hop  {
            when " /bgp/bgp-instance/peer/config/peer-as  or /bgp/bgp-instance/peer/config/mapped-peer-group-tag ";
            type  empty;
            description "Turns on the enforcement of eBGP neighbors perform multihop.";
        } // END of enforce-multi-hop definition.

        leaf neighbor-override-capability  {
            when " /bgp/bgp-instance/peer/config/peer-as  or /bgp/bgp-instance/peer/config/mapped-peer-group-tag ";
            type  empty;
            description "Override a capability negotiation result and use locally configured
                        values.";
        } // END of neighbor-override-capability definition.

        leaf neighbor-strict-capability-match  {
            when " /bgp/bgp-instance/peer/config/peer-as  or /bgp/bgp-instance/peer/config/mapped-peer-group-tag ";
            type  empty;
            description "Close the BGP connection if capability value does not match the remote
                        peer.";
        } // END of neighbor-strict-capability-match definition.

        leaf disallow-infinite-hold-time  {
            when " /bgp/bgp-instance/peer/config/peer-as  and not(/bgp/bgp-instance/peer/config/mapped-peer-group-tag) ";
            type  empty;
            description "Disallow configuration of infinite hold-time. A hold-time of 0 seconds
                        from the peer (during exchange of open messages) or the user (during
                        configuration) will be rejected.";
        } // END of disallow-infinite-hold-time definition.

        leaf disable-capability-negotiation  {
            when " /bgp/bgp-instance/peer/config/peer-as  and not(/bgp/bgp-instance/peer/config/mapped-peer-group-tag) ";
            type  empty;
            description "Disable the capability negotiation. It allows compatibility with older
                        BGP versions that have no capability parameters used in open messages
                        between peers.";
        } // END of disable-capability-negotiation definition.

        leaf neighbor-passive  {
            when " /bgp/bgp-instance/peer/config/peer-as  or /bgp/bgp-instance/peer/config/mapped-peer-group-tag ";
            type  empty;
            description "Sets a BGP neighbor as passive.";
        } // END of neighbor-passive definition.

        leaf peer-shutdown  {
            when " /bgp/bgp-instance/peer/config/peer-as  or /bgp/bgp-instance/peer/config/mapped-peer-group-tag ";
            type  empty;
            description "Disables a neighbor administratively. It will terminate any active
                        session for a specified neighbor and clear all related routing
                        information. In case a peer group is specified for shutdown, a large
                        number of peering sessions could be terminated.";
        } // END of peer-shutdown definition.

        leaf peer-shutdown-description  {
            when " /bgp/bgp-instance/peer/config/peer-as  or /bgp/bgp-instance/peer/config/mapped-peer-group-tag ";
            // when " ipi-bgp-peer:peer/config/peer-shutdown ";
            type  cml-data-types:cml_line_t {
                length "1..255";
            }
            description "Use this attribute to send shutdown communication message to inform
                        peer the reason for the shutdown of the BGP session.";
        } // END of peer-shutdown-description definition.

        leaf peer-port  {
            when " /bgp/bgp-instance/peer/config/peer-as  or /bgp/bgp-instance/peer/config/mapped-peer-group-tag ";
            type  uint16 {
                 range "0..65535"  {
                    description "0..65535: Supported range 0 - 65535";
                 }
            }
            default "179";
            description "Sets the BGP port number of a neighbor.";
        } // END of peer-port definition.

        leaf bgp-version  {
            when " /bgp/bgp-instance/peer/config/peer-as ";
            type  uint8;
            default "4";
            description "Configure router to accept only a particular BGP version. By default,
                        the system uses BGP version 4 and on request dynamically negotiates
                        down to version 2. Disables the routers version-negotiation capability
                        and forces the router to use only a specified version with the
                        neighbor.";
        } // END of bgp-version definition.

        leaf interface-name  {
            when " /bgp/bgp-instance/peer/config/peer-as  or /bgp/bgp-instance/peer/config/mapped-peer-group-tag ";
            type  string {
                length "1..1965";
                pattern "[^?' =,>|]+";
            }
            description "Configure the interface name of a BGP neighbor.";
        } // END of interface-name definition.

        leaf mapped-peer-group-tag  {
            when " /bgp/bgp-instance/peer-group/config/peer-as ";
            type  string {
                length "1..1965";
                pattern "[^?' =,>|]+";
            }
            description "Adds a neighbor to an existing peer group. Neighbors with the same
                        update policies are grouped into peer groups. This facilitates the
                        updates of various policies, such as distribute and filter lists. The
                        peer group is then configured easily with any of the neighbor
                        attributes. Any changes made to the peer group affect all members.";
        } // END of mapped-peer-group-tag definition.

        leaf enable-ext-opt-param-len  {
            when " /bgp/bgp-instance/peer/config/peer-as ";
            type  empty;
            description "Use this attribute for a specific peer to encode extended optional
                        parameter length.";
        } // END of enable-ext-opt-param-len definition.

    } // END of bgp-peer-common-config definition.
    grouping bgp-peer-common-state {
        description
            "Runtime parameters common for BGP peers";
    } // END of bgp-peer-common-state definition.
    grouping bgp-peer-address-family-aigp-config {
        description
            "Config parameters of peer's aigp cost-community for BGP address family";
        leaf admin-status  {
            if-feature feature-list:HAVE_BGP_AIGP;
            type  cml-data-types:cml_enable_disable_t;
            description "Enable or disable AIGP";
        } // END of admin-status definition.

        leaf aigp-send-med  {
            type  empty;
            description "Enable AIGP send multi exit discriminator.";
        } // END of aigp-send-med definition.

    } // END of bgp-peer-address-family-aigp-config definition.
    grouping bgp-peer-address-family-aigp-cost-community-config {
        description
            "Config parameters of peer's aigp cost-community for BGP address family";
        leaf send-cost-community-id  {
            if-feature feature-list:HAVE_BGP_AIGP;
            type  uint8 {
                 range "0..255"  {
                    description "0..255: Supported range 0 - 255";
                 }
            }
            mandatory true;
            description "Send AIGP value in Cost community. And get the Community ID.";
        } // END of send-cost-community-id definition.

        leaf point-of-insertion  {
            if-feature feature-list:HAVE_BGP_AIGP;
            type  ipi-bgp-types:bgp_aigp_metric_cost_community_poi_t;
            mandatory true;
            description "Send AIGP value in Cost community. And get point of insertion.";
        } // END of point-of-insertion definition.

        leaf enable-transitive  {
            if-feature feature-list:HAVE_BGP_AIGP;
            type  empty;
            description "Send AIGP value in Cost community and Enable Transitive Cost Community";
        } // END of enable-transitive definition.

    } // END of bgp-peer-address-family-aigp-cost-community-config definition.
    grouping bgp-peer-address-family-aigp-config-top {
        description
            "Config parameters of peer's AIGP for BGP address family";
        container aigp {
            if-feature feature-list:HAVE_BGP_AIGP;
            description
                "configuration parameters relating to AIGP";
            container config {
                description
                    "Configuration parameters relating to the BGP peer's AIGP";
                uses bgp-peer-address-family-aigp-config;
            } // END of config-container definition.
            container state {
                description
                    "State parameters relating to the BGP peer's AIGP";
                uses bgp-peer-address-family-aigp-config;
            } // END of state-container definition.
            container cost-community {
                if-feature feature-list:HAVE_BGP_AIGP;
                description
                    "configuration parameters relating to AIGP cost-community";
                container config {
                    presence "To configure cost-community";
                    description
                        "Configuration parameters relating to the BGP peer's AIGP
                                cost-community";
                    uses bgp-peer-address-family-aigp-cost-community-config;
                } // END of config-container definition.
                container state {
                    description
                        "State parameters relating to the BGP peer's aigp cost-community";
                    uses bgp-peer-address-family-aigp-cost-community-config;
                } // END of state-container definition.
            } // END of cost-community-container definition.
        } // END of aigp-container definition.
    } // END of bgp-peer-address-family-aigp-config-top definition.
    grouping bgp-peer-address-family-common-config {
        description
            "Configuration parameters common for BGP address family";
        leaf afi  {
            type  ipi-bgp-types:bgp_afi_type_t;
            description "BGP address family identifier";
        } // END of afi definition.

        leaf safi  {
            type  ipi-bgp-types:bgp_safi_type_t;
            description "BGP sub address family identifier";
        } // END of safi definition.

        leaf additional-paths-mode  {
            when " /bgp/bgp-instance/peer/address-family/config/activate ";
            if-feature feature-list:HAVE_BGP_ADD_PATH;
            type  ipi-bgp-types:bgp_peer_additional_path_type_t;
            description "Adds additional paths in the BGP table";
        } // END of additional-paths-mode definition.

        leaf additional-path-select-all  {
            when " /bgp/bgp-instance/peer/address-family/config/activate ";
            if-feature feature-list:HAVE_BGP_ADD_PATH;
            type  empty;
            description "Attribute to select advertise additional path";
        } // END of additional-path-select-all definition.

        leaf additional-paths-best-select-count  {
            when " /bgp/bgp-instance/peer/address-family/config/activate ";
            if-feature feature-list:HAVE_BGP_ADD_PATH;
            type  uint8 {
                 range "2..3"  {
                    description "2..3: Supported range 2 - 3";
                 }
            }
            description "Attribute to select best advertise additional path";
        } // END of additional-paths-best-select-count definition.

        leaf route-server-client  {
            type  empty;
            description "This attribute configures a neighbor as the route server client for
                        specified address-family.";
        } // END of route-server-client definition.

        leaf next-hop-self  {
            type  empty;
            description "This attribute configure the router as the next hop for a BGP-speaking
                        neighbor or peer group. This attribute allows a BGP router to change
                        the nexthop information that is sent to the iBGP peer. The nexthop
                        information is set to the IP address of the interface used to
                        communicate with the neighbor.";
        } // END of next-hop-self definition.

    } // END of bgp-peer-address-family-common-config definition.


}
