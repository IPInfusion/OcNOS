/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgp-epe.yang
*
*/

submodule ipi-bgp-epe {

    yang-version 1.1;

    belongs-to  ipi-bgp { prefix ipi-bgp; }

    import feature-list {
        prefix feature-list;
        revision-date 2023-02-21;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "";


    revision "2022-06-01" {
        description "Updated the yang file with feature";
        reference " 0.1.4.";
    }

    revision "2022-02-28" {
        description "Modified the Backup container heirarchy";
        reference " 0.1.3.";
    }

    revision "2021-10-03" {
        description "Added BGP-LS-EPE runtime attributes";
        reference " 0.1.2.";
    }

    revision "2021-09-03" {
        description "Update descriptions of attribute";
        reference " 0.1.1.";
    }

    revision "2021-08-09" {
        description "Initial Version";
        reference " 0.1.0.";
    }

    grouping bgp-epe-global-config {
        description
            "Global Configurational       Parameters for Egress Engineering";
        leaf enable-epe  {
            type  empty;
            description "Use this attribute to enable Egress Peer Engineering for bgp";
        } // END of enable-epe definition.

    } // END of bgp-epe-global-config definition.
    grouping bgp-epe-peer-node-config {
        description
            "Configurational parameters       for peer-node SID";
        leaf enable-peer-node  {
            type  empty;
            description "Use this attribute to enable peer node SID for bgp neighbor";
        } // END of enable-peer-node definition.

    } // END of bgp-epe-peer-node-config definition.
    grouping bgp-epe-peer-set-config {
        description
            "Configurational parameters       for Peer-Set SID";
        leaf set-name  {
            type  string {
                length "1..1965";
                pattern "[^?' =,>|]+";
            }
            description "";
        } // END of set-name definition.

    } // END of bgp-epe-peer-set-config definition.
    grouping bgp-epe-peer-adjacency-config {
        description
            "Configurational       parameters for Peer-Adj SID";
        leaf hop-address  {
            type  inet:ipv4-address;
            description "";
        } // END of hop-address definition.

    } // END of bgp-epe-peer-adjacency-config definition.
    grouping bgp-epe-backup-peer-node-config {
        description
            "Configurational       parameters for backup for peer-node SID";
        leaf address  {
            when " /bgp/bgp-instance/peer/egress-engineering/config/enable-peer-node ";
            type  inet:ipv4-address;
            description "Use this attribute for the backup peer-address";
        } // END of address definition.

    } // END of bgp-epe-backup-peer-node-config definition.
    grouping bgp-epe-backup-peer-adjacency-config {
        description
            "Configurational       parameters for backup of Peer-Adj SID";
        leaf adjacent-address  {
            type  inet:ipv4-address;
            mandatory true;
            description "Use this attribute for the backup peer-address";
        } // END of adjacent-address definition.

        leaf nexthop-address  {
            type  inet:ipv4-address;
            mandatory true;
            description "Use this attribute for the peer-address";
        } // END of nexthop-address definition.

    } // END of bgp-epe-backup-peer-adjacency-config definition.
    grouping bgp-epe-peer-sid-state {
        description
            "bgpCMLSEPepeCMLSEPpeerCMLSEPsidCMLSEPstate";
        leaf in-label  {
            type  uint32;
            description "This attribute holds the EPE label for a particular type of
                        SID allocation for a peer.";
        } // END of in-label definition.

    } // END of bgp-epe-peer-sid-state definition.
    grouping bgp-epe-peer-out-segments-state {
        description
            "bgpCMLSEPepeCMLSEPpeerCMLSEPoutCMLSEPsegmentsCMLSEPstate";
        leaf nexthop-ip-address  {
            type  inet:ipv4-address;
            description "This attribute displays the nexthop address used to reach
                        the EPE peer for a particular SID allocation";
        } // END of nexthop-ip-address definition.

        leaf out-interface  {
            type  string {
                length "1..1965";
                pattern "[^?' =,>|]+";
            }
            description "This attribute displays the out-interface used to reach the
                        EPE peer for a particular SID allocation";
        } // END of out-interface definition.

    } // END of bgp-epe-peer-out-segments-state definition.
    grouping bgp-epe-peer-node-state {
        description
            "peer node";
        uses bgp-epe-peer-sid-state;
        uses bgp-epe-peer-out-segments-state;
    } // END of bgp-epe-peer-node-state definition.
    grouping bgp-epe-peer-set-state {
        description
            "peer set";
        uses bgp-epe-peer-sid-state;
        uses bgp-epe-peer-out-segments-state;
    } // END of bgp-epe-peer-set-state definition.
    grouping bgp-epe-peer-adjacency-state {
        description
            "peer adjacency";
        uses bgp-epe-peer-sid-state;
        uses bgp-epe-peer-out-segments-state;
    } // END of bgp-epe-peer-adjacency-state definition.
    grouping bgp-epe-backup-peer-state {
        description
            "backup peer";
        uses bgp-epe-peer-out-segments-state;
    } // END of bgp-epe-backup-peer-state definition.

    grouping  peer-engineering-grouping {
    description
        "Global Egress Engineering parameter";
    container peer-engineering {
        if-feature feature-list:HAVE_BGPD;
        if-feature feature-list:HAVE_BGP_EPE;
        description
            "Global Egress Engineering parameter";
        container config {
            description
                "config of EPE";
            uses bgp-epe-global-config;
        } // END of config-container definition.
        container state {
            config false;
            description
                "state";
            uses bgp-epe-global-config;
        } // END of state-container definition.
    } // END of peer-engineering-container definition.
    } // END of peer-engineering-grouping definition.

    grouping  egress-engineering-grouping {
    description
        "Egrees Peer Engineering";
    container egress-engineering {
        when " /bgp/bgp-instance/peer-engineering/config/enable-epe ";
        if-feature feature-list:HAVE_BGPD;
        if-feature feature-list:HAVE_BGP_EPE;
        description
            "Egrees Peer Engineering";

        list peer-adjacency {
            key "hop-address";
            description
                "Paramters for Peer-Adj SIDs";
            leaf hop-address  {
                type  leafref {
                    path  "../config/hop-address";
                }
                description "";
            } // END of hop-address definition.

            container config {
                description
                    "Config for Peer-adj";
                uses bgp-epe-peer-adjacency-config;
            } // END of config-container definition.
            container state {
                config false;
                description
                    "";
                uses bgp-epe-peer-adjacency-config;
                uses bgp-epe-peer-adjacency-state;
            } // END of state-container definition.
            container backup {
                description
                    "Backup configs for Peer-Adj SIDs";
                container peer-node {
                    description
                        "Backup peer address";
                    container config {
                        description
                            "Configs for Backup for Peer-Adjacency";
                        uses bgp-epe-backup-peer-node-config;
                    } // END of config-container definition.
                    container state {
                        config false;
                        description
                            "State of backup EPE for peer Adjacency";
                        uses bgp-epe-backup-peer-node-config;
                        uses bgp-epe-backup-peer-state;
                    } // END of state-container definition.
                } // END of peer-node-container definition.
                container adjacency {
                    description
                        "Backup peer address for peer-adjacency";
                    container config {
                        description
                            "Configs for Backup for Peer-adjacency";
                        uses bgp-epe-backup-peer-adjacency-config;
                    } // END of config-container definition.
                    container state {
                        config false;
                        description
                            "State of backup EPE for peer";
                        uses bgp-epe-backup-peer-adjacency-config;
                        uses bgp-epe-backup-peer-state;
                    } // END of state-container definition.
                } // END of adjacency-container definition.
            } // END of backup-container definition.
        } // End of peer-adjacency-list
        container config {
            description
                "";
            uses bgp-epe-peer-node-config;
        } // END of config-container definition.
        container state {
            config false;
            description
                "";
            uses bgp-epe-peer-node-config;
            uses bgp-epe-peer-node-state;
        } // END of state-container definition.
        container peer-set {
            description
                "Peer-SET SIDs";
            container config {
                description
                    "Configs for Peer SET SIDs";
                uses bgp-epe-peer-set-config;
            } // END of config-container definition.
            container state {
                config false;
                description
                    "";
                uses bgp-epe-peer-set-config;
                uses bgp-epe-peer-set-state;
            } // END of state-container definition.
        } // END of peer-set-container definition.
        container backup {
            description
                "Backup configs for peer-node SIDs";
            container peer-node {
                when " not(/bgp/bgp-instance/peer/egress-engineering/backup/adjacency/config/adjacent-address) and not(/bgp/bgp-instance/peer/egress-engineering/backup/adjacency/config/nexthop-address) ";
                description
                    "Backup peer address";
                container config {
                    description
                        "Configs for backup Peer Node";
                    uses bgp-epe-backup-peer-node-config;
                } // END of config-container definition.
                container state {
                    config false;
                    description
                        "State of backup EPE for peer Node";
                    uses bgp-epe-backup-peer-node-config;
                    uses bgp-epe-backup-peer-state;
                } // END of state-container definition.
            } // END of peer-node-container definition.
            container adjacency {
                when " not(/bgp/bgp-instance/peer/egress-engineering/backup/peer-node/config/address) ";
                description
                    "Backup peer address for peer-adjacency";
                container config {
                    description
                        "Configs for Backup Peer-Node";
                    uses bgp-epe-backup-peer-adjacency-config;
                } // END of config-container definition.
                container state {
                    config false;
                    description
                        "State of backup EPE for peer Adjacency";
                    uses bgp-epe-backup-peer-adjacency-config;
                    uses bgp-epe-backup-peer-state;
                } // END of state-container definition.
            } // END of adjacency-container definition.
        } // END of backup-container definition.
    } // END of egress-engineering-container definition.
    } // END of egress-engineering-grouping definition.


}
