/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : dns.yang
*
*/

submodule dns {

    belongs-to  ZebOS { prefix ZebOS; }
    include vrf;


    import cml_data_types {
        prefix cml_data_types;
    }

    import feature_list {
        prefix feature_list;
    }

    description
        "dns_configuration";


    revision "2016-12-27" {
        description "Added snmp oid and documentation tag.";
    }

    revision "2016-10-28" {
        description "Initial version of DNS datamodel.";
    }


    grouping  dns-grouping {
    container dns {
                config true;

        description
            "dns";

        leaf vrfName  {
            type  cml_data_types:CML_STRING_T {
                length "0..255";
            }
            default "default";
        } // END of vrfName definition.

        leaf domainlookup  {
            type  cml_data_types:CML_BOOL_T;  
            description "ip domain-lookup";
        } // END of domainlookup definition.

        leaf defaultdomain  {
            if-feature feature_list:HAVE_DNS_CLIENT;
            type  cml_data_types:CML_BOOL_T;  
            description "Default domain";
        } // END of defaultdomain definition.

        leaf domainname  {
            if-feature feature_list:HAVE_DNS_CLIENT;
            type  cml_data_types:CML_STRING_T {
                length "0..255";
            }
        } // END of domainname definition.

        leaf debugdns  {
            if-feature feature_list:HAVE_DNS_CLIENT;
            type  cml_data_types:CML_BOOL_T;  
            description "debug dns client";
        } // END of debugdns definition.


        list domainlistNAME {
             
            description
                "domainlistNAME";

            config true;
            key "domainlist";

            
            leaf vrfName  {
                type  cml_data_types:CML_STRING_T {
                    length "0..255";
                }
                default "default";
            } // END of vrfName definition.

            leaf domainlist  {
                type  cml_data_types:CML_STRING_T {
                    length "0..255";
                }
                description "ip domain-list";
            } // END of domainlist definition.

        } // End of domainlistNAME-list

        list hostname {
             
            description
                "hostname";

            config true;
            key "host";

            
            leaf vrfName  {
                type  cml_data_types:CML_STRING_T {
                    length "0..255";
                }
                default "default";
            } // END of vrfName definition.

            leaf host  {
                type  cml_data_types:CML_STRING_T {
                    length "0..255";
                }
            } // END of host definition.

            leaf hostaddr1  {
                mandatory true;
                type  cml_data_types:CML_IP_ADDR_T;  
            } // END of hostaddr1 definition.

            leaf hostaddr2  {
                mandatory true;
                type  cml_data_types:CML_IP_ADDR_T;  
                description "ip host";
            } // END of hostaddr2 definition.

        } // End of hostname-list
    } // END of dns-container definition.
    } // END of dns-container definition.


}
