/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-synce.yang
*
*/

module ipi-synce {

    yang-version 1.1;

    namespace   "http://www.ipinfusion.com/yang/ocnos/ipi-synce";

    prefix "ipi-synce";

    import ipi-interface {
        prefix ipi-interface;
        revision-date 2022-08-24;
    }

    import ipi-synce-types {
        prefix ipi-synce-types;
        revision-date 2020-12-15;
    }

    import cml-data-types {
        prefix cml-data-types;
        revision-date 2022-09-30;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Synchronous Ethernet configurations";


    revision "2022-09-30" {
        description "Import cml-data-types used by notifications";
        reference " 0.5.0.";
    }

    revision "2022-06-01" {
        description "Updated the yang file with feature";
        reference " 0.4.0.";
    }

    revision "2021-09-03" {
        description "Update descriptions of attribute";
        reference " 0.3.4.";
    }

    revision "2020-12-15" {
        description "Change to have data-types in lower case instead of camel case";
        reference " 0.2.0.";
    }

    revision "2017-12-01" {
        description "Initial version of datamodel with Backend mapping";
        reference " 0.1.0.";
    }

    grouping synce-global-config {
        description
            "synce global config parameters";
        leaf enable  {
            type  empty;
            mandatory true;
            description "Use this command to configure Synchronous Ethernet. This command
                        changes the mode from configure mode to configure Synchronous Ethernet
                        mode and initializes the global Synchronous Ethernet parameters.";
        } // END of enable definition.

        leaf network-option  {
            type  ipi-synce-types:synce_sync_option_t;
            default "1";
            description "Use this command to set the synchronization option for the internal
                        clock that is locked in frequency to an incoming signal.";
        } // END of network-option definition.

        leaf clock-selection-mode  {
            type  ipi-synce-types:synce_clk_selection_mode_t;
            default "ql-enabled";
            description "Use this command to determine whether to use the Quality Level (QL) as
                        a criteria when selecting a clock";
        } // END of clock-selection-mode definition.

        leaf dpll3-select-10mhz-in  {
            type  empty;
            description "Use this command to select/deselect dpll3 input";
        } // END of dpll3-select-10mhz-in definition.

        leaf holdover-timer  {
            type  uint16 {
                 range "0..1440"  {
                    description "0..1440: Supported range 0 - 1440";
                 }
            }
            default "120";
            description "set this command to enable synce holdover (default 120 min)";
        } // END of holdover-timer definition.

    } // END of synce-global-config definition.
    grouping synce-global-state {
        description
            "synce global state runtime parameters";
        leaf equipment-clock  {
            type  string {
                length "1..1965";
                pattern "[^?' =,>|]+";
            }
            description "Equipment Clock option";
        } // END of equipment-clock definition.

        leaf locked-interface  {
            type  string {
                length "1..1965";
                pattern "[^?' =,>|]+";
            }
            description "The input interface which is locked for clock synchronization";
        } // END of locked-interface definition.

        leaf esmc-state  {
            type  ipi-synce-types:synce_esmc_state_t;
            description "The condition of Ethernet Synchronization Messaging Channel (ESMC)
                        status on the associated interface.";
        } // END of esmc-state definition.

        leaf is-source-selected  {
            type  ipi-synce-types:synce_is_src_selected_t;
            description "Whether this interface is the selected source for frequency signal";
        } // END of is-source-selected definition.

        leaf quality-level  {
            type  string {
                length "1..1965";
                pattern "[^?' =,>|]+";
            }
            description "The signals Quality Level (SyncE can choose its selected frequency
                        source based on level of signal quality or on configured Priority
                        Number)";
        } // END of quality-level definition.

        leaf current-clock-state  {
            type  ipi-synce-types:synce_clock_state_t;
            description "The clock state of the frequency signal on the associated interface.
                        Either Locked or Free Running";
        } // END of current-clock-state definition.

        leaf dpll-clock-state  {
            type  ipi-synce-types:synce_clock_state_t;
            description "The clock state of the frequency signal on the associated interface in
                        device level. Either Locked or Free Running";
        } // END of dpll-clock-state definition.

        leaf state-duration  {
            type  ipi-synce-types:synce_uptime_t {
                length "1..1965";
            }
            description "Synce State Duration";
        } // END of state-duration definition.

        leaf selected-clock-src-id  {
            type  uint32;
            description "Selected Clk-Src-ID";
        } // END of selected-clock-src-id definition.

    } // END of synce-global-state definition.
    grouping synce-interface-config {
        description
            "synce configuration interface parameters";
        leaf enable  {
            type  empty;
            mandatory true;
            description "Use this command to enable Synchronous Ethernet for an interface. This
                        command changes the mode from interface mode to interface Synchronous
                        Ethernet mode. This command does not automatically start
                        synchronization distribution. You must explicitly give the mode
                        command, specifying the synchronous option";
        } // END of enable definition.

        leaf synchronous-mode  {
            type  ipi-synce-types:synce_mode_option_t;
            default "non-synchronous";
            description "Use this command to configure the interface as synchronous or
                        non-synchronous";
        } // END of synchronous-mode definition.

        leaf input-source-priority  {
            type  uint8 {
                 range "0..255"  {
                    description "0..255: Supported range 0 - 255";
                 }
            }
            default "255";
            description "Use this command to set an input timing source. Synchronization
                        packets are received from this source and sent to the clock selection
                        algorithm";
        } // END of input-source-priority definition.

        leaf is-output-source  {
            type  boolean;
            description "Use this command to configures an Ethernet interface as a timing
                        output interface";
        } // END of is-output-source definition.

        leaf wait-to-restore-timer  {
            type  uint8 {
                 range "0..12"  {
                    description "0..12: Supported range 0 - 12";
                 }
            }
            default "5";
            description "Use this command to set the wait-to-restore timer in minutes. The
                        wait-to-restore time ensures that a synchronization source that
                        previously failed is considered by the selection process again only if
                        it is fault free for a certain time.";
        } // END of wait-to-restore-timer definition.

        leaf vlan-id  {
            type  uint16 {
                 range "1..4095"  {
                    description "1..4095: Supported range 1 - 4095";
                 }
            }
            description "use this command to configure and unconfigure the dot1q 1-4095";
        } // END of vlan-id definition.

        leaf hold-off-timer  {
            type  uint16 {
                 range "300..1800"  {
                    description "300..1800: Supported range 300 - 1800";
                 }
            }
            default "300";
            description "Use this command to set the hold-off time in milliseconds. The
                        hold-off time ensures that short activation of signal fail is not
                        passed to the selection process.";
        } // END of hold-off-timer definition.

        leaf quality-level  {
            type  string {
                length "1..1965";
                pattern "[^?' =,>|]+";
            }
            description "Use this command to set the quality level (QL) for the timing source";
        } // END of quality-level definition.

        leaf clock-source-id  {
            type  uint8 {
                 range "1..255"  {
                    description "1..255: Supported range 1 - 255";
                 }
            }
            description "Configure clock-source-identifier";
        } // END of clock-source-id definition.

        leaf clock-source-lockout  {
            if-feature feature-list:HAVE_SWFWDR;
            type  boolean;
            description "Use this command to set or clear the lockout for a clock source. A
                        clock source flagged as lockout is not considered by the clock
                        selection algorithm.";
        } // END of clock-source-lockout definition.

        leaf source-switch  {
            if-feature feature-list:HAVE_SWFWDR;
            type  ipi-synce-types:synce_source_select_t;
            description "Use this command to forcefully or manually select a synchronization
                        source";
        } // END of source-switch definition.

        leaf auto-neg-mode  {
            type  ipi-synce-types:synce_autoneg_mode_t;
            description "Use this command to configure mode";
        } // END of auto-neg-mode definition.

    } // END of synce-interface-config definition.
    grouping synce-interface-state {
        description
            "synce interface state runtime parameters";
        leaf esmc-state  {
            type  ipi-synce-types:synce_esmc_state_t;
            description "The condition of Ethernet Synchronization Messaging Channel (ESMC)
                        status on the associated interface.";
        } // END of esmc-state definition.

        leaf is-source-selected  {
            type  ipi-synce-types:synce_is_src_selected_t;
            description "Whether this interface is the selected source for frequency signal.";
        } // END of is-source-selected definition.

        leaf esmc-received  {
            type  uint64;
            description "The count of Ethernet Synchronization Messaging Channel (ESMC) packets
                        received on this interface.";
        } // END of esmc-received definition.

        leaf esmc-sent  {
            type  uint64;
            description "The count of Ethernet Synchronization Messaging Channel (ESMC) packets
                        sent on this interface.";
        } // END of esmc-sent definition.

        leaf quality-level-received-esmc  {
            type  string {
                length "1..1965";
                pattern "[^?' =,>|]+";
            }
            description "The signals Quality Level received in ESMC";
        } // END of quality-level-received-esmc definition.

        leaf operational-quality-level  {
            type  string {
                length "1..1965";
                pattern "[^?' =,>|]+";
            }
            description "The Operational Quality Level (SyncE can choose its selected frequency
                        source based on level of signal quality or on configured Priority
                        Number)";
        } // END of operational-quality-level definition.

        leaf configured-quality-level  {
            type  string {
                length "1..1965";
                pattern "[^?' =,>|]+";
            }
            description "The Configured Quality Level (SyncE can choose its selected frequency
                        source based on level of signal quality or on configured Priority
                        Number)";
        } // END of configured-quality-level definition.

        leaf interface-config-priority  {
            type  uint8;
            description "The configured Priority for this interface (used when selection
                        process is based on priority rather than on oscillator frequency
                        quality level)";
        } // END of interface-config-priority definition.

        leaf signal-fail  {
            type  ipi-synce-types:synce_is_sf_t;
            description "Whether a synchronization source has failed";
        } // END of signal-fail definition.

        leaf external-command  {
            type  ipi-synce-types:synce_external_cmds_t;
            description "Commands activated on SyncE interfaces that connect to external
                        devices. Lockout keeps a signal from a connected external device from
                        participating in the frequency source selection process. The command
                        force causes the device to use the external  synchronization signal
                        arriving on a particular interface.";
        } // END of external-command definition.

        leaf wtr-timer-status  {
            type  ipi-synce-types:synce_is_timer_running_t;
            description "Whether WTR Timer Running";
        } // END of wtr-timer-status definition.

        leaf hold-off-timer-status  {
            type  ipi-synce-types:synce_is_timer_running_t;
            description "Hold-off Timer Running";
        } // END of hold-off-timer-status definition.

        leaf link-state  {
            type  ipi-synce-types:synce_link_state_t;
            description "Synce interface link state(up/down)";
        } // END of link-state definition.

    } // END of synce-interface-state definition.
    grouping synce-external-interface-config {
        description
            "synce config external interface parameters";
        leaf external-synce-interface  {
            type  ipi-synce-types:synce_external_interface_t;
            description "";
        } // END of external-synce-interface definition.

        leaf synchronous-mode  {
            type  ipi-synce-types:synce_mode_option_t;
            default "non-synchronous";
            description "Configure the synce interface mode";
        } // END of synchronous-mode definition.

        leaf input-source-priority  {
            type  uint8 {
                 range "0..255"  {
                    description "0..255: Supported range 0 - 255";
                 }
            }
            default "255";
            description "Use this command to set an input timing source. Synchronization
                        packets are received from this source and sent to the clock selection
                        algorithm.Use the no form of this command to delete an input source.";
        } // END of input-source-priority definition.

        leaf wait-to-restore-timer  {
            type  uint8 {
                 range "0..12"  {
                    description "0..12: Supported range 0 - 12";
                 }
            }
            default "5";
            description "Use this command to set the wait-to-restore timer in minutes. The
                        wait-to-restore time ensures that a synchronization source that
                        previously failed is considered by the selection process again only if
                        it is fault free for a certain time";
        } // END of wait-to-restore-timer definition.

        leaf hold-off-timer  {
            type  uint16 {
                 range "300..1800"  {
                    description "300..1800: Supported range 300 - 1800";
                 }
            }
            default "300";
            description "Use this command to set the hold-off time in milliseconds. The
                        hold-off time ensures that short activation of signal fail is not
                        passed to the selection process";
        } // END of hold-off-timer definition.

        leaf quality-level  {
            type  string {
                length "1..1965";
                pattern "[^?' =,>|]+";
            }
            description "Use this command to set the quality level (QL) for the timing source";
        } // END of quality-level definition.

    } // END of synce-external-interface-config definition.
    grouping synce-global-top {
        description
            "synce global config parameters";
        container globals {
            description
                "synce global structure";
            container config {
                presence "Enable Synce";
                description
                    "synce global structure for config parameters";
                uses synce-global-config;
            } // END of config-container definition.
            container state {
                config false;
                description
                    "synce Operational state data";
                uses synce-global-config;
                uses synce-global-state;
            } // END of state-container definition.
        } // END of globals-container definition.
    } // END of synce-global-top definition.
    grouping synce-interface-top {
        description
            "synce interface config";
        container interfaces {
            description
                "Top level container for interfaces, including configuration and state
                        data";

            list interface {
            when " /ipi-synce:synce/ipi-synce:globals/ipi-synce:config ";
                key "name";
                description
                    "SyncE interface related operations";
                leaf name  {
                    type  leafref {
                        path  "/ipi-interface:interfaces/ipi-interface:interface/ipi-interface:name";
                    }
                    description "";
                } // END of name definition.

                container config {
                    presence "Enable Synce for an interface";
                    description
                        "SyncE interface for config parameters";
                    uses synce-interface-config;
                } // END of config-container definition.
                container state {
                    config false;
                    description
                        "SyncE interface Operational state data";
                    uses synce-interface-config;
                    uses synce-interface-state;
                } // END of state-container definition.
            } // End of interface-list
        } // END of interfaces-container definition.
    } // END of synce-interface-top definition.
    grouping synce-external-interface-top {
        description
            "synce external interface parameters";

        list external-interfaces {
        when " /ipi-synce:synce/ipi-synce:globals/ipi-synce:config ";
            key "external-synce-interface";
            description
                "External SyncE interface related operations";
            leaf external-synce-interface  {
                type  leafref {
                    path  "../config/external-synce-interface";
                }
                description "";
            } // END of external-synce-interface definition.

            container config {
                description
                    "SyncE external interface for config parameters";
                uses synce-external-interface-config;
            } // END of config-container definition.
            container state {
                config false;
                description
                    "SyncE interface Operational state data";
                uses synce-external-interface-config;
                uses synce-interface-state;
            } // END of state-container definition.
        } // End of external-interfaces-list
    } // END of synce-external-interface-top definition.

    grouping  synce-grouping {
    description
        "Synce global level information";
    container synce {
        if-feature feature-list:HAVE_SYNCED;
        description
            "Synce global level information";
        uses synce-global-top;
        uses synce-interface-top;
        uses synce-external-interface-top;
    } // END of synce-container definition.
    } // END of synce-grouping definition.

    uses synce-grouping;

    rpc clear-synce-stats {
        if-feature feature-list:HAVE_SYNCED;
        description "clear Ethernet Synchronization Messaging Chanel (ESMC) counters in all
                    interface or in specified interface";
        input  {
            leaf interface-name  {
                type string;
                mandatory true;
                description "Name of the interface to clear counters for. Specify NULL to clear
                            counters for all interfaces";
            }
        }
    }

    rpc synce-debug-on {
        if-feature feature-list:HAVE_SYNCED;
        description "turn on  transmission ,reception ,event  debugging";
        input  {
            leaf debug-options  {
                type ipi-synce-types:synce_debug_t;
                mandatory true;
                description "Debugging functions";
            }
        }
    }

    rpc synce-debug-off {
        if-feature feature-list:HAVE_SYNCED;
        description "turn off transmission ,reception ,event  debugging";
        input  {
            leaf debug-options  {
                type ipi-synce-types:synce_debug_t;
                mandatory true;
                description "Debugging functions";
            }
        }
    }

    notification synce-clock-status {
        if-feature feature-list:HAVE_SYNCED;

        description "Notify the SyncE Clock State Status.";

        leaf severity {
            type cml-data-types:cml_notif_severity_t;
            description "Notification severity level (value: CRITICAL)";
        }

        leaf eventClass {
            type cml-data-types:cml_notif_class_t;
            description "Notification event class (value: MESSAGE)";
        }

        leaf message {
            type string;
            description " alarm message notification";
        }
    }

    notification synce-clock-state-change-notify {
        if-feature feature-list:HAVE_SYNCED;

        description "Notify when there is SyncE Clock State transition.";

        leaf severity {
            type cml-data-types:cml_notif_severity_t;
            description "Notification severity level";
        }

        leaf eventClass {
            type cml-data-types:cml_notif_class_t;
            description "Notification event class (value: STATE)";
        }

        leaf previous-clock-state {
            type ipi-synce-types:synce_clock_state_t;
        description
            "The clock state of the frequency signal on the associated interface.
                    Either Locked or Free Running";
        }

        leaf current-clock-state {
            type ipi-synce-types:synce_clock_state_t;
        description
            "The clock state of the frequency signal on the associated interface.
                    Either Locked or Free Running";
        }
    }

    notification synce-clock-state-transition-locked-interface {
        if-feature feature-list:HAVE_SYNCED;

        description "Notify when there is SyncE Clock State transition and locked interface.";

        leaf severity {
            type cml-data-types:cml_notif_severity_t;
            description "Notification severity level";
        }

        leaf eventClass {
            type cml-data-types:cml_notif_class_t;
            description "Notification event class (value: STATE)";
        }

        leaf previous-clock-state {
            type ipi-synce-types:synce_clock_state_t;
        description
            "The clock state of the frequency signal on the associated interface.
                    Either Locked or Free Running";
        }

        leaf current-clock-state {
            type ipi-synce-types:synce_clock_state_t;
        description
            "The clock state of the frequency signal on the associated interface.
                    Either Locked or Free Running";
        }

        leaf locked-interface {
            type  string;
        description
            "The input interface which is locked for clock synchronization";
        }
    }

}
