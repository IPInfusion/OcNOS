/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-synce-types.yang
*
*/

module ipi-synce-types {

    yang-version 1.1;

    namespace   "http://www.ipinfusion.com/yang/ocnos/ipi-synce-types";

    prefix "ipi-synce-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-synce-types";


    revision "2020-12-15" {
        description "Change to have data-types in lower case instead of camel case";
        reference " 0.2.0.";
    }

    revision "2020-06-20" {
        description "Initial Version";
        reference " 0.1.0.";
    }



    typedef  synce_external_interface_t {
        type enumeration {
            enum gps {
                value 1;
                description "GPS interface as input-source";
            }
            enum 10mhz-in {
                value 2;
                description "10MHZ interface as input-source";
            }
            enum ptp {
                value 3;
                description "PTP interface as input-source";
            }
            enum bits-t1 {
                value 4;
                description "BITS-T1 interface as input-source";
            }
            enum bits-e1 {
                value 5;
                description "BITS-E1 interface as input-source";
            }
            enum 2mhz-in {
                value 6;
                description "2mhz interface as input-source";
            }
            enum bits-t1-1 {
                value 7;
                description "BITS-T1-1 interface as input-source";
            }
            enum bits-t1-2 {
                value 8;
                description "BITS-T1-2 interface as input-source";
            }
            enum bits-t1-3 {
                value 9;
                description "BITS-T1-3 interface as input-source";
            }
            enum bits-e1-1 {
                value 10;
                description "BITS-E1-1 interface as input-source";
            }
            enum bits-e1-2 {
                value 11;
                description "BITS-E1-2 interface as input-source";
            }
            enum bits-e1-3 {
                value 12;
                description "BITS-E1-3 interface as input-source";
            }
        }
        description "type definition for SYNCE_EXTERNAL_INTERFACE_T";
    }

    typedef  synce_sync_option_t {
        type enumeration {
            enum 1 {
                value 1;
                description "Networks optimized for the 2048 kbit/s hierarchy ";
            }
            enum 2 {
                value 2;
                description "Networks optimized for the 1544 kbit/s hierarchy that includes the rates 1544 kbit/s 6312 kbit/s and 44 736 kbit/s ";
            }
        }
        description "type definition for SYNCE_SYNC_OPTION_T";
    }

    typedef  synce_clk_selection_mode_t {
        type enumeration {
            enum ql-enabled {
                value 1;
                description "Use the quality level as a criteria when selecting a clock ";
            }
            enum ql-disabled {
                value 2;
                description "Do not use the quality level as a criteria when selecting a clock";
            }
        }
        description "type definition for SYNCE_CLK_SELECTION_MODE_T";
    }

    typedef  synce_autoneg_mode_t {
        type enumeration {
            enum master {
                value 1;
                description "Configure Base-T mode to master";
            }
            enum slave {
                value 2;
                description "Configure Base-T mode to slave";
            }
        }
        description "type definition for SYNCE_AUTONEG_MODE_T";
    }

    typedef  synce_mode_option_t {
        type enumeration {
            enum synchronous {
                value 1;
                description "Configure the interface to synchronous mode";
            }
            enum non-synchronous {
                value 2;
                description "Configure the interface to non-synchronous mode";
            }
        }
        description "type definition for SYNCE_MODE_OPTION_T";
    }

    typedef  synce_source_select_t {
        type enumeration {
            enum force {
                value 1;
                description "Forcefully select a synchronization source";
            }
            enum manual {
                value 2;
                description "manually select a synchronization source";
            }
        }
        description "type definition for SYNCE_SOURCE_SELECT_T";
    }

    typedef  synce_debug_t {
        type bits {
            bit event {
                position 0;
                description "event debugs";
            }
            bit recvd {
                position 1;
                description "rx debugs";
            }
            bit trans {
                position 2;
                description "tx debugs";
            }
        }
        description "type definition for SYNCE_DEBUG_T";
    }

    typedef  synce_is_src_selected_t {
        type enumeration {
            enum No {
                value 0;
                description "Src is not seleceted";
            }
            enum Yes {
                value 1;
                description "Src is seleceted";
            }
        }
        description "type definition for SYNCE_IS_SRC_SELECTED_T";
    }

    typedef  synce_is_sf_t {
        type enumeration {
            enum No {
                value 0;
                description "Interface is not in Signal Fail condition";
            }
            enum Yes {
                value 1;
                description "Interface is in Signal Fail condition";
            }
        }
        description "type definition for SYNCE_IS_SF_T";
    }

    typedef  synce_external_cmds_t {
        type enumeration {
            enum None {
                value 0;
                description "No external commands configured";
            }
            enum Lockout {
                value 1;
                description "Lockout external command configured";
            }
            enum Force {
                value 2;
                description "Force switch external command configured";
            }
            enum Manual {
                value 3;
                description "Manual switch external command configured";
            }
        }
        description "type definition for SYNCE_EXTERNAL_CMDS_T";
    }

    typedef  synce_is_timer_running_t {
        type enumeration {
            enum Not-Running {
                value 0;
                description "Interface is not in Signal Fail condition";
            }
            enum Running {
                value 1;
                description "Interface is in Signal Fail condition";
            }
        }
        description "type definition for SYNCE_IS_TIMER_RUNNING_T";
    }

    typedef  synce_clock_state_t {
        type enumeration {
            enum Not-Applicable {
                value 0;
                description "N/A";
            }
            enum Free-run {
                value 1;
                description "Clk is in Free-run state";
            }
            enum Holdover {
                value 2;
                description "Clk is in Holdover state";
            }
            enum Locked {
                value 3;
                description "Clk is in Locked state";
            }
            enum Acquiring {
                value 4;
                description "Clk is in Acquiring state";
            }
        }
        description "type definition for SYNCE_CLOCK_STATE_T";
    }

    typedef  synce_esmc_state_t {
        type enumeration {
            enum Idle {
                value 0;
                description "ESMC state is idle";
            }
            enum Start {
                value 1;
                description "ESMC state is Start";
            }
            enum OK {
                value 2;
                description "ESMC state is OK";
            }
            enum Failed {
                value 3;
                description "ESMC state is Failed";
            }
            enum Not-Applicable {
                value 4;
                description "ESMC state Not-Applicable";
            }
        }
        description "type definition for SYNCE_ESMC_STATE_T";
    }

    typedef  synce_link_state_t {
        type enumeration {
            enum up {
                value 1;
                description "Synce Interface is up";
            }
            enum down {
                value 2;
                description "Synce Interface is down";
            }
        }
        description "type definition for SYNCE_LINK_STATE_T";
    }

    typedef  synce_uptime_t {
        type string;
        description "type definition for SYNCE_UPTIME_T";
    }

}
