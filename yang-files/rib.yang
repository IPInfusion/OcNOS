/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : rib.yang
*
*/

submodule rib {

    belongs-to  ZebOS { prefix ZebOS; }
    include interface;
    include vrf;


    import cml_data_types {
        prefix cml_data_types;
    }

    import feature_list {
        prefix feature_list;
    }


    revision "2017-02-27" {
        description "Added implicit delete tags.";
    }

    revision "2016-09-15" {
        description "Revisied on 2016-09-15.";
    }

    revision "2016-01-03" {
        description "Added implicit delete tags..";
    }



    grouping ribInterface-grouping {
        list ribInterface {
             
            description
                "RIB BFD interface related operations";

            config true;
            key "ifName";

            
            leaf ifName  {
                type  cml_data_types:CML_STRING_T {
                    length "0..255";
                }
            } // END of ifName definition.

            leaf staticBfd  {
                if-feature feature_list:HAVE_BFD;
                type  cml_data_types:CML_BOOL_T;  
            } // END of staticBfd definition.

            leaf staticBfdDisable  {
                if-feature feature_list:HAVE_BFD;
                type  cml_data_types:CML_BOOL_T;  
            } // END of staticBfdDisable definition.

            leaf ipv6StaticBfd  {
                if-feature feature_list:HAVE_IPV6;
                if-feature feature_list:HAVE_BFD;
                type  cml_data_types:CML_BOOL_T;  
            } // END of ipv6StaticBfd definition.

            leaf ipv6StaticBfdDisable  {
                if-feature feature_list:HAVE_IPV6;
                if-feature feature_list:HAVE_BFD;
                type  cml_data_types:CML_BOOL_T;  
            } // END of ipv6StaticBfdDisable definition.

        } // End of ribInterface-list
    } // END of ribInterface-grouping definition.
    grouping ribRuntimeGrp {
                leaf subType  {
            type  cml_data_types:CML_STRING_T {
                length "0..255";
            }
            config false;
        } // END of subType definition.

        leaf distance  {
            type  cml_data_types:CML_UINT8_T;  
            config false;
        } // END of distance definition.

        leaf metric  {
            type  cml_data_types:CML_UINT8_T;  
            config false;
        } // END of metric definition.

        leaf blackHole  {
            type  cml_data_types:CML_STRING_T {
                length "0..255";
            }
            config false;
        } // END of blackHole definition.

        leaf ribUptime  {
            type  cml_data_types:CML_STRING_T {
                length "0..255";
            }
            config false;
        } // END of ribUptime definition.

        leaf ribFibStatus  {
            type  cml_data_types:CML_STRING_T {
                length "0..255";
            }
            config false;
        } // END of ribFibStatus definition.


        list nextHopRunTime {
             
            description
                "nextHopRunTime";

            config false;
            key "gwAddrRuntime";

            
            leaf gwAddrRuntime  {
                type  cml_data_types:CML_IPV4_ADDR_T;  
            } // END of gwAddrRuntime definition.

            leaf gwLastResort  {
                type  cml_data_types:CML_IPV4_ADDR_T;  
            } // END of gwLastResort definition.

            leaf nexthopIfName  {
                type  cml_data_types:CML_STRING_T {
                    length "0..255";
                }
            } // END of nexthopIfName definition.

            leaf nexthopIfIndex  {
                type  cml_data_types:CML_STRING_T {
                    length "0..255";
                }
            } // END of nexthopIfIndex definition.

            leaf nexthopFlagActive  {
                type  cml_data_types:CML_STRING_T {
                    length "0..255";
                }
            } // END of nexthopFlagActive definition.

            leaf nexthopFibStatus  {
                type  cml_data_types:CML_STRING_T {
                    length "0..255";
                }
            } // END of nexthopFibStatus definition.

        } // End of nextHopRunTime-list
    } // END of ribRuntimeGrp definition.
    grouping ribVrfAfiGrp {
                leaf totalRoutes  {
            type  cml_data_types:CML_UINT32_T;  
            config false;
        } // END of totalRoutes definition.

        leaf totalPaths  {
            type  cml_data_types:CML_UINT32_T;  
            config false;
        } // END of totalPaths definition.

        leaf countFib  {
            type  cml_data_types:CML_UINT32_T;  
            config false;
        } // END of countFib definition.

        leaf ecmpRoutes  {
            type  cml_data_types:CML_UINT32_T;  
            config false;
        } // END of ecmpRoutes definition.

        leaf ecmpPaths  {
            type  cml_data_types:CML_UINT32_T;  
            config false;
        } // END of ecmpPaths definition.

        leaf ecmpPathCntr  {
            type  cml_data_types:CML_STRING_T {
                length "0..255";
            }
            config false;
        } // END of ecmpPathCntr definition.


        list routeSource {
             
            description
                "routeSource";

            config false;
            key "routeType";

            
            leaf routeType  {
                type  cml_data_types:CML_STRING_T {
                    length "0..255";
                }
            } // END of routeType definition.

            leaf routeTypeCount  {
                type  cml_data_types:CML_UINT32_T;  
            } // END of routeTypeCount definition.

        } // End of routeSource-list
    } // END of ribVrfAfiGrp definition.
    grouping ribAttr {
                leaf distValue  {
            type  cml_data_types:CML_INT32_T {
                 range "1..255";
            }
        } // END of distValue definition.

        leaf tagVal  {
            type  cml_data_types:CML_UINT32_T {
                 range "0..4294967295";
            }
            default "0";
        } // END of tagVal definition.

        leaf description  {
            type  cml_data_types:CML_STRING_T {
                length "0..255";
            }
        } // END of description definition.

    } // END of ribAttr definition.

    grouping  rib-grouping {
    container rib {
                config true;

        description
            "rib";

        leaf fibRetain  {
            if-feature feature_list:HAVE_L3;
            type  cml_data_types:CML_FIB_RETAIN_T;  
            default "60";
        } // END of fibRetain definition.

        leaf multipathNum  {
            if-feature feature_list:HAVE_MULTIPATH;
            type  cml_data_types:CML_UINT8_T {
                 range "1..64";
            }
            default "1";
        } // END of multipathNum definition.

        leaf maxStaticRoutes  {
            type  cml_data_types:CML_UINT32_T {
                 range "1..4294967294";
            }
            default "4294967294";
        } // END of maxStaticRoutes definition.

        leaf maxFibRoutes  {
            type  cml_data_types:CML_UINT32_T {
                 range "1..16384";
            }
        } // END of maxFibRoutes definition.

        leaf debugTypeExit  {
            type  cml_data_types:CML_RIB_DEBUG_EXIT_TYPE_T;  
            default "all";
        } // END of debugTypeExit definition.

        leaf debugIpExit  {
            type  cml_data_types:CML_RIB_DEBUG_ROUTING_TYPE_T;  
        } // END of debugIpExit definition.

        leaf debugIpv6Exit  {
            type  cml_data_types:CML_RIB_DEBUG_ROUTING_TYPE_T;  
        } // END of debugIpv6Exit definition.

        leaf unDebug  {
            type  cml_data_types:CML_RIB_UNDEBUG_TYPE_T;  
            default "all";
        } // END of unDebug definition.

        leaf debugType  {
            type  cml_data_types:CML_RIB_DEBUG_TYPE_T;  
            default "all";
        } // END of debugType definition.

        leaf debugIp  {
            type  cml_data_types:CML_RIB_DEBUG_ROUTING_TYPE_T;  
        } // END of debugIp definition.

        leaf debugIpv6  {
            type  cml_data_types:CML_RIB_DEBUG_ROUTING_TYPE_T;  
        } // END of debugIpv6 definition.


        list ribIpv4 {
             
            description
                "ribIpv4";

            config true;
            key "destPrefix";

            
            leaf destPrefix  {
                type  cml_data_types:CML_IPV4_PREFIX_T;  
            } // END of destPrefix definition.


            list ribStaticGwAddr {
                 
                description
                    "ribStaticGwAddr";

                config true;
                key "gwAddr";

                
                leaf gwAddr  {
                    type  cml_data_types:CML_IPV4_ADDR_T;  
                } // END of gwAddr definition.

                container ribBfd {
                                        config true;

                    description
                        "ribBfd";

                    leaf ribStaticBfd  {
                        type  cml_data_types:CML_BOOL_T;  
                    } // END of ribStaticBfd definition.

                    leaf ribStaticBfdDisable  {
                        type  cml_data_types:CML_BOOL_T;  
                    } // END of ribStaticBfdDisable definition.

                } // END of ribBfd-container definition.
                uses ribAttr;
            } // End of ribStaticGwAddr-list

            list ribStaticIfName {
                 
                description
                    "ribStaticIfName";

                config true;
                key "gwIfName";

                
                leaf gwIfName  {
                    type  cml_data_types:CML_STRING_T {
                        length "0..255";
                    }
                } // END of gwIfName definition.

                uses ribAttr;
            } // End of ribStaticIfName-list

            list ribRuntime {
                 
                description
                    "ribRuntime";

                config false;
                key "type";

                
                leaf type  {
                    type  cml_data_types:CML_STRING_T {
                        length "0..255";
                    }
                } // END of type definition.

                uses ribRuntimeGrp;
            } // End of ribRuntime-list
        } // End of ribIpv4-list

        list ribIpv4Vrf {
                         if-feature feature_list:HAVE_VRF;

            description
                "ribIpv4Vrf";

            config true;
            key "vrfName";

            
            leaf vrfName  {
                type  cml_data_types:CML_STRING_T {
                    length "0..255";
                }
            } // END of vrfName definition.


            list vrfDestPrefix {
                 
                description
                    "vrfDestPrefix";

                config true;
                key "destVrfPrefix";

                
                leaf destVrfPrefix  {
                    type  cml_data_types:CML_IPV4_PREFIX_T;  
                } // END of destVrfPrefix definition.


                list vrfIfName {
                     
                    description
                        "vrfIfName";

                    config true;
                    key "gwVrfIfName";

                    
                    leaf gwVrfIfName  {
                        type  cml_data_types:CML_STRING_T {
                            length "0..255";
                        }
                    } // END of gwVrfIfName definition.

                    uses ribAttr;
                } // End of vrfIfName-list

                list vrfGwAddr {
                     
                    description
                        "vrfGwAddr";

                    config true;
                    key "vrfGwAddr";

                    
                    leaf vrfGwAddr  {
                        type  cml_data_types:CML_IPV4_ADDR_T;  
                    } // END of vrfGwAddr definition.


                    list vrfGwAddrIfName {
                         
                        description
                            "vrfGwAddrIfName";

                        config true;
                        key "gwVrfIfNameAddr";

                        
                        leaf gwVrfIfNameAddr  {
                            type  cml_data_types:CML_STRING_T {
                                length "0..255";
                            }
                        } // END of gwVrfIfNameAddr definition.

                        uses ribAttr;
                    } // End of vrfGwAddrIfName-list
                } // End of vrfGwAddr-list

                list ribRuntime {
                     
                    description
                        "ribRuntime";

                    config false;
                    key "type";

                    
                    leaf type  {
                        type  cml_data_types:CML_STRING_T {
                            length "0..255";
                        }
                    } // END of type definition.

                    uses ribRuntimeGrp;
                } // End of ribRuntime-list
            } // End of vrfDestPrefix-list
            container ribIpv4VrfAfi {
                                config false;

                description
                    "ribIpv4VrfAfi";

                uses ribVrfAfiGrp;
            } // END of ribIpv4VrfAfi-container definition.
        } // End of ribIpv4Vrf-list

        list ribIpv6 {
                         if-feature feature_list:HAVE_IPV6;

            description
                "ribIpv6";

            config true;
            key "ipv6DestPrefix";

            
            leaf ipv6DestPrefix  {
                type  cml_data_types:CML_IPV6_PREFIX_T;  
            } // END of ipv6DestPrefix definition.


            list ribIpv6GwAddr {
                 
                description
                    "ribIpv6GwAddr";

                config true;
                key "ipv6GwAddr";

                
                leaf ipv6GwAddr  {
                    type  cml_data_types:CML_IPV6_ADDR_T;  
                } // END of ipv6GwAddr definition.

                leaf ipv6DistVal  {
                    type  cml_data_types:CML_INT32_T {
                         range "1..255";
                    }
                } // END of ipv6DistVal definition.

                leaf ribIpv6StaticBfd  {
                    type  cml_data_types:CML_BOOL_T;  
                } // END of ribIpv6StaticBfd definition.

                leaf ribIpv6StaticBfdDisable  {
                    type  cml_data_types:CML_BOOL_T;  
                } // END of ribIpv6StaticBfdDisable definition.

            } // End of ribIpv6GwAddr-list

            list ribIpv6GwIfName {
                 
                description
                    "ribIpv6GwIfName";

                config true;
                key "ipv6GwIfName";

                
                leaf ipv6GwIfName  {
                    type  cml_data_types:CML_STRING_T {
                        length "0..255";
                    }
                } // END of ipv6GwIfName definition.

                leaf ipv6DistVal  {
                    type  cml_data_types:CML_INT32_T {
                         range "1..255";
                    }
                } // END of ipv6DistVal definition.

            } // End of ribIpv6GwIfName-list

            list ribIpv6GwAddrIfName {
                 
                description
                    "ribIpv6GwAddrIfName";

                config true;
                key "ipv6GateWayAddr";

                
                leaf ipv6GateWayAddr  {
                    type  cml_data_types:CML_IPV6_ADDR_T;  
                } // END of ipv6GateWayAddr definition.


                list ribIpv6GwIfName {
                     
                    description
                        "ribIpv6GwIfName";

                    config true;
                    key "ipv6GateWayIfName";

                    
                    leaf ipv6GateWayIfName  {
                        type  cml_data_types:CML_STRING_T {
                            length "0..255";
                        }
                    } // END of ipv6GateWayIfName definition.

                    leaf distValgwAddr  {
                        type  cml_data_types:CML_INT32_T {
                             range "1..255";
                        }
                    } // END of distValgwAddr definition.

                } // End of ribIpv6GwIfName-list
            } // End of ribIpv6GwAddrIfName-list

            list ribRuntime {
                 
                description
                    "ribRuntime";

                config false;
                key "type";

                
                leaf type  {
                    type  cml_data_types:CML_STRING_T {
                        length "0..255";
                    }
                } // END of type definition.

                uses ribRuntimeGrp;
            } // End of ribRuntime-list
        } // End of ribIpv6-list

        list ribIpv6Vrf {
                         if-feature feature_list:HAVE_VRF;

            description
                "ribIpv6Vrf";

            config true;
            key "vrfName";

            
            leaf vrfName  {
                type  cml_data_types:CML_STRING_T {
                    length "0..255";
                }
            } // END of vrfName definition.


            list vrfDestPrefix {
                                 if-feature feature_list:HAVE_IPV6;

                description
                    "vrfDestPrefix";

                config true;
                key "ipv6VrfDestPrefix";

                
                leaf ipv6VrfDestPrefix  {
                    type  cml_data_types:CML_IPV6_PREFIX_T;  
                } // END of ipv6VrfDestPrefix definition.


                list vrfIpv6GwAddr {
                     
                    description
                        "vrfIpv6GwAddr";

                    config true;
                    key "ipv6VrfGwAddr";

                    
                    leaf ipv6VrfGwAddr  {
                        type  cml_data_types:CML_IPV6_ADDR_T;  
                    } // END of ipv6VrfGwAddr definition.


                    list vrfGwAddrIfName {
                         
                        description
                            "vrfGwAddrIfName";

                        config true;
                        key "ipv6VrfgwIfName";

                        
                        leaf ipv6VrfgwIfName  {
                            type  cml_data_types:CML_STRING_T {
                                length "0..255";
                            }
                        } // END of ipv6VrfgwIfName definition.

                    } // End of vrfGwAddrIfName-list
                } // End of vrfIpv6GwAddr-list

                list ribRuntime {
                     
                    description
                        "ribRuntime";

                    config false;
                    key "type";

                    
                    leaf type  {
                        type  cml_data_types:CML_STRING_T {
                            length "0..255";
                        }
                    } // END of type definition.

                    uses ribRuntimeGrp;
                } // End of ribRuntime-list
            } // End of vrfDestPrefix-list
            container ribIpv6VrfAfi {
                                config false;

                description
                    "ribIpv6VrfAfi";

                uses ribVrfAfiGrp;
            } // END of ribIpv6VrfAfi-container definition.
        } // End of ribIpv6Vrf-list

        list ribMrouteVRF {
                         if-feature feature_list:HAVE_VRF;

            description
                "ribMrouteVRF";

            config true;
            key "vrfName";

            
            leaf vrfName  {
                type  cml_data_types:CML_STRING_T {
                    length "0..255";
                }
            } // END of vrfName definition.


            list ribMroute {
                 
                description
                    "ribMroute";

                config true;
                key "srcPrfix";

                
                leaf srcPrfix  {
                    type  cml_data_types:CML_IPV4_PREFIX_T;  
                } // END of srcPrfix definition.


                list mrouteProtoType {
                     
                    description
                        "mrouteProtoType";

                    config true;
                    key "mrouteIpv4Proto";

                    
                    leaf mrouteIpv4Proto  {
                        type  cml_data_types:CML_MROUTE_ROUTETYPE_T;  
                    } // END of mrouteIpv4Proto definition.

                    leaf rpfRoute  {
                        type  cml_data_types:CML_IPV4_ADDR_T;  
                    } // END of rpfRoute definition.

                    leaf adminDist  {
                        type  cml_data_types:CML_INT32_T {
                             range "1..255";
                        }
                    } // END of adminDist definition.

                } // End of mrouteProtoType-list
            } // End of ribMroute-list
        } // End of ribMrouteVRF-list

        list ribIpv6MrouteVRF {
                         if-feature feature_list:HAVE_VRF;

            description
                "ribIpv6MrouteVRF";

            config true;
            key "vrfName";

            
            leaf vrfName  {
                type  cml_data_types:CML_STRING_T {
                    length "0..255";
                }
            } // END of vrfName definition.


            list ribMrouteIpv6 {
                                 if-feature feature_list:HAVE_IPV6;

                description
                    "ribMrouteIpv6";

                config true;
                key "srcPrfixIpv6";

                
                leaf srcPrfixIpv6  {
                    type  cml_data_types:CML_IPV6_PREFIX_T;  
                } // END of srcPrfixIpv6 definition.


                list mrouteIpv6ProtoType {
                     
                    description
                        "mrouteIpv6ProtoType";

                    config true;
                    key "mrouteIpv6Proto";

                    
                    leaf mrouteIpv6Proto  {
                        type  cml_data_types:CML_MROUTE_ROUTETYPE_T;  
                    } // END of mrouteIpv6Proto definition.

                    leaf gwIpv6Mroute  {
                        type  cml_data_types:CML_MROUTE_GW_ADDR_T;  
                    } // END of gwIpv6Mroute definition.

                    leaf adminDist  {
                        type  cml_data_types:CML_INT32_T {
                             range "1..255";
                        }
                    } // END of adminDist definition.


                    list ipv6MrouteGwAddr {
                         
                        description
                            "ipv6MrouteGwAddr";

                        config true;
                        key "mrouteIpv6gwAddr";

                        
                        leaf mrouteIpv6gwAddr  {
                            type  cml_data_types:CML_IPV6_ADDR_T;  
                        } // END of mrouteIpv6gwAddr definition.


                        list ipv6MrouteGwIfName {
                             
                            description
                                "ipv6MrouteGwIfName";

                            config true;
                            key "mrouteIpv6gwIfName";

                            
                            leaf mrouteIpv6gwIfName  {
                                type  cml_data_types:CML_STRING_T {
                                    length "0..255";
                                }
                            } // END of mrouteIpv6gwIfName definition.

                            leaf adminDist  {
                                type  cml_data_types:CML_INT32_T {
                                     range "1..255";
                                }
                            } // END of adminDist definition.

                        } // End of ipv6MrouteGwIfName-list
                    } // End of ipv6MrouteGwAddr-list
                } // End of mrouteIpv6ProtoType-list
            } // End of ribMrouteIpv6-list
        } // End of ribIpv6MrouteVRF-list
        container ribAfi {
                        config false;

            description
                "ribAfi";

            uses ribVrfAfiGrp;
        } // END of ribAfi-container definition.
        container ribIpv6Afi {
                        config false;

            description
                "ribIpv6Afi";

            uses ribVrfAfiGrp;
        } // END of ribIpv6Afi-container definition.
        container ribVrf {
                        config true;

            description
                "ribVrf";

            leaf ribVrfConfBfdIpv4  {
                type  cml_data_types:CML_BOOL_T;  
            } // END of ribVrfConfBfdIpv4 definition.

            leaf ribVrfConfBfdIpv6  {
                type  cml_data_types:CML_BOOL_T;  
            } // END of ribVrfConfBfdIpv6 definition.

        } // END of ribVrf-container definition.
    } // END of rib-container definition.
    } // END of rib-container definition.


}
