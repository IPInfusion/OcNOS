/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : cmm.yang
*
*/

submodule cmm {

    belongs-to  ZebOS { prefix ZebOS; }
    include interface;


    import cml_data_types {
        prefix cml_data_types;
    }

    description
        "Chassis Monitoring Module";


    revision "2017-02-03" {
        description "Notification changes.";
    }

    revision "2017-01-29" {
        description "Initial Draft Version.";
    }



    grouping dmmMonitorPort-grouping {
        list dmmMonitorPort {
             
            description
                "DMM Monitor Port enable";

            config true;
            key "ifName";

            
            leaf ifName  {
                type  cml_data_types:CML_STRING_T {
                    length "0..255";
                }
            } // END of ifName definition.

            leaf monitorPort  {
                type  cml_data_types:CML_BOOL_T;  
                description "ddm monitor";
            } // END of monitorPort definition.

        } // End of dmmMonitorPort-list
    } // END of dmmMonitorPort-grouping definition.


    grouping cmmStackUnitTable-grouping {
        list cmmStackUnitTable {
             
            description
                "list of stack units configured in the chassis";

            config false;
            
            leaf cmmStackUnitIndex  {
                type  cml_data_types:CML_INT32_T;  
                description "The unique index for this entry.Refer to the object cmmStackUnitIndexNext.";
            } // END of cmmStackUnitIndex definition.

            leaf cmmStackUnitModelName  {
                type  cml_data_types:CML_STRING_T {
                    length "0..255";
                }
                description "The plugged-in model ID for this unit.";
            } // END of cmmStackUnitModelName definition.

            leaf cmmStackUnitSerialNumber  {
                type  cml_data_types:CML_STRING_T {
                    length "0..255";
                }
                description "The unit's serial number.";
            } // END of cmmStackUnitSerialNumber definition.

            leaf cmmStackUnitUpTime  {
                type  cml_data_types:CML_STRING_T {
                    length "0..255";
                }
                description "The system up time of the unit.";
            } // END of cmmStackUnitUpTime definition.

            leaf cmmStackUnitMfgDate  {
                type  cml_data_types:CML_STRING_T {
                    length "0..255";
                }
                description "The date the unit is manufactured.";
            } // END of cmmStackUnitMfgDate definition.

            leaf cmmStackUnitMacAddress  {
                type  cml_data_types:CML_STRING_T {
                    length "0..255";
                }
                description "A 6-octet MAC Address assigned to tis unit.";
            } // END of cmmStackUnitMacAddress definition.

            leaf cmmStackUnitPartNum  {
                type  cml_data_types:CML_STRING_T {
                    length "0..255";
                }
                description "The unit part number";
            } // END of cmmStackUnitPartNum definition.

            leaf cmmStackLabelRevision  {
                type  cml_data_types:CML_STRING_T {
                    length "0..255";
                }
                description "The unit's label Revesion";
            } // END of cmmStackLabelRevision definition.

            leaf cmmStackUnitCountryCode  {
                type  cml_data_types:CML_STRING_T {
                    length "0..255";
                }
                description "The unit manufacturer's country code";
            } // END of cmmStackUnitCountryCode definition.

            leaf cmmStackUnitNumFanTrays  {
                type  cml_data_types:CML_INT32_T;  
                description "The number of fan trays on the unit.";
            } // END of cmmStackUnitNumFanTrays definition.

            leaf cmmStackUnitNumPowerSupplies  {
                type  cml_data_types:CML_INT32_T;  
                description "The number of power supplies available to the unit.";
            } // END of cmmStackUnitNumPowerSupplies definition.

            leaf cmmStackUnitNumPluggableModules  {
                type  cml_data_types:CML_INT32_T;  
                description "The number of pluggable modules in the stack.";
            } // END of cmmStackUnitNumPluggableModules definition.

            leaf cmmStackUnitNumFastEtherPorts  {
                type  cml_data_types:CML_INT32_T;  
                description "The number of 100M Ethernet/802.3 interfaces in this unit.";
            } // END of cmmStackUnitNumFastEtherPorts definition.

            leaf cmmStackUnitNumGigEtherPorts  {
                type  cml_data_types:CML_INT32_T;  
                description "The number of 1G Ethernet/802.3 interfaces in this unit.";
            } // END of cmmStackUnitNumGigEtherPorts definition.

            leaf cmmStackUnitNum10GigEtherPorts  {
                type  cml_data_types:CML_INT32_T;  
                description "The number of 10G Ethernet/802.3 interfaces in this unit.";
            } // END of cmmStackUnitNum10GigEtherPorts definition.

            leaf cmmStackUnitNum25GigEtherPorts  {
                type  cml_data_types:CML_INT32_T;  
                description "The number of 25G Ethernet/802.3 interfaces in this unit.";
            } // END of cmmStackUnitNum25GigEtherPorts definition.

            leaf cmmStackUnitNum40GigEtherPorts  {
                type  cml_data_types:CML_INT32_T;  
                description "The number of 40G Ethernet/802.3 interfaces in this unit.";
            } // END of cmmStackUnitNum40GigEtherPorts definition.

            leaf cmmStackUnitNum50GigEtherPorts  {
                type  cml_data_types:CML_INT32_T;  
                description "The number of 50G Ethernet/802.3 interfaces in this unit.";
            } // END of cmmStackUnitNum50GigEtherPorts definition.

            leaf cmmStackUnitNum100GigEtherPorts  {
                type  cml_data_types:CML_INT32_T;  
                description "The number of 100G Ethernet/802.3 interfaces in this unit.";
            } // END of cmmStackUnitNum100GigEtherPorts definition.

            leaf cmmStackUnitServiceTag  {
                type  cml_data_types:CML_STRING_T {
                    length "0..255";
                }
                description "The unit's service tag.";
            } // END of cmmStackUnitServiceTag definition.

            leaf cmmStackPlatformName  {
                type  cml_data_types:CML_STRING_T {
                    length "0..255";
                }
                description "The unit's Platform Name.";
            } // END of cmmStackPlatformName definition.

            leaf cmmStackOnieVersion  {
                type  cml_data_types:CML_STRING_T {
                    length "0..255";
                }
                description "The unit's ONIE Version.";
            } // END of cmmStackOnieVersion definition.

            leaf cmmStackMfg  {
                type  cml_data_types:CML_STRING_T {
                    length "0..255";
                }
                description "The unit's Manufacturer Name.";
            } // END of cmmStackMfg definition.

            leaf cmmStackVendorName  {
                type  cml_data_types:CML_STRING_T {
                    length "0..255";
                }
                description "The unit's Vendor Name.";
            } // END of cmmStackVendorName definition.

            leaf cmmStackDiagVersion  {
                type  cml_data_types:CML_STRING_T {
                    length "0..255";
                }
                description "The unit's Diagnostic Version.";
            } // END of cmmStackDiagVersion definition.

            leaf cmmStackCrc32  {
                type  cml_data_types:CML_STRING_T {
                    length "0..255";
                }
                description "The unit's Cyclic Redundancy Check 32 Bit value.";
            } // END of cmmStackCrc32 definition.


            list cmmSysPortTable {
                 
                description
                    "list of power supply resident in the  chassis";

                config false;
                key "cmmSysPortIndex";

                
                leaf cmmSysPortIndex  {
                    type  cml_data_types:CML_UINT32_T;  
                    description "A unique index for each slot within the unit.";
                } // END of cmmSysPortIndex definition.

                leaf cmmSysPortType  {
                    type  cml_data_types:CML_STRING_T {
                        length "0..255";
                    }
                    description "The type of port in the unit.";
                } // END of cmmSysPortType definition.

                leaf cmmSysidentifier  {
                    type  cml_data_types:CML_STRING_T {
                        length "0..255";
                    }
                    description "Type of transceiver";
                } // END of cmmSysidentifier definition.

                leaf cmmSysextendedidentifier  {
                    type  cml_data_types:CML_STRING_T {
                        length "0..255";
                    }
                    description "Extended identifier of type of transceiver";
                } // END of cmmSysextendedidentifier definition.

                leaf cmmSysconnectortype  {
                    type  cml_data_types:CML_STRING_T {
                        length "0..255";
                    }
                    description "Code for connector type";
                } // END of cmmSysconnectortype definition.

                leaf cmmSystransceivercode  {
                    type  cml_data_types:CML_STRING_T {
                        length "0..255";
                    }
                    description "Code for electronic or optical compatibility";
                } // END of cmmSystransceivercode definition.

                leaf cmmSysencoding  {
                    type  cml_data_types:CML_STRING_T {
                        length "0..255";
                    }
                    description "Code for high speed serial encoding algorithm";
                } // END of cmmSysencoding definition.

                leaf cmmSysnominalbitrate  {
                    type  cml_data_types:CML_INT32_T;  
                    description "Nominal signalling rate, units of 100MBd.";
                } // END of cmmSysnominalbitrate definition.

                leaf cmmSyslengthkmtrs  {
                    type  cml_data_types:CML_INT32_T;  
                    description "Link length supported for single mode fiber, units of km";
                } // END of cmmSyslengthkmtrs definition.

                leaf cmmSyslengthmtrs  {
                    type  cml_data_types:CML_INT32_T;  
                    description "Link length supported for single mode fiber, units of 100 m";
                } // END of cmmSyslengthmtrs definition.

                leaf cmmSyslengthom1  {
                    type  cml_data_types:CML_INT32_T;  
                    description "Link length supported for 62.5 um OM1 fiber, units of 10 m";
                } // END of cmmSyslengthom1 definition.

                leaf cmmSyslengthom2  {
                    type  cml_data_types:CML_INT32_T;  
                    description "Link length supported for 50 um OM2 fiber, units of 10 m";
                } // END of cmmSyslengthom2 definition.

                leaf cmmSyslengthom3  {
                    type  cml_data_types:CML_INT32_T;  
                    description "Link length supported for 50 um OM3 fiber, units of 10 m";
                } // END of cmmSyslengthom3 definition.

                leaf cmmSysvendorname  {
                    type  cml_data_types:CML_STRING_T {
                        length "0..255";
                    }
                    description "SFP vendor name";
                } // END of cmmSysvendorname definition.

                leaf cmmSysvendoroui  {
                    type  cml_data_types:CML_STRING_T {
                        length "0..255";
                    }
                    description "SFP vendor IEEE company ID";
                } // END of cmmSysvendoroui definition.

                leaf cmmSysvendorpartnumber  {
                    type  cml_data_types:CML_STRING_T {
                        length "0..255";
                    }
                    description "Part number provided by SFP vendor";
                } // END of cmmSysvendorpartnumber definition.

                leaf cmmSysvendorrevision  {
                    type  cml_data_types:CML_STRING_T {
                        length "0..255";
                    }
                    description "Revision level for part number provided by vendor";
                } // END of cmmSysvendorrevision definition.

                leaf cmmSyscheckcode  {
                    type  cml_data_types:CML_STRING_T {
                        length "0..255";
                    }
                    description "Check code for Base ID Fields";
                } // END of cmmSyscheckcode definition.

                leaf cmmSysbitratemax  {
                    type  cml_data_types:CML_INT32_T;  
                    description "Upper bit rate margin, units of %";
                } // END of cmmSysbitratemax definition.

                leaf cmmSysbitratemin  {
                    type  cml_data_types:CML_INT32_T;  
                    description "Lower bit rate margin, units of %";
                } // END of cmmSysbitratemin definition.

                leaf cmmSysvendorserialnumber  {
                    type  cml_data_types:CML_STRING_T {
                        length "0..255";
                    }
                    description "Serial number provided by vendor";
                } // END of cmmSysvendorserialnumber definition.

                leaf cmmSysdatecode  {
                    type  cml_data_types:CML_STRING_T {
                        length "0..255";
                    }
                    description "Vendor's manufacturing date code";
                } // END of cmmSysdatecode definition.

                leaf cmmSysddmtype  {
                    type  cml_data_types:CML_STRING_T {
                        length "0..255";
                    }
                    description "Indicates which type of diagnostic monitoring is implemented";
                } // END of cmmSysddmtype definition.

                leaf cmmSyscheckcodeextended  {
                    type  cml_data_types:CML_STRING_T {
                        length "0..255";
                    }
                    description "Check code for the Extended ID Fields";
                } // END of cmmSyscheckcodeextended definition.

                leaf cmmSysrxpower0  {
                    type  cml_data_types:CML_INT32_T;  
                    description "Single precision floating point calibration data, Rx optical power.Bit 7 of byte 72 is MSB, bit 0 of byte 75 is LSB. RxPWR(0) should be set to zero for internally calibrated devices.";
                } // END of cmmSysrxpower0 definition.

                leaf cmmSysrxpower1  {
                    type  cml_data_types:CML_INT32_T;  
                    description "Single precision floating point calibration data, Rx optical power. Bit 7 of byte 68 is MSB, bit 0 of byte 71 is LSB. RxPWR(1) should be set to 1 for internally calibrated devices.";
                } // END of cmmSysrxpower1 definition.

                leaf cmmSysrxpower2  {
                    type  cml_data_types:CML_INT32_T;  
                    description "Single precision floating point calibration data, Rx optical power. Bit 7 of byte 64 is MSB, bit 0 of byte 67 is LSB. RxPWR(2) should be set to zero for internally calibrated devices.";
                } // END of cmmSysrxpower2 definition.

                leaf cmmSysrxpower3  {
                    type  cml_data_types:CML_INT32_T;  
                    description " Single precision floating point calibration data - Rx optical power. Bit 7 of byte 60 is MSB. Bit 0 of byte 63 is LSB. RxPWR(3) should be set to zero for internally calibrated devices.";
                } // END of cmmSysrxpower3 definition.

                leaf cmmSysrxpower4  {
                    type  cml_data_types:CML_INT32_T;  
                    description "Single precision floating point calibration data - Rx optical power. Bit 7 of byte 56 is MSB. Bit 0 of byte 59 is LSB. RxPWR(4) should be set to zero for internally calibrated devices.";
                } // END of cmmSysrxpower4 definition.

                leaf cmmSyslaserbiasslope  {
                    type  cml_data_types:CML_INT32_T;  
                    description " Fixed decimal (unsigned) calibration data, laser bias current. Bit 7 of byte 76 is MSB, bit 0 of byte 77 is LSB. TxI(Slope) should be set to 1 for internally calibrated devices.";
                } // END of cmmSyslaserbiasslope definition.

                leaf cmmSyslaserbiasoffset  {
                    type  cml_data_types:CML_INT32_T;  
                    description " Fixed decimal (signed two's complement) calibration data, laser bias current. Bit 7 of byte 78 is MSB, bit 0 of byte 79 is LSB. TxI(Offset) should  be set to zero for internally calibrated devices.";
                } // END of cmmSyslaserbiasoffset definition.

                leaf cmmSystxpowerslope  {
                    type  cml_data_types:CML_INT32_T;  
                    description "Fixed decimal (unsigned) calibration data, transmitter coupled output power. Bit 7 of byte 80 is MSB, bit 0 of byte 81 is LSB. TxPWR(Slope) should be set to 1 for internally calibrated devices.";
                } // END of cmmSystxpowerslope definition.

                leaf cmmSystxpoweroffset  {
                    type  cml_data_types:CML_INT32_T;  
                    description "Fixed decimal (signed two's complement) calibration data, transmitter coupled output power. Bit 7 of byte 82 is MSB, bit 0 of byte 83 is LSB. TxPWR(Offset) should be set to zero for internally calibrated devices.";
                } // END of cmmSystxpoweroffset definition.

                leaf cmmSystempslope  {
                    type  cml_data_types:CML_INT32_T;  
                    description "Fixed decimal (unsigned) calibration data, internal module temperature. Bit 7 of byte 84 is MSB, bit 0 of byte 85 is LSB. T(Slope) should be set to 1 for internally calibrated devices.";
                } // END of cmmSystempslope definition.

                leaf cmmSystempoffset  {
                    type  cml_data_types:CML_INT32_T;  
                    description "Fixed decimal (signed two's complement) calibration data, internal module temperature. Bit 7 of byte 86 is MSB, bit 0 of byte 87 is LSB. T(Offset) should be set to zero for internally calibrated devices.";
                } // END of cmmSystempoffset definition.

                leaf cmmSysvoltageslope  {
                    type  cml_data_types:CML_INT32_T;  
                    description " Fixed decimal (unsigned) calibration data, internal module supply voltage.Bit 7 of byte 88 is MSB, bit 0 of byte 89 is LSB. V(Slope) should be set to 1 for internally calibrated devices.";
                } // END of cmmSysvoltageslope definition.

                leaf cmmSysvoltageoffset  {
                    type  cml_data_types:CML_INT32_T;  
                    description "Fixed decimal (signed two's complement) calibration data, internal module supply voltage. Bit 7 of byte 90 is MSB. Bit 0 of byte 91 is LSB. V(Offset) should be set to zero for internally calibrated devices.";
                } // END of cmmSysvoltageoffset definition.

                leaf cmmSysTemperature  {
                    type  cml_data_types:CML_STRING_T {
                        length "0..255";
                    }
                    description "Temperature value of the system";
                } // END of cmmSysTemperature definition.

                leaf cmmSysVoltage  {
                    type  cml_data_types:CML_STRING_T {
                        length "0..255";
                    }
                    description "Internally measured supply voltage in transceiver";
                } // END of cmmSysVoltage definition.

                leaf cmmSysLaserBiasCurrent  {
                    type  cml_data_types:CML_STRING_T {
                        length "0..255";
                    }
                    description "Internally measured TX Bias Current.";
                } // END of cmmSysLaserBiasCurrent definition.

                leaf cmmSysTxOutputPower  {
                    type  cml_data_types:CML_STRING_T {
                        length "0..255";
                    }
                    description "Measured TX output power.";
                } // END of cmmSysTxOutputPower definition.

                leaf cmmSysRxInputPower  {
                    type  cml_data_types:CML_STRING_T {
                        length "0..255";
                    }
                    description "Measured RX input power.";
                } // END of cmmSysRxInputPower definition.

            } // End of cmmSysPortTable-list
        } // End of cmmStackUnitTable-list
    } // END of cmmStackUnitTable-grouping definition.


    grouping cmmSysPowerSupplyTable-grouping {
        list cmmSysPowerSupplyTable {
             
            description
                "list of power supply resident in the  chassis";

            config false;
            key "cmmSysPowerSupplyIndex";

            
            leaf cmmSysPowerSupplyIndex  {
                type  cml_data_types:CML_INT32_T;  
                description "The unique index of the power supply.";
            } // END of cmmSysPowerSupplyIndex definition.

            leaf cmmSysPOWERVDDR  {
                type  cml_data_types:CML_STRING_T {
                    length "0..255";
                }
                description "Power statistics for VCC 3.3v on Main board";
            } // END of cmmSysPOWERVDDR definition.

            leaf cmmSysPOWERCORE  {
                type  cml_data_types:CML_STRING_T {
                    length "0..255";
                }
                description "Power statistics for Mac 1v on Main board";
            } // END of cmmSysPOWERCORE definition.

            leaf cmmSysV1P1POWERRAIL  {
                type  cml_data_types:CML_STRING_T {
                    length "0..255";
                }
                description "Power statistics for Mac AVS 1v on Main board";
            } // END of cmmSysV1P1POWERRAIL definition.

            leaf cmmSysMAINBOARDPOWERRAIL  {
                type  cml_data_types:CML_STRING_T {
                    length "0..255";
                }
                description "Power status  for Main Board";
            } // END of cmmSysMAINBOARDPOWERRAIL definition.

            leaf cmmSysVCC5V  {
                type  cml_data_types:CML_STRING_T {
                    length "0..255";
                }
                description "Power status of VCC 5V";
            } // END of cmmSysVCC5V definition.

            leaf cmmSysVCC33V  {
                type  cml_data_types:CML_STRING_T {
                    length "0..255";
                }
                description "Power status of VCC 33V";
            } // END of cmmSysVCC33V definition.

            leaf cmmSysVCCMAC1V  {
                type  cml_data_types:CML_STRING_T {
                    length "0..255";
                }
                description "Power status of VCCMAC1V";
            } // END of cmmSysVCCMAC1V definition.

            leaf cmmSysVCCMACAVS1V  {
                type  cml_data_types:CML_STRING_T {
                    length "0..255";
                }
                description "Power status of VCCMACAVS1V";
            } // END of cmmSysVCCMACAVS1V definition.

            leaf cmmSysVCCV1P05  {
                type  cml_data_types:CML_STRING_T {
                    length "0..255";
                }
                description "Power Status of VCCV1P05";
            } // END of cmmSysVCCV1P05 definition.

            leaf cmmSysVCCV1P5  {
                type  cml_data_types:CML_STRING_T {
                    length "0..255";
                }
                description "Power Status of VCCV1P5";
            } // END of cmmSysVCCV1P5 definition.

            leaf cmmSysVCCV1P8  {
                type  cml_data_types:CML_STRING_T {
                    length "0..255";
                }
                description "Power Status of VCCV1P8";
            } // END of cmmSysVCCV1P8 definition.

            leaf cmmSysV1P05POWERRAIL  {
                type  cml_data_types:CML_STRING_T {
                    length "0..255";
                }
                description "Power status of V1P05POWERRAIL";
            } // END of cmmSysV1P05POWERRAIL definition.

            leaf cmmSysV1P5POWERRAIL  {
                type  cml_data_types:CML_STRING_T {
                    length "0..255";
                }
                description "Power status of V1P5POWERRAIL";
            } // END of cmmSysV1P5POWERRAIL definition.

            leaf cmmSysVCCPOWERRAIL  {
                type  cml_data_types:CML_STRING_T {
                    length "0..255";
                }
                description "Power status of VCCPOWERRAIL";
            } // END of cmmSysVCCPOWERRAIL definition.

            leaf cmmSysSBV1P5POWERRAIL  {
                type  cml_data_types:CML_STRING_T {
                    length "0..255";
                }
                description "Power status of SBV1P5POWERRAIL";
            } // END of cmmSysSBV1P5POWERRAIL definition.

            leaf cmmSysV1P0POWERRAIL  {
                type  cml_data_types:CML_STRING_T {
                    length "0..255";
                }
                description "Power rail 1.0V Status";
            } // END of cmmSysV1P0POWERRAIL definition.

            leaf cmmSysV3P3POWERRAIL  {
                type  cml_data_types:CML_STRING_T {
                    length "0..255";
                }
                description "Power rail 3.3V Status";
            } // END of cmmSysV3P3POWERRAIL definition.

            leaf cmmSysV1P8POWERRAIL  {
                type  cml_data_types:CML_STRING_T {
                    length "0..255";
                }
                description "Power rail 1.8V Status";
            } // END of cmmSysV1P8POWERRAIL definition.

            leaf cmmSysV1P35POWERRAIL  {
                type  cml_data_types:CML_STRING_T {
                    length "0..255";
                }
                description "Power Rail 1.35 Status";
            } // END of cmmSysV1P35POWERRAIL definition.

            leaf cmmSysDDRVTT  {
                type  cml_data_types:CML_STRING_T {
                    length "0..255";
                }
                description "Power statistics for VCC 5v on Main board.";
            } // END of cmmSysDDRVTT definition.

            leaf cmmSysPowerSupplyOperStatus  {
                type  cml_data_types:CML_STRING_T {
                    length "0..255";
                }
                description "The status of the power supply.";
            } // END of cmmSysPowerSupplyOperStatus definition.

            leaf cmmSysPowerSupplyType  {
                type  cml_data_types:CML_STRING_T {
                    length "0..255";
                }
                description "The type of the power supply.";
            } // END of cmmSysPowerSupplyType definition.

            leaf cmmSysHotSwapStat  {
                type  cml_data_types:CML_STRING_T {
                    length "0..255";
                }
                description "Power status  for HOT SWAP";
            } // END of cmmSysHotSwapStat definition.

            leaf cmmSysPSConsumption  {
                type  cml_data_types:CML_STRING_T {
                    length "0..255";
                }
                description "Output Power of Power supply";
            } // END of cmmSysPSConsumption definition.

            leaf cmmSysInputPower  {
                type  cml_data_types:CML_STRING_T {
                    length "0..255";
                }
                description "Input Power of Power supply";
            } // END of cmmSysInputPower definition.

            leaf cmmSysInputVoltage  {
                type  cml_data_types:CML_STRING_T {
                    length "0..255";
                }
                description "Input Voltage of Power supply";
            } // END of cmmSysInputVoltage definition.

            leaf cmmSysOutputVoltage  {
                type  cml_data_types:CML_STRING_T {
                    length "0..255";
                }
                description "Output Voltage of Power supply";
            } // END of cmmSysOutputVoltage definition.

            leaf cmmSysInputCurrent  {
                type  cml_data_types:CML_STRING_T {
                    length "0..255";
                }
                description "Input Current of Power supply";
            } // END of cmmSysInputCurrent definition.

            leaf cmmSysOutputCurrent  {
                type  cml_data_types:CML_STRING_T {
                    length "0..255";
                }
                description "Output Current of Power supply";
            } // END of cmmSysOutputCurrent definition.

            leaf cmmSysPSTemperature  {
                type  cml_data_types:CML_STRING_T {
                    length "0..255";
                }
                description "Temperature of Power supply";
            } // END of cmmSysPSTemperature definition.

            leaf cmmSysPSFanRpm  {
                type  cml_data_types:CML_STRING_T {
                    length "0..255";
                }
                description "Fan rpm of Power supply";
            } // END of cmmSysPSFanRpm definition.

            leaf cmmSysVCCAVS1V  {
                type  cml_data_types:CML_STRING_T {
                    length "0..255";
                }
                description "Power status of VCCAVS1V";
            } // END of cmmSysVCCAVS1V definition.

        } // End of cmmSysPowerSupplyTable-list
    } // END of cmmSysPowerSupplyTable-grouping definition.


    grouping cmmSysFanTable-grouping {
        list cmmSysFanTable {
             
            description
                "list of fan tray resident in the M-series chassis";

            config false;
            key "cmmSysFanTrayNumber";

            
            leaf cmmSysFanIndex  {
                type  cml_data_types:CML_INT32_T;  
                description "The unique index of the fan.";
            } // END of cmmSysFanIndex definition.

            leaf cmmSysFanControllerNum  {
                type  cml_data_types:CML_INT32_T;  
                description "Value represents the fan controller number.";
            } // END of cmmSysFanControllerNum definition.

            leaf cmmSysFanTrayNumber  {
                type  cml_data_types:CML_INT32_T;  
                description "Value represents the fan tray Number.";
            } // END of cmmSysFanTrayNumber definition.

            leaf cmmSysFanRpm  {
                type  cml_data_types:CML_INT32_T;  
                description "Value represents the fan rpm.";
            } // END of cmmSysFanRpm definition.

            leaf cmmSysFanLowRpm  {
                type  cml_data_types:CML_INT32_T;  
                description "Value represents the low RPM of fan.";
            } // END of cmmSysFanLowRpm definition.

            leaf cmmSysFanMidRpm  {
                type  cml_data_types:CML_INT32_T;  
                description "Value represents the  mid RPM of fan.";
            } // END of cmmSysFanMidRpm definition.

            leaf cmmSysFanHighRpm  {
                type  cml_data_types:CML_INT32_T;  
                description "Value represents the  high RPM of fan.";
            } // END of cmmSysFanHighRpm definition.

            leaf cmmSysFanTrayOperStatus  {
                type  cml_data_types:CML_STRING_T {
                    length "0..255";
                }
                description "The status of the fan tray.";
            } // END of cmmSysFanTrayOperStatus definition.

            leaf cmmSysFanTrayLed  {
                type  cml_data_types:CML_STRING_T {
                    length "0..255";
                }
                description "Value represents the fan led status.";
            } // END of cmmSysFanTrayLed definition.

        } // End of cmmSysFanTable-list
    } // END of cmmSysFanTable-grouping definition.


    grouping cmmSysTemperatureTable-grouping {
        list cmmSysTemperatureTable {
             
            description
                "list of Temperature Entities on board";

            config false;
            key "cmmSysTemperatureSensorIndex";

            
            leaf cmmSysTemperatureSensorIndex  {
                type  cml_data_types:CML_INT32_T;  
                description "Value represents Temperature Sensor Index";
            } // END of cmmSysTemperatureSensorIndex definition.

            leaf cmmSysTemperatureValue  {
                type  cml_data_types:CML_STRING_T {
                    length "0..255";
                }
                description "Value represents Temperature Sensor value";
            } // END of cmmSysTemperatureValue definition.

            leaf cmmSysTempLowThreshold  {
                type  cml_data_types:CML_STRING_T {
                    length "0..255";
                }
                description "Value represents Temperature Sensor lower threshold";
            } // END of cmmSysTempLowThreshold definition.

            leaf cmmSysTempHighThreshold  {
                type  cml_data_types:CML_STRING_T {
                    length "0..255";
                }
                description "Value represents Temperature Sensor high threshold";
            } // END of cmmSysTempHighThreshold definition.

        } // End of cmmSysTemperatureTable-list
    } // END of cmmSysTemperatureTable-grouping definition.


    grouping cmmSysChipTemperatureTable-grouping {
        list cmmSysChipTemperatureTable {
             
            description
                "list of Temperature Entities inside board chip";

            config false;
            key "cmmSysChipTemperatureSensorIndex";

            
            leaf cmmSysChipTemperatureSensorIndex  {
                type  cml_data_types:CML_INT32_T;  
                description "Value represents Temperature Monitor Index inside chip";
            } // END of cmmSysChipTemperatureSensorIndex definition.

            leaf cmmSysChipTemperatureValue  {
                type  cml_data_types:CML_STRING_T {
                    length "0..255";
                }
                description "Value represents Temperature monitor value";
            } // END of cmmSysChipTemperatureValue definition.

            leaf cmmSysChipTempPeakValue  {
                type  cml_data_types:CML_STRING_T {
                    length "0..255";
                }
                description "Value represents Temperature monitor peak value since last reading";
            } // END of cmmSysChipTempPeakValue definition.

        } // End of cmmSysChipTemperatureTable-list
    } // END of cmmSysChipTemperatureTable-grouping definition.

    grouping  cmmGlobals-grouping {
    container cmmGlobals {
                config true;

        description
            "cmm global structure";

        leaf locatorLed  {
            type  cml_data_types:CML_BOOL_T;  
            description "locator led";
        } // END of locatorLed definition.

        leaf dmmDebugFlag  {
            type  cml_data_types:CML_BOOL_T;  
            description "debug ddm";
        } // END of dmmDebugFlag definition.

        leaf cmmDebugFlag  {
            type  cml_data_types:CML_BOOL_T;  
            description "debug cmm";
        } // END of cmmDebugFlag definition.

    } // END of cmmGlobals-container definition.
    } // END of cmmGlobals-container definition.

    grouping  cmmDmm-grouping {
    container cmmDmm {
                config true;

        description
            "ddm monitor";

        leaf monitorEnabled  {
            type  cml_data_types:CML_BOOL_T;  
            description "ddm monitor all";
        } // END of monitorEnabled definition.

        leaf monitorTimerInterval  {
            type  cml_data_types:CML_UINT16_T {
                 range "60..3600";
            }
            description "ddm monitor interval";
        } // END of monitorTimerInterval definition.

        leaf statusServiceUnsuppTrans  {
            type  cml_data_types:CML_BOOL_T;  
            description "service unsupported-transceiver";
        } // END of statusServiceUnsuppTrans definition.

    } // END of cmmDmm-container definition.
    } // END of cmmDmm-container definition.

    grouping  ddmFalseAlarm-grouping {
    container ddmFalseAlarm {
                config true;

        description
            "ddm false alarm";

        leaf temperatureVal  {
            type  cml_data_types:CML_STRING_T {
                length "0..255";
            }
        } // END of temperatureVal definition.

        leaf voltageVal  {
            type  cml_data_types:CML_STRING_T {
                length "0..255";
            }
        } // END of voltageVal definition.

        leaf currentVal  {
            type  cml_data_types:CML_STRING_T {
                length "0..255";
            }
        } // END of currentVal definition.

        leaf rxpowerVal  {
            type  cml_data_types:CML_STRING_T {
                length "0..255";
            }
        } // END of rxpowerVal definition.

        leaf txpowerVal  {
            type  cml_data_types:CML_STRING_T {
                length "0..255";
            }
        } // END of txpowerVal definition.

    } // END of ddmFalseAlarm-container definition.
    } // END of ddmFalseAlarm-container definition.

    grouping  cmmCpuInfo-grouping {
    container cmmCpuInfo {
                config true;

        description
            "cpu information";

        leaf cpuUsage  {
            type  cml_data_types:CML_UINT8_T {
                 range "0..100";
            }
        } // END of cpuUsage definition.

        leaf psuNo  {
            type  cml_data_types:CML_UINT8_T {
                 range "1..2";
            }
        } // END of psuNo definition.

        leaf pOut  {
            type  cml_data_types:CML_UINT16_T {
                 range "0..1000";
            }
        } // END of pOut definition.

        leaf sensorNo  {
            type  cml_data_types:CML_UINT8_T {
                 range "1..10";
            }
        } // END of sensorNo definition.

        leaf currentTemperature  {
            type  cml_data_types:CML_UINT8_T {
                 range "0..150";
            }
        } // END of currentTemperature definition.

        leaf fanTrayNo  {
            type  cml_data_types:CML_UINT8_T {
                 range "1..10";
            }
        } // END of fanTrayNo definition.

        leaf fanNo  {
            type  cml_data_types:CML_UINT8_T {
                 range "1..10";
            }
        } // END of fanNo definition.

    } // END of cmmCpuInfo-container definition.
    } // END of cmmCpuInfo-container definition.

    grouping  cmmSysRamTable-grouping {
    container cmmSysRamTable {
                config false;

        description
            "list of Ram Entries";

        leaf cmmSysRamFreeMem  {
            type  cml_data_types:CML_UINT64_T;  
            description "CPU RAM's total free memory available for utilisation in KBytes.";
        } // END of cmmSysRamFreeMem definition.

        leaf cmmSysRamAvailableMem  {
            type  cml_data_types:CML_UINT64_T;  
            description "CPU RAM's total available memory in Kbytes.";
        } // END of cmmSysRamAvailableMem definition.

        leaf cmmSysRamThreshold  {
            type  cml_data_types:CML_UINT32_T;  
            description "The CPU Free Memory threshold in kilobytes.A zero threshold value indicates the CPU Free Memory Notification feature is disabled.Notifications are triggered when the CPU Free Memory falls below the configured threshold and when it rises to 10% above the configured threshold.CPU utilization in percentage for last 1 minute.";
        } // END of cmmSysRamThreshold definition.

        leaf cmmSysRamUsedMem  {
            type  cml_data_types:CML_UINT64_T;  
            description "CPU RAM's total used memory in Kbytes.";
        } // END of cmmSysRamUsedMem definition.

    } // END of cmmSysRamTable-container definition.
    } // END of cmmSysRamTable-container definition.

    grouping  cmmStackUnitUtilTable-grouping {
    container cmmStackUnitUtilTable {
                config false;

        description
            "list of Stack Unit Util Entries";

        leaf cmmStackUnitCpuProcessor  {
            type  cml_data_types:CML_UINT32_T;  
            description "The number of Online Processors Available";
        } // END of cmmStackUnitCpuProcessor definition.

        leaf cmmStackUnitCpuUtil1Min  {
            type  cml_data_types:CML_STRING_T {
                length "0..255";
            }
            description "CPU utilization in percentage for last 1 minute";
        } // END of cmmStackUnitCpuUtil1Min definition.

        leaf cmmStackUnitCpuUtil5Min  {
            type  cml_data_types:CML_STRING_T {
                length "0..255";
            }
            description "CPU utilization in percentage for last 5 minutes";
        } // END of cmmStackUnitCpuUtil5Min definition.

        leaf cmmStackUnitCpuUtil15Min  {
            type  cml_data_types:CML_STRING_T {
                length "0..255";
            }
            description "CPU utilization in percentage for last 15 minutes";
        } // END of cmmStackUnitCpuUtil15Min definition.

        leaf cmmSysCpuThresholdInterval  {
            type  cml_data_types:CML_UINT32_T;  
            description "The CPU Rising threshold interval in seconds. The time interval is configured in multiples of 5 seconds.A zero Rising interval indicates CPU Utilization Notification feature is disabled..";
        } // END of cmmSysCpuThresholdInterval definition.

        leaf cmmSysCpuThreshold  {
            type  cml_data_types:CML_UINT32_T;  
            description "The CPU MAX Threshold";
        } // END of cmmSysCpuThreshold definition.

        leaf cmmStackUnitCpuUtilization  {
            type  cml_data_types:CML_STRING_T {
                length "0..255";
            }
            description "Total memory usage in percentage";
        } // END of cmmStackUnitCpuUtilization definition.

        leaf cmmStackUnitCpuProcessorModelName  {
            type  cml_data_types:CML_STRING_T {
                length "0..255";
            }
            description "Displays CPU processor Model Name";
        } // END of cmmStackUnitCpuProcessorModelName definition.

    } // END of cmmStackUnitUtilTable-container definition.
    } // END of cmmStackUnitUtilTable-container definition.

    grouping  cmmSysLedTable-grouping {
    container cmmSysLedTable {
                config false;

        description
            "Sequence of cmmSysLedEntry";

        leaf cmmSysPowerLed  {
            type  cml_data_types:CML_STRING_T {
                length "0..255";
            }
            description "Status of Power led";
        } // END of cmmSysPowerLed definition.

        leaf cmmSysLocatorLed  {
            type  cml_data_types:CML_STRING_T {
                length "0..255";
            }
            description "Status of Locater led";
        } // END of cmmSysLocatorLed definition.

        leaf cmmSysMasterLed  {
            type  cml_data_types:CML_STRING_T {
                length "0..255";
            }
            description "Status of Master led";
        } // END of cmmSysMasterLed definition.

        leaf cmmSysSystemLed  {
            type  cml_data_types:CML_STRING_T {
                length "0..255";
            }
            description "Status of System led";
        } // END of cmmSysSystemLed definition.

        leaf cmmSysFrontFanLed  {
            type  cml_data_types:CML_STRING_T {
                length "0..255";
            }
            description "Status of FrontFan led";
        } // END of cmmSysFrontFanLed definition.

    } // END of cmmSysLedTable-container definition.
    } // END of cmmSysLedTable-container definition.

    grouping  cmmSysSwModuleTable-grouping {
    container cmmSysSwModuleTable {
                config false;

        description
            "list of software version information in a processor";

        leaf cmmSysSwRuntimeImgVersion  {
            type  cml_data_types:CML_STRING_T {
                length "0..255";
            }
            description "This variable indicates the software module version that is currently running on the processor.The software release version is in the format as follow: <major version>.<minor version>.<minor version>......'1.2' indicate major version of 1 and minor release of 2.";
        } // END of cmmSysSwRuntimeImgVersion definition.

        leaf cmmSysSwRuntimeImgDate  {
            type  cml_data_types:CML_STRING_T {
                length "0..255";
            }
            description "The release date of this software module.";
        } // END of cmmSysSwRuntimeImgDate definition.

    } // END of cmmSysSwModuleTable-container definition.
    } // END of cmmSysSwModuleTable-container definition.

    grouping  cmmAlarmVariable-grouping {
    container cmmAlarmVariable {
                config false;

        description
            "cmmAlarmVariable";

        leaf cmmAlarmVarInteger  {
            type  cml_data_types:CML_INT32_T;  
            description "An generic integer value in the TRAP object";
        } // END of cmmAlarmVarInteger definition.

        leaf cmmAlarmVarString  {
            type  cml_data_types:CML_STRING_T {
                length "0..255";
            }
            description "An generic string value in the TRAP object";
        } // END of cmmAlarmVarString definition.

    } // END of cmmAlarmVariable-container definition.
    } // END of cmmAlarmVariable-container definition.


}
