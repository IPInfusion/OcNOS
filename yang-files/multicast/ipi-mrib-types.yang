/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mrib-types.yang
*
*/

module ipi-mrib-types {

    yang-version 1.1;

    namespace   "http://www.ipinfusion.com/yang/ocnos/ipi-mrib-types";

    prefix "ipi-mrib-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Definitions types for the MRIB Datamodel";


    revision "2022-06-01" {
        description "Updated the yang file with feature";
        reference " 0.3.0.";
    }

    revision "2022-05-18" {
        description "Added Netconf GetAPI support for multicast routing table entries";
        reference " 0.2.0.";
    }

    revision "2021-12-02" {
        description "Initial Version";
        reference " 0.1.0.";
    }



    typedef  mrib_debug_t {
        type bits {
            bit event {
                position 0;
                description "None";
            }
            bit vif {
                position 1;
                description "None";
            }
            bit mrt {
                position 2;
                description "None";
            }
            bit stats {
                position 3;
                description "None";
            }
            bit fib-msg {
                position 4;
                description "None";
            }
            bit register-msg {
                position 5;
                description "None";
            }
            bit nsm-msg {
                position 6;
                description "None";
            }
            bit mrib-msg {
                position 7;
                description "None";
            }
            bit mtrace {
                position 8;
                description "None";
            }
            bit mtrace-detail {
                position 9;
                description "None";
            }
        }
        description "type definition for MRIB_DEBUG_T";
    }

    typedef  mrib_route_type_t {
        type enumeration {
            enum MRIB {
                value 10;
                description "MRIB";
            }
            enum PIM {
                value 11;
                description "PIM";
            }
            enum L2MRIB {
                value 46;
                if-feature feature-list:HAVE_L2MRIBD;
                description "L2MRIB";
            }
        }
        description "type definition for MRIB_ROUTE_TYPE_T";
    }

}
