/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mrib-ipv6.yang
*
*/

submodule ipi-mrib-ipv6 {

    yang-version 1.1;

    belongs-to  ipi-mrib { prefix ipi-mrib; }

    import feature-list {
        prefix feature-list;
        revision-date 2023-02-21;
    }

    import ipi-mrib-types {
        prefix ipi-mrib-types;
        revision-date 2022-06-01;
    }

    import ipi-interface {
        prefix ipi-interface;
        revision-date 2022-08-24;
    }

    include ipi-mrib-common { revision-date 2022-07-06;}
    organization
        "IP Infusion Inc.";

    contact
        "Address: 3965 Freedom Circle, Suite 200, Santa Clara, CA 95054
         Phone: +1 408-400-1900
         E-mail: support@ipinfusion.com
         Web: http://www.ipinfusion.com/";

    description
        "Datamodel for MRIB IPv6 configuration";


    revision "2022-07-15" {
        description "Adding CML_CONFIG_RUNTIME flag to interface list";
        reference " 0.3.2.";
    }

    revision "2022-07-06" {
        description "Corrected heirarchy for mrib-ip-vrf-common-mcast-route-oil-top";
        reference " 0.3.1.";
    }

    revision "2022-06-07" {
        description "Added 'rpa-id' attribute to mrib-ip-vrf-common-mcast-route-state";
        reference " 0.3.0.";
    }

    revision "2022-06-01" {
        description "Updated the yang file with feature";
        reference " 0.2.0.";
    }

    revision "2022-05-18" {
        description "Added Netconf GetAPI support for multicast routing table entries";
        reference " 0.1.1.";
    }

    revision "2022-03-17" {
        description "Restructured module as per open-config style";
        reference " 0.1.0.";
    }

    grouping mrib-ipv6-vrf-common-debug-state {
        description
            "MRIB6 VRF level terminal attributes of debug";
        leaf terminal-debug-options  {
            type  ipi-mrib-types:mrib_debug_t;
            description "Use this attribute to display MRIB terminal debugging information";
        } // END of terminal-debug-options definition.

    } // END of mrib-ipv6-vrf-common-debug-state definition.
    grouping mrib-ipv6-interface-config {
        description
            "MRIB IPv6 Interface level configuration";
        leaf name  {
            type  leafref {
                path  "/ipi-interface:interfaces/ipi-interface:interface/ipi-interface:name";
            }
            description "Use this attribute to specify the interface";
        } // END of name definition.

        leaf ttl-threshold  {
            type  uint8 {
                 range "1..255"  {
                    description "1..255: Supported range 1 - 255";
                 }
            }
            description "Use this attribute to configure the time-to-live (TTL) threshold of
                        packets being forwarded out of an interface. Only multicast packets
                        with a TTL value greater than the threshold are forwarded out of the
                        interface.";
        } // END of ttl-threshold definition.

    } // END of mrib-ipv6-interface-config definition.
    grouping mrib-ipv6-vrf-route-limit-top {
        description
            "MRIB IPv6 VRF level route limit configuration";
        container route-limit {
            description
                "container for MRIB IPv6 multicast route limit configuration and state
                        information";
            container config {
                // when " ipi-mrib-ipv6:ipv6/vrfs/vrf/config/multicast-routing-enable ";
                description
                    "MRIB IPv6 multicast route limit configuration";
                uses mrib-ip-vrf-common-route-limit-config;
            } // END of config-container definition.
            container state {
                config false;
                description
                    "MRIB IPv6 multicast route limit operational state";
                uses mrib-ip-vrf-common-route-limit-config;
            } // END of state-container definition.
        } // END of route-limit-container definition.
    } // END of mrib-ipv6-vrf-route-limit-top definition.
    grouping mrib-ipv6-vrf-debug-top {
        description
            "MRIB IPv6 VRF level debug configuration";
        container debug {
            description
                "container for MRIB IPv6 multicast route limit configuration and state
                        information";
            container config {
                when " /mrib/ipv6/vrfs/vrf/config/multicast-routing-enable ";
                description
                    "MRIB IPv6 multicast debug configuration";
                uses mrib-ip-vrf-common-debug-config;
            } // END of config-container definition.
            container state {
                config false;
                description
                    "MRIB IPv6 multicast route debug operational state";
                uses mrib-ip-vrf-common-debug-config;
                uses mrib-ipv6-vrf-common-debug-state;
            } // END of state-container definition.
        } // END of debug-container definition.
    } // END of mrib-ipv6-vrf-debug-top definition.
    grouping mrib-ipv6-vrfs-top {
        description
            "Top level grouping for MRIB IPv6 VRF configuration and data";
        container vrfs {
            description
                "container for vrf level MRIB IPv6 configuration and state information";

            list vrf {
                key "vrf-name";
                description
                    "VRF level MRIB IPv6 configuration and state information";
                leaf vrf-name  {
                    type  leafref {
                        path  "../config/vrf-name";
                    }
                    description "Use this attribute to specify the VRF";
                } // END of vrf-name definition.

                container config {
                    description
                        "MRIB IPV6 vrf configuration information";
                    uses mrib-ip-vrf-common-config;
                } // END of config-container definition.
                container state {
                    config false;
                    description
                        "MRIB IPV6 VRF state information";
                    container counters {
                        config false;
                        description
                            "MRIB IPv6 VRF Statistics counters";
                        uses mrib-ip-vrf-common-counters-state;
                    } // END of counters-container definition.
                    uses mrib-ip-vrf-common-config;
                    uses mrib-ip-vrf-common-state;
                } // END of state-container definition.
                uses mrib-ipv6-vrf-route-limit-top;
                uses mrib-ipv6-vrf-debug-top;
                uses mrib-ip-vrf-common-mcast-route-top;
            } // End of vrf-list
        } // END of vrfs-container definition.
    } // END of mrib-ipv6-vrfs-top definition.
    grouping mrib-ipv6-interfaces-top {
        description
            "Top level grouping for MRIB IPv6 interface configuration and data";
        container interfaces {
            description
                "container for VRF level MRIB IPv6 configuration and state information";

            list interface {
                key "name";
                description
                    "Interface level MRIB IPv6 configuration and state information";
                leaf name  {
                    type  leafref {
                        path  "../config/name";
                    }
                    description "Use this attribute to specify the interface";
                } // END of name definition.

                container config {
                    description
                        "MRIB IPv6 interface configuration information";
                    uses mrib-ipv6-interface-config;
                } // END of config-container definition.
                container state {
                    config false;
                    description
                        "MRIB IPv6 interface state information";
                    uses mrib-ipv6-interface-config;
                    uses mrib-ip-common-interface-state;
                } // END of state-container definition.
            } // End of interface-list
        } // END of interfaces-container definition.
    } // END of mrib-ipv6-interfaces-top definition.

    grouping  ipv6-grouping {
    description
        "Top level container for all IPv6 multicast RIB configuration and state
                data";
    container ipv6 {
        if-feature feature-list:HAVE_MRIBD;
        if-feature feature-list:HAVE_MCAST_IPV6;
        description
            "Top level container for all IPv6 multicast RIB configuration and state
                    data";
        uses mrib-ipv6-vrfs-top;
        uses mrib-ipv6-interfaces-top;
    } // END of ipv6-container definition.
    } // END of ipv6-grouping definition.


}
