/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-igmp-snooping-types.yang
*
*/

module ipi-igmp-snooping-types {

    yang-version 1.1;

    namespace   "http://www.ipinfusion.com/yang/ocnos/ipi-igmp-snooping-types";

    prefix "ipi-igmp-snooping-types";

    organization
        "IP Infusion Inc.";

    contact
        "Address: 3965 Freedom Circle, Suite 200, Santa Clara, CA 95054
         Phone: +1 408-400-1900
         E-mail: support@ipinfusion.com
         Web: http://www.ipinfusion.com/";

    description
        "Definition types for IGMP Snooping";


    revision "2021-11-15" {
        description "Restructured module as per OpenConfig style";
        reference " 0.1.0.";
    }



    typedef  igmp_snoop_unknown_mcast_action_t {
        type enumeration {
            enum flood {
                value 0;
                description "flood mode";
            }
            enum discard {
                value 1;
                description "Discard mode";
            }
        }
        description "type definition for IGMP_SNOOP_UNKNOWN_MCAST_ACTION_T";
    }

    typedef  igmp_snoop_debug_options_t {
        type bits {
            bit decode {
                position 0;
                description "decode";
            }
            bit encode {
                position 1;
                description "encode";
            }
            bit events {
                position 2;
                description "events";
            }
            bit fsm {
                position 3;
                description "FSM";
            }
            bit tib {
                position 4;
                description "Tree-Info-Base (TIB)";
            }
        }
        description "type definition for IGMP_SNOOP_DEBUG_OPTIONS_T";
    }

}
