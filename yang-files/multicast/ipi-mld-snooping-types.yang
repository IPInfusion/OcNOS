/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mld-snooping-types.yang
*
*/

module ipi-mld-snooping-types {

    yang-version 1.1;

    namespace   "http://www.ipinfusion.com/yang/ocnos/ipi-mld-snooping-types";

    prefix "ipi-mld-snooping-types";

    organization
        "IP Infusion Inc.";

    contact
        "Address: 3965 Freedom Circle, Suite 200, Santa Clara, CA 95054
         Phone: +1 408-400-1900
         E-mail: support@ipinfusion.com
         Web: http://www.ipinfusion.com/";

    description
        "Definition types for MLD Snooping";


    revision "2022-06-01" {
        description "Updated the yang file with feature";
        reference " 0.2.0.";
    }

    revision "2022-01-31" {
        description "Initial Version";
        reference " 0.1.0.";
    }



    typedef  mld_snoop_debug_options_t {
        type bits {
            bit decode {
                position 0;
                description "decode option";
            }
            bit encode {
                position 1;
                description "encode option";
            }
            bit events {
                position 2;
                description "events option";
            }
            bit fsm {
                position 3;
                description "FSM option";
            }
            bit tib {
                position 4;
                description "Tree-Info-Base (TIB) option";
            }
        }
        description "type definition for MLD_SNOOP_DEBUG_OPTIONS_T";
    }

}
