/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-igmp-groups.yang
*
*/

submodule ipi-igmp-groups {

    yang-version 1.1;

    belongs-to  ipi-igmp { prefix ipi-igmp; }

    import feature-list {
        prefix feature-list;
        revision-date 2023-02-21;
    }

    import ietf-inet-types {
        prefix inet;
        revision-date 2013-07-15;
    }

    import ipi-igmp-types {
        prefix ipi-igmp-types;
        revision-date 2022-06-01;
    }

    import ipi-interface {
        prefix ipi-interface;
        revision-date 2022-08-24;
    }

    import ipi-network-instance {
        prefix ipi-network-instance;
        revision-date 2022-06-01;
    }

    import ipi-vrf {
        prefix ipi-vrf;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Data model for IGMP Groups";


    revision "2022-06-01" {
        description "Updated the yang file with feature";
        reference " 0.3.0.";
    }

    revision "2022-02-07" {
        description "Renamed CML_YES_NO_T to IGMP_YES_NO_T";
        reference " 0.2.0.";
    }

    revision "2021-11-15" {
        description "Initial Version";
        reference " 0.1.0.";
    }

    grouping igmp-instance-vrf-entry-state {
        description
            "Interface entry operational state data";
        leaf vrf-name  {
            type  string {
                length "1..1965";
                pattern "[^?' =,>|]+";
            }
            description "VRF instance name";
        } // END of vrf-name definition.

    } // END of igmp-instance-vrf-entry-state definition.
    grouping igmp-instance-if-entry-state {
        description
            "Interface entry operational state data";
        leaf if-name  {
            type  string {
                length "1..1965";
                pattern "[^?' =,>|]+";
            }
            description "Interface instance name";
        } // END of if-name definition.

    } // END of igmp-instance-if-entry-state definition.
    grouping igmp-instance-group-state {
        description
            "IGMP Instance Group State Information";
        leaf group-address  {
            type  inet:ipv4-address;
            description "Multicast group address joined";
        } // END of group-address definition.

        leaf dynamic-remote  {
            type  empty;
            description "Indicates that this multicast source is learnt dynamically";
        } // END of dynamic-remote definition.

        leaf static-group  {
            type  empty;
            description "Presence of this attribute indicates a statically configured multicast
                        group";
        } // END of static-group definition.

        leaf local  {
            type  empty;
            description "Presence of this attribute indicates a locally joined group";
        } // END of local definition.

        leaf ssm-mapped  {
            type  empty;
            description "Presence of this attribute indicates a SSM mapped group";
        } // END of ssm-mapped definition.

        leaf static-source  {
            type  empty;
            description "Presence of this attribute indicates a statically configured multicast
                        source";
        } // END of static-source definition.

        leaf up-time  {
            type  string {
                length "1..1965";
                pattern "[^?' =,>|]+";
            }
            description "Indicates the up-time for group membership";
        } // END of up-time definition.

        leaf group-mode  {
            type  ipi-igmp-types:igmp_ssm_group_mode_t;
            description "Indicates the SSM group mode as include or exclude";
        } // END of group-mode definition.

        leaf expiry  {
            type  string {
                length "1..1965";
                pattern "[^?' =,>|]+";
            }
            description "Indicates the expiry time for group membership";
        } // END of expiry definition.

        leaf last-reporter  {
            type  inet:ipv4-address;
            description "Indicates the last reporter for this group";
        } // END of last-reporter definition.

    } // END of igmp-instance-group-state definition.
    grouping igmp-instance-group-source-state {
        description
            "IGMP Instance Group Source State";
        leaf source-address  {
            type  inet:ipv4-address;
            description "Multicast source address for the group";
        } // END of source-address definition.

        leaf dynamic-remote  {
            type  empty;
            description "Indicates that this multicast source is learnt dynamically";
        } // END of dynamic-remote definition.

        leaf static-source  {
            type  empty;
            description "Indicates that this multicast source is configured statically";
        } // END of static-source definition.

        leaf local  {
            type  empty;
            description "Locally configured multicast source";
        } // END of local definition.

        leaf ssm-mapped  {
            type  empty;
            description "Presence of this attribute indicates a SSM mapped group";
        } // END of ssm-mapped definition.

        leaf up-time  {
            type  string {
                length "1..1965";
                pattern "[^?' =,>|]+";
            }
            description "Indicates the up-time for group membership";
        } // END of up-time definition.

        leaf expiry  {
            type  string {
                length "1..1965";
                pattern "[^?' =,>|]+";
            }
            description "Indicates the expiry time for group membership";
        } // END of expiry definition.

        leaf is-forwarded  {
            type  ipi-igmp-types:igmp_yes_no_t;
            description "Indicates if traffic from this source-group is forwarded upstream";
        } // END of is-forwarded definition.

    } // END of igmp-instance-group-source-state definition.
    grouping igmp-proxy-group-state {
        description
            "IGMP Proxy Group State Information";
        leaf group-address  {
            type  inet:ipv4-address;
            description "Multicast group address joined";
        } // END of group-address definition.

        leaf proxy-interface  {
            type  string {
                length "1..1965";
                pattern "[^?' =,>|]+";
            }
            description "Indicates the upstream proxy interface";
        } // END of proxy-interface definition.

        leaf group-mode  {
            type  ipi-igmp-types:igmp_ssm_group_mode_t;
            description "Indicates the SSM group mode as include or exclude";
        } // END of group-mode definition.

        leaf state  {
            type  ipi-igmp-types:igmp_if_state_t;
            description "State of the proxy interface";
        } // END of state definition.

        leaf membership-state  {
            type  ipi-igmp-types:igmp_proxy_grp_membership_state_t;
            description "Indicates the group-membership state";
        } // END of membership-state definition.

        leaf-list multicast-sources  {
            type  inet:ipv4-address;
            description "List of multicast sources for this group membership.";
        } // END of multicast-sources definition.

    } // END of igmp-proxy-group-state definition.

    grouping  group-membership-tree-grouping {
    description
        "Group Membership Tree Container";
    container group-membership-tree {
        if-feature feature-list:HAVE_MRIBD;
        config false;
        description
            "Group Membership Tree Container";
        container igmp-instances {
            config false;
            description
                "IGMP Instances";

            list igmp-instance {
                key "vrf-name";
                config false;
                description
                    "IGMP Instance";
                leaf vrf-name  {
                    type  leafref {
                        path  "/ipi-network-instance:network-instances/ipi-network-instance:network-instance/ipi-vrf:vrf/ipi-vrf:config/ipi-vrf:vrf-name";
                    }
                    config false;
                    description "VRF name";
                } // END of vrf-name definition.

                container interfaces {
                    config false;
                    description
                        "IGMP Interfaces related operations";

                    list interface {
                        key "if-name";
                        config false;
                        description
                            "IGMP Interace Instance";
                        leaf if-name  {
                            type  leafref {
                                path  "/ipi-interface:interfaces/ipi-interface:interface/ipi-interface:name";
                            }
                            config false;
                            description "Interface name";
                        } // END of if-name definition.

                        container member-groups {
                            config false;
                            description
                                "IGMP Member-Groups";

                            list member-group {
                                key "group-address";
                                config false;
                                description
                                    "List of member-group instances";
                                leaf group-address  {
                                    type  leafref {
                                        path  "../state/group-address";
                                    }
                                    description "Multicast group address joined";
                                } // END of group-address definition.

                                container state {
                                    config false;
                                    description
                                        "State container for IGMP member-groups";
                                    uses igmp-instance-group-state;
                                } // END of state-container definition.
                                container include-sources {
                                    config false;
                                    description
                                        "Include-sources for IGMP member-groups";

                                    list include-source {
                                        key "source-address";
                                        config false;
                                        description
                                            "List of include sources for the group";
                                        leaf source-address  {
                                            type  leafref {
                                                path  "../state/source-address";
                                            }
                                            description "Multicast source address for the group";
                                        } // END of source-address definition.

                                        container state {
                                            config false;
                                            description
                                                "State container for include-source instance";
                                            uses igmp-instance-group-source-state;
                                        } // END of state-container definition.
                                    } // End of include-source-list
                                } // END of include-sources-container definition.
                                container exclude-sources {
                                    config false;
                                    description
                                        "Exclude-sources for IGMP member-groups";

                                    list exclude-source {
                                        key "source-address";
                                        config false;
                                        description
                                            "List of exclude sources for the group";
                                        leaf source-address  {
                                            type  leafref {
                                                path  "../state/source-address";
                                            }
                                            description "Multicast source address for the group";
                                        } // END of source-address definition.

                                        container state {
                                            config false;
                                            description
                                                "State container for exclude-source instance";
                                            uses igmp-instance-group-source-state;
                                        } // END of state-container definition.
                                    } // End of exclude-source-list
                                } // END of exclude-sources-container definition.
                            } // End of member-group-list
                        } // END of member-groups-container definition.
                        container proxy-groups {
                            config false;
                            description
                                "IGMP proxy-groups";

                            list proxy-group {
                                key "group-address";
                                config false;
                                description
                                    "List of IGMP proxy group memberships on the interface";
                                leaf group-address  {
                                    type  leafref {
                                        path  "../state/group-address";
                                    }
                                    description "Multicast group address joined";
                                } // END of group-address definition.

                                container state {
                                    config false;
                                    description
                                        "State container for proxy-group instance";
                                    uses igmp-proxy-group-state;
                                } // END of state-container definition.
                            } // End of proxy-group-list
                        } // END of proxy-groups-container definition.
                    } // End of interface-list
                } // END of interfaces-container definition.
            } // End of igmp-instance-list
        } // END of igmp-instances-container definition.
    } // END of group-membership-tree-container definition.
    } // END of group-membership-tree-grouping definition.


}
