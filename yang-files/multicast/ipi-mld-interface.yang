/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mld-interface.yang
*
*/

submodule ipi-mld-interface {

    yang-version 1.1;

    belongs-to  ipi-mld { prefix ipi-mld; }

    import feature-list {
        prefix feature-list;
        revision-date 2023-02-21;
    }

    import ietf-inet-types {
        prefix inet;
        revision-date 2013-07-15;
    }

    import ietf-yang-types {
        prefix yang;
        revision-date 2013-07-15;
    }

    import ipi-interface {
        prefix ipi-interface;
        revision-date 2022-08-24;
    }

    import ipi-mld-types {
        prefix ipi-mld-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Data model for MLD Interface Managed object";


    revision "2022-06-01" {
        description "Updated the yang file with feature";
        reference " 0.2.0.";
    }

    revision "2022-03-09" {
        description "Initial Version";
        reference " 0.1.0.";
    }

    grouping mld-interface-config {
        description
            "MLD Interface Configurations";
        leaf name  {
            type  leafref {
                path  "/ipi-interface:interfaces/ipi-interface:interface/ipi-interface:name";
            }
            description "This attribute defines the interface where MLD is configured";
        } // END of name definition.

        leaf enabled  {
            type  empty;
            description "Use this attribute to enable the MLD protocol operation on an
                        interface. This attribute enables MLD protocol operation in
                        stand-alone mode,
                        and can be used to learn local-membership information prior to
                        enabling a multicast routing protocol on the interface.
                        This attribute will have no effect on interfaces configured for MLD
                        Proxy.";
        } // END of enabled definition.

        leaf last-member-query-count  {
            type  uint8 {
                 range "2..7"  {
                    description "2..7: Supported range 2 - 7";
                 }
            }
            default "2";
            description "Use this attribute to set the last-member query-count value.
                        This attribute applies to interfaces configured for MLD Layer-3
                        multicast protocols,
                        MLD Snooping, or MLD Proxy.";
        } // END of last-member-query-count definition.

        leaf last-member-query-interval  {
            type  uint16 {
                 range "1000..25500"  {
                    description "1000..25500: Supported range 1000 - 25500";
                 }
            }
            units "seconds";
            default "1000";
            description "Use this attribute to set the frequency at which the router sends MLD
                        group-specific host query messages.
                        This attribute applies to interfaces configured for MLD Layer-3
                        multicast protocols, MLD Snooping, or MLD Proxy";
        } // END of last-member-query-interval definition.

        leaf querier-timeout  {
            type  uint16 {
                 range "60..300"  {
                    description "60..300: Supported range 60 - 300";
                 }
            }
            units "seconds";
            default "250";
            description "Use this attribute to configure the timeout period before the router
                        takes over as the querier for the interface after the previous querier
                        has stopped querying.
                        This attribute applies to interfaces configured for MLD Layer-3
                        multicast protocols, MLD Snooping, or MLD Proxy.";
        } // END of querier-timeout definition.

        leaf query-interval  {
            type  uint16 {
                 range "1..18000"  {
                    description "1..18000: Supported range 1 - 18000";
                 }
            }
            units "seconds";
            default "125";
            description "Use this attribute to set the frequency of sending MLD host query
                        messages.
                        This attribute applies to interfaces configured for MLD Layer-3
                        multicast protocols, MLD Snooping, or MLD Proxy.";
        } // END of query-interval definition.

        leaf query-max-response-time  {
            type  uint8 {
                 range "1..240"  {
                    description "1..240: Supported range 1 - 240";
                 }
            }
            units "seconds";
            default "10";
            description "Use this attribute to set the maximum response time advertised in MLD
                        queries.
                        This attribute applies to interfaces configured for MLD Layer-3
                        multicast protocols, MLD Snooping, or MLD Proxy.";
        } // END of query-max-response-time definition.

        leaf startup-query-interval  {
            type  uint16 {
                 range "1..18000"  {
                    description "1..18000: Supported range 1 - 18000";
                 }
            }
            units "seconds";
            default "31";
            description "Use this attribute to set a startup query interval value for MLD";
        } // END of startup-query-interval definition.

        leaf startup-query-count  {
            type  uint8 {
                 range "2..10"  {
                    description "2..10: Supported range 2 - 10";
                 }
            }
            default "2";
            description "Use this attribute to set a startup query count for MLD";
        } // END of startup-query-count definition.

        leaf robustness-variable  {
            type  uint8 {
                 range "2..7"  {
                    description "2..7: Supported range 2 - 7";
                 }
            }
            default "2";
            description "Use this attribute to set the robustness variable value on an
                        interface. This attribute applies to interfaces configured for MLD
                        Layer-3 multicast protocols, MLD Snooping, or MLD Proxy.";
        } // END of robustness-variable definition.

        leaf version  {
            type  uint8 {
                 range "1..2"  {
                    description "1..2: Supported range 1 - 2";
                 }
            }
            description "Use this attribute to set the current MLD protocol version on an
                        interface. This attribute applies to interfaces configured for MLD
                        Layer-3 multicast protocols, MLD Snooping, or MLD Proxy.";
        } // END of version definition.

    } // END of mld-interface-config definition.
    grouping mld-interface-state {
        description
            "MLD Interface State Information";
        leaf internet-address  {
            type  inet:ipv6-address;
            description "Interface IP address used by MLD to communicate with remote peer";
        } // END of internet-address definition.

        leaf oper-status  {
            type  ipi-mld-types:mld_if_oper_status_t;
            description "Operational status of the MLD interface";
        } // END of oper-status definition.

        leaf host-version  {
            type  uint8;
            description "host-version";
        } // END of host-version definition.

        leaf is-querier  {
            type  boolean;
            description "Indicates whether this interface is a MLD querier or not.";
        } // END of is-querier definition.

        leaf querying-router  {
            type  inet:ipv6-address;
            description "MLD querying router for this subnet";
        } // END of querying-router definition.

        leaf group-membership-interval  {
            type  uint32;
            units "seconds";
            description "Time interval after which the group memberships on this interface will
                        time out.";
        } // END of group-membership-interval definition.

    } // END of mld-interface-state definition.
    grouping mld-interface-counters-state {
        description
            "MLD Interface Counters Information";
        leaf v1-reports-received  {
            type  yang:counter32;
            description "Number of MLDv1 reports received on this interface.";
        } // END of v1-reports-received definition.

        leaf v2-reports-received  {
            type  yang:counter32;
            description "Number of MLDv2 reports received on this interface.";
        } // END of v2-reports-received definition.

        leaf v1-leaves-received  {
            type  yang:counter32;
            description "Number of MLDv1 leaves received on this interface.";
        } // END of v1-leaves-received definition.

        leaf current-group-records  {
            type  yang:counter32;
            description "Number of current group membership records on this interface.";
        } // END of current-group-records definition.

    } // END of mld-interface-counters-state definition.
    grouping mld-if-proxy-config {
        description
            "MLD Interface Proxy Configurations";
        leaf enable-proxy-service  {
            type  empty;
            description "Use this attribute to designate an interface to be the MLD
                        proxy-service upstream host-side interface,
                        thus enabling MLD host-side protocol operation on this interface.
                        All associated downstream router-side interfaces will have their
                        memberships consolidatedon this interface,
                        according to MLD host-side functionality. This attribute should not be
                        used when configuring interfaces enabled for MLD in association with a
                        multicast-routing protocol,
                        otherwise the behavior will be undefined.";
        } // END of enable-proxy-service definition.

        leaf mroute-proxy-interface  {
            type  string {
                length "1..1965";
                pattern "[^?' =,>|]+";
            }
            default "NULL";
            description "Use this attribute to specify the MLD Proxy service (upstream
                        host-side) interface with which to be associated.
                        MLD router-side protocol operation is enabled only when the specified
                        upstream proxy-service interface is functional.
                        This attribute should not be configured on interfaces enabled for MLD
                        in association with a multicast routing protocol otherwise,
                        the behavior will be undefined.";
        } // END of mroute-proxy-interface definition.

        leaf unsolicited-report-interval  {
            type  uint16 {
                 range "1000..25500"  {
                    description "1000..25500: Supported range 1000 - 25500";
                 }
            }
            default "1000";
            description "Use this attribute to set an unsolicited report interval for an
                        interface designated as an MLD proxy";
        } // END of unsolicited-report-interval definition.

    } // END of mld-if-proxy-config definition.
    grouping mld-if-proxy-state {
        description
            "MLD Interface Proxy State Information";
        leaf oper-status  {
            type  ipi-mld-types:mld_proxy_if_oper_status_t;
            description "MLD proxy operational status";
        } // END of oper-status definition.

        leaf upstream-interface  {
            type  string {
                length "1..1965";
                pattern "[^?' =,>|]+";
            }
            description "Name of Upstream Interface";
        } // END of upstream-interface definition.

        leaf mcast-groups-count  {
            type  yang:counter32;
            description "Number of multicast groups";
        } // END of mcast-groups-count definition.

    } // END of mld-if-proxy-state definition.
    grouping mld-if-grp-membsership-config {
        description
            "MLD Inteface Group Membership Configurations";
        leaf access-group-name  {
            type  string {
                length "1..1965";
                pattern "[a-zA-Z0-9][^?' =,>|]*";
            }
            default "NULL";
            description "Use this attribute to control the multicast local-membership groups
                        learned on an interface. This attribute applies to
                        interfaces configured for MLD Layer-3 multicast protocols, MLD proxy.";
        } // END of access-group-name definition.

        leaf immediate-leave-groups-list  {
            type  string {
                length "1..1965";
                pattern "[a-zA-Z0-9][^?' =,>|]*";
            }
            default "NULL";
            description "In MLD version 2, use this attribute to minimize the leave latency of
                        MLD memberships.
                        This attribute is used when only one receiver host is connected to
                        each interface.
                        This command applies to interfaces configured for MLD Layer-3
                        multicast protocols, MLD Proxy.";
        } // END of immediate-leave-groups-list definition.

        leaf member-limit  {
            type  uint32 {
                 range "1..2097152"  {
                    description "1..2097152: Supported range 1 - 2097152";
                 }
            }
            default "1";
            description "Use this attribute to set the limit on the maximum number of group
                        membership states at either the router level,
                        or forthe specified interface. Once the specified number of group
                        memberships is reached, all further local-memberships will be ignored.
                        Optionally, an exception access-list can be configured to specify the
                        group-address(es) to be excluded from being subject to the limit.";
        } // END of member-limit definition.

        leaf limit-exception-acl  {
            when " /mld/interfaces/interface/group-membership-control/config/member-limit ";
            type  string {
                length "1..1965";
                pattern "[a-zA-Z0-9][^?' =,>|]*";
            }
            default "NULL";
            description "Use this attribute to set the maximum number of group membership
                        states, at either the router level or at the interface
                        level. Once the specified number of group memberships is reached, all
                        further local-memberships are ignored.
                        Optionally, an exception access-list can be configured to specify the
                        group-address to be excluded from being subject to the limit.";
        } // END of limit-exception-acl definition.

    } // END of mld-if-grp-membsership-config definition.
    grouping mld-if-asm-static-grp-config {
        description
            "MLD Interface ASM Static Group Configurations";
        leaf group-address  {
            type  inet:ipv6-address;
            description "Use this attribute to statically configure IPv6 group membership
                        entries on an interface. To statically add only a group membership,
                        do not specify any parameters. This attribute applies to MLD operation
                        on a specific interface to statically add group and/or source records
                        or to MLD Snooping on a VLAN interface to statically add group and/or
                        source records.";
        } // END of group-address definition.

    } // END of mld-if-asm-static-grp-config definition.
    grouping mld-if-ssm-static-grp-config {
        description
            "MLD Interface SSM Static Group Configurations";
        leaf group-address  {
            type  inet:ipv6-address;
            description "Use this attribute to statically configure the group to be joined.";
        } // END of group-address definition.

        leaf source  {
            type  ipi-mld-types:mld_static_ssm_source_t;
            description "Use this attribute to statically configure the multicast source for
                        group to be joined.";
        } // END of source definition.

    } // END of mld-if-ssm-static-grp-config definition.

    grouping  interfaces-grouping {
    description
        "Top level container for MLD interfaces";
    container interfaces {
        if-feature feature-list:HAVE_MCAST_IPV6;
        if-feature feature-list:NOT_HAVE_DUNE_OR_HAVE_DNX;
        description
            "Top level container for MLD interfaces";

        list interface {
            key "name";
            description
                "MLD interface instance configurations";
            leaf name  {
                type  leafref {
                    path  "../config/name";
                }
                description "This attribute defines the interface where MLD is configured";
            } // END of name definition.

            container config {
                description
                    "config container for MLD interface instance configurations";
                uses mld-interface-config;
            } // END of config-container definition.
            container state {
                config false;
                description
                    "state container for MLD interface instance configurations";
                container counters {
                    config false;
                    description
                        "container for MLD interface counters";
                    uses mld-interface-counters-state;
                } // END of counters-container definition.
                uses mld-interface-state;
                uses mld-interface-config;
            } // END of state-container definition.
            container proxy {
                description
                    "MLD inteface proxy configurations";
                container config {
                    description
                        "config container for MLD proxy configurations";
                    uses mld-if-proxy-config;
                } // END of config-container definition.
                container state {
                    config false;
                    description
                        "state container for MLD proxy configurations";
                    uses mld-if-proxy-config;
                    uses mld-if-proxy-state;
                } // END of state-container definition.
            } // END of proxy-container definition.
            container group-membership-control {
                description
                    "MLD inteface group membership control configurations";
                container config {
                    description
                        "config container for MLD group membership control configurations";
                    uses mld-if-grp-membsership-config;
                } // END of config-container definition.
                container state {
                    config false;
                    description
                        "state container for MLD group membership control configurations";
                    uses mld-if-grp-membsership-config;
                } // END of state-container definition.
            } // END of group-membership-control-container definition.
            container asm-static-groups {
                description
                    "MLD inteface ASM static groups configurations";

                list asm-static-group {
                    key "group-address";
                    description
                        "MLD interface ASM static group instance configurations";
                    leaf group-address  {
                        type  leafref {
                            path  "../config/group-address";
                        }
                        description "Use this attribute to statically configure IPv6 group membership
                                    entries on an interface. To statically add only a group membership,
                                    do not specify any parameters. This attribute applies to MLD operation
                                    on a specific interface to statically add group and/or source records
                                    or to MLD Snooping on a VLAN interface to statically add group and/or
                                    source records.";
                    } // END of group-address definition.

                    container config {
                        description
                            "config container for MLD ASM static group configurations";
                        uses mld-if-asm-static-grp-config;
                    } // END of config-container definition.
                    container state {
                        config false;
                        description
                            "state container for MLD ASM static group configurations";
                        uses mld-if-asm-static-grp-config;
                    } // END of state-container definition.
                } // End of asm-static-group-list
            } // END of asm-static-groups-container definition.
            container ssm-static-groups {
                description
                    "MLD inteface SSM static groups configurations";

                list ssm-static-group {
                    key "group-address source";
                    description
                        "MLD interface SSM static group instance configurations";
                    leaf group-address  {
                        type  leafref {
                            path  "../config/group-address";
                        }
                        description "Use this attribute to statically configure the group to be joined.";
                    } // END of group-address definition.

                    leaf source  {
                        type  leafref {
                            path  "../config/source";
                        }
                        description "Use this attribute to statically configure the multicast source for
                                    group to be joined.";
                    } // END of source definition.

                    container config {
                        description
                            "config container for MLD SSM static group configurations";
                        uses mld-if-ssm-static-grp-config;
                    } // END of config-container definition.
                    container state {
                        config false;
                        description
                            "state container for MLD SSM static group configurations";
                        uses mld-if-ssm-static-grp-config;
                    } // END of state-container definition.
                } // End of ssm-static-group-list
            } // END of ssm-static-groups-container definition.
        } // End of interface-list
    } // END of interfaces-container definition.
    } // END of interfaces-grouping definition.


}
