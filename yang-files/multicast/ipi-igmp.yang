/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-igmp.yang
*
*/

module ipi-igmp {

    yang-version 1.1;

    namespace   "http://www.ipinfusion.com/yang/ocnos/ipi-igmp";

    prefix "ipi-igmp";

    import ietf-inet-types {
        prefix inet;
        revision-date 2013-07-15;
    }

    import ipi-network-instance {
        prefix ipi-network-instance;
        revision-date 2022-06-01;
    }

    import ipi-vrf {
        prefix ipi-vrf;
        revision-date 2022-07-13;
    }

    import ipi-igmp-types {
        prefix ipi-igmp-types;
        revision-date 2022-06-01;
    }

    import feature-list {
        prefix feature-list;
        revision-date 2023-02-21;
    }

    include ipi-igmp-interface { revision-date 2022-06-01;}
    include ipi-igmp-groups { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Data model for IGMP Module";


    revision "2022-06-20" {
        description "Added custom-error-codes to disable-ssm-map and disable-tos-check attributes";
        reference " 0.4.1.";
    }

    revision "2022-06-01" {
        description "Updated the yang file with feature";
        reference " 0.4.0.";
    }

    revision "2022-02-07" {
        description "Renamed CML_YES_NO_T to IGMP_YES_NO_T in igmp-groups";
        reference " 0.3.0.";
    }

    revision "2021-12-16" {
        description "Removing relevant db-triggers for igmp and igmp-interface";
        reference " 0.2.0.";
    }

    revision "2021-11-15" {
        description "Initial Version";
        reference " 0.1.0.";
    }

    grouping igmp-instance-config {
        description
            "IGMP Instance Configurations";
        leaf vrf-name  {
            type  leafref {
                path  "/ipi-network-instance:network-instances/ipi-network-instance:network-instance/ipi-vrf:vrf/ipi-vrf:config/ipi-vrf:vrf-name";
            }
            description "VPN routing/forwarding Instance name";
        } // END of vrf-name definition.

        leaf disable-ssm-map  {
            type  empty;
            description "Use this attribute to enable the IGMP operation on an interface. This
                        command enables IGMP operation in standalone mode,
                        and can be used to learn local-membership information prior to
                        enabling a multicast routing protocol on the interface.
                        This command will has no effect on interfaces configured for IGMP
                        proxy.";
        } // END of disable-ssm-map definition.

        leaf disable-tos-check  {
            type  empty;
            description "Use this attribute to disable TOS check for Internetwork Control";
        } // END of disable-tos-check definition.

    } // END of igmp-instance-config definition.
    grouping igmp-group-membership-config {
        description
            "IGMP Group Membership Configurations";
        leaf member-limit  {
            type  uint32 {
                 range "1..2097152"  {
                    description "1..2097152: Supported range 1 - 2097152";
                 }
            }
            default "1";
            description "Use this attribute to set the maximum number of group membership
                        states, at either the router level or at the interface
                        level. Once the specified number of group memberships is reached, all
                        further local-memberships are ignored.
                        Optionally, an exception access-list can be configured to specify the
                        group-address(es) to be excluded from being subject to the limit.
                        This command applies to interfaces configured for IGMP Layer-3
                        multicast protocols and IGMP Proxy. The limit applies,
                        individually, to each of its constituent interfaces.";
        } // END of member-limit definition.

        leaf limit-exception-acl  {
            when " /ipi-igmp:igmp/ipi-igmp:vrfs/ipi-igmp:vrf/ipi-igmp:group-membership-control/ipi-igmp:config/ipi-igmp:member-limit ";
            type  string {
                length "1..1965";
                pattern "[^?' =,>|]+";
            }
            description "Use this attribute to set the maximum number of group membership
                        states, at either the router level or at the interface
                        level. Once the specified number of group memberships is reached, all
                        further local-memberships are ignored.
                        Optionally, an exception access-list can be configured to specify the
                        group-address(es) to be excluded from being subject to the limit.
                        This command applies to interfaces configured for IGMP Layer-3
                        multicast protocols and IGMP Proxy. The limit applies,
                        individually, to each of its constituent interfaces.";
        } // END of limit-exception-acl definition.

    } // END of igmp-group-membership-config definition.
    grouping igmp-group-membership-state {
        description
            "IGMP Group Membership State Information";
        leaf current-states-count  {
            type  uint32;
            config false;
            description "Current group membership record states for this IGMP instance.";
        } // END of current-states-count definition.

    } // END of igmp-group-membership-state definition.
    grouping igmp-instance-ssm-map-config {
        description
            "IGMP Instance SSM Map Configurations";
        leaf group-ranges-acl  {
            type  string {
                length "1..1965";
                pattern "[^?' =,>|]+";
            }
            description "Use this attribute to specify SSM Static Access List";
        } // END of group-ranges-acl definition.

        leaf source  {
            type  inet:ipv4-address;
            description "Use this attribute to specify the static mode of defining SSM mapping.
                        SSM mapping statically assigns sources to IGMPv1 and IGMPv2 groups to
                        translate such (star G) groups memberships
                        to (S,G) memberships for use with PIMSSM.This attribute applies to
                        interfaces configured
                        for IGMP Layer-3 multicast protocols and IGMP Proxy.";
        } // END of source definition.

    } // END of igmp-instance-ssm-map-config definition.
    grouping igmp-debug-config {
        description
            "IGMP debug configurations";
        leaf debug-options  {
            type  ipi-igmp-types:igmp_debug_options_t;
            description "Use this attribute to enable igmp debugging configurations";
        } // END of debug-options definition.

    } // END of igmp-debug-config definition.
    grouping igmp-debug-state {
        description
            "IGMP debug state information";
        leaf terminal-debug-status-on  {
            type  ipi-igmp-types:igmp_debug_options_t;
            description "Use this attribute to display igmp terminal debug options enabled";
        } // END of terminal-debug-status-on definition.

    } // END of igmp-debug-state definition.

    grouping  igmp-grouping {
    description
        "IGMP configurations";
    container igmp {
        if-feature feature-list:HAVE_MRIBD;
        description
            "IGMP configurations";
        container vrfs {
            description
                "IGMP vrf configurations";

            list vrf {
                key "vrf-name";
                description
                    "IGMP vrf instance configurations";
                leaf vrf-name  {
                    type  leafref {
                        path  "../config/vrf-name";
                    }
                    description "VPN routing/forwarding Instance name";
                } // END of vrf-name definition.

                container config {
                    description
                        "config container for IGMP vrf instance configurations";
                    uses igmp-instance-config;
                } // END of config-container definition.
                container state {
                    config false;
                    description
                        "state container for IGMP vrf instance configurations";
                    uses igmp-instance-config;
                } // END of state-container definition.
                container group-membership-control {
                    description
                        "IGMP Group Membership Control Configurations";
                    container config {
                        description
                            "config container for IGMP group membership control configurations";
                        uses igmp-group-membership-config;
                    } // END of config-container definition.
                    container state {
                        config false;
                        description
                            "state container for IGMP group membership control configurations";
                        uses igmp-group-membership-config;
                        uses igmp-group-membership-state;
                    } // END of state-container definition.
                } // END of group-membership-control-container definition.
                container ssm {
                    description
                        "IGMP SSM Configurations";
                    container static-mappings {
                        description
                            "IGMP Static-Mappings Container";

                        list static-mapping {
                            key "group-ranges-acl source";
                            description
                                "IGMP Static-Mapping Instance configurations";
                            leaf group-ranges-acl  {
                                type  leafref {
                                    path  "../config/group-ranges-acl";
                                }
                                description "Use this attribute to specify SSM Static Access List";
                            } // END of group-ranges-acl definition.

                            leaf source  {
                                type  leafref {
                                    path  "../config/source";
                                }
                                description "Use this attribute to specify the static mode of defining SSM mapping.
                                            SSM mapping statically assigns sources to IGMPv1 and IGMPv2 groups to
                                            translate such (star G) groups memberships
                                            to (S,G) memberships for use with PIMSSM.This attribute applies to
                                            interfaces configured
                                            for IGMP Layer-3 multicast protocols and IGMP Proxy.";
                            } // END of source definition.

                            container config {
                                description
                                    "config container for IGMP static-mapping configurations";
                                uses igmp-instance-ssm-map-config;
                            } // END of config-container definition.
                            container state {
                                config false;
                                description
                                    "state container for IGMP static-mapping configurations";
                                uses igmp-instance-ssm-map-config;
                            } // END of state-container definition.
                        } // End of static-mapping-list
                    } // END of static-mappings-container definition.
                } // END of ssm-container definition.
                container debug {
                    description
                        "IGMP Debug Configurations";
                    container config {
                        description
                            "config container for IGMP debug configurations";
                        uses igmp-debug-config;
                    } // END of config-container definition.
                    container state {
                        config false;
                        description
                            "state container for IGMP debug configurations";
                        uses igmp-debug-config;
                        uses igmp-debug-state;
                    } // END of state-container definition.
                } // END of debug-container definition.
            } // End of vrf-list
        } // END of vrfs-container definition.
        uses interfaces-grouping;
        uses group-membership-tree-grouping;
    } // END of igmp-container definition.
    } // END of igmp-grouping definition.

    uses igmp-grouping;

    rpc igmp-terminal-debug-on {
        if-feature feature-list:HAVE_MRIBD;
        description "Use this RPC to enable terminal debugging options for IGMP";
        input  {
            leaf vrf-name  {
                type string;
                default "default";
                description "VPN routing/forwarding Instance name";
            }
            leaf term-debug-options  {
                type ipi-igmp-types:igmp_debug_options_t;
                mandatory true;
                description "Use this attribute to enable igmp debugging configurations";
            }
        }
    }

    rpc igmp-terminal-debug-off {
        if-feature feature-list:HAVE_MRIBD;
        description "Use this RPC to disable terminal debugging options for IGMP";
        input  {
            leaf vrf-name  {
                type string;
                default "default";
                description "VPN routing/forwarding Instance name";
            }
            leaf term-debug-options  {
                type ipi-igmp-types:igmp_debug_options_t;
                mandatory true;
                description "Use this attribute to enable igmp debugging configurations";
            }
        }
    }

    rpc igmp-clear-all-groups {
        if-feature feature-list:HAVE_MRIBD;
        description "Use this attribute to clear all IGMP local-memberships on all
                    interfaces. This attributes applies to interfaces configured for IGMP
                    Layer-3 multicast protocols, or IGMP Proxy.";
        input  {
            leaf vrf-name  {
                type string;
                default "default";
                description "VPN routing/forwarding Instance name";
            }
            leaf clear-all  {
                type empty;
                mandatory true;
                description "Use this attribute to clear all IGMP local-memberships on all
                            interface";
            }
        }
    }

    rpc igmp-clear-group-on-interface {
        if-feature feature-list:HAVE_MRIBD;
        description "Use this RPC to clear all IGMP local-memberships on all interfaces
                    based on Group Address.             This attributes applies to
                    interfaces configured for IGMP Layer-3 multicast protocols, or IGMP
                    Proxy";
        input  {
            leaf vrf-name  {
                type string;
                default "default";
                description "VPN routing/forwarding Instance name";
            }
            leaf group-address  {
                type inet:ipv4-address;
                mandatory true;
                description "Group Address";
            }
            leaf if-name  {
                type string;
                mandatory true;
                description "Interface Name";
            }
        }
    }

    rpc igmp-clear-all-groups-on-interface {
        if-feature feature-list:HAVE_MRIBD;
        description "Use this RPC to clear all IGMP local-memberships on all interfaces.
                    This attributes applies to interfaces configured for IGMP Layer-3
                    multicast protocols, or IGMP Proxy.";
        input  {
            leaf vrf-name  {
                type string;
                default "default";
                description "VPN routing/forwarding Instance name";
            }
            leaf if-name  {
                type string;
                mandatory true;
                description "Interface Name";
            }
        }
    }

    rpc igmp-clear-group {
        if-feature feature-list:HAVE_MRIBD;
        description "Use this attribute to clear all IGMP local-memberships on  group. This
                    attributes applies to interfaces configured for IGMP Layer-3 multicast
                    protocols, or IGMP Proxy.";
        input  {
            leaf vrf-name  {
                type string;
                default "default";
                description "VPN routing/forwarding Instance name";
            }
            leaf group-address  {
                type inet:ipv4-address;
                mandatory true;
                description "Group Address";
            }
        }
    }

}
