/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-evpn-srv6.yang
*
*/

module ipi-evpn-srv6 {

    yang-version 1.1;

    namespace   "http://www.ipinfusion.com/yang/ocnos/ipi-evpn-srv6";

    prefix "ipi-evpn-srv6";

    import ietf-inet-types {
        prefix inet;
        revision-date 2013-07-15;
    }

    import ipi-vrf {
        prefix ipi-vrf;
        revision-date 2022-07-13;
    }

    import ipi-network-instance {
        prefix ipi-network-instance;
        revision-date 2022-06-01;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for EVPN-SRV6 protocol";


    revision "2022-06-01" {
        description "Updated the yang file with feature";
        reference " 0.2.0.";
    }

    revision "2022-05-13" {
        description "Initial Version";
        reference " 0.1.0.";
    }

    grouping evpn-srv6-global-config {
        description
            "Grouping for global evpn-srv6 configuration";
        leaf enabled  {
            type  empty;
            mandatory true;
            description "Use this attribute to enable EVPN-SRV6 module. Without this
                        attribute evpn srv6 functionality can not be achieved";
        } // END of enabled definition.

        leaf vtep-ipv6-address  {
            type  inet:ipv6-address;
            description "Use this attribute to set source vtep global ip address.
                        This will be treated at evpn srv6 tunnel source address";
        } // END of vtep-ipv6-address definition.

    } // END of evpn-srv6-global-config definition.
    grouping evpn-srv6-tenant-top {
        description
            "Grouping for EVPN-SRV6 tenant top";
        container tenants {
            description
                "Tenants list";

            list tenant {
            when " /ipi-evpn-srv6:evpn-srv6/ipi-evpn-srv6:global/ipi-evpn-srv6:config ";
                key "tenant-identifier";
                description
                    "Tenant configurations for EVPN-SRV6";
                leaf tenant-identifier  {
                    type  leafref {
                        path  "../config/tenant-identifier";
                    }
                    description "Tenant Identifier";
                } // END of tenant-identifier definition.

                container config {
                    description
                        "Configuration data";
                    uses evpn-srv6-tenant-config;
                    uses evpn-srv6-tenant-global-config;
                } // END of config-container definition.
                container state {
                    config false;
                    description
                        "Operational state data";
                    uses evpn-srv6-tenant-config;
                    uses evpn-srv6-tenant-global-config;
                } // END of state-container definition.
            } // End of tenant-list
        } // END of tenants-container definition.
    } // END of evpn-srv6-tenant-top definition.
    grouping evpn-srv6-tenant-global-config {
        description
            "Grouping for EVPN-SRV6 tenant global configuration";
        leaf tenant-identifier  {
            type  uint32 {
                 range "1..16777215"  {
                    description "1..16777215: Supported range 1 - 16777215";
                 }
            }
            description "Tenant Identifier";
        } // END of tenant-identifier definition.

        leaf vpws-identifier  {
            if-feature feature-list:HAVE_EVPN_VPWS;
            type  uint32 {
                 range "1..16777215"  {
                    description "1..16777215: Supported range 1 - 16777215";
                 }
            }
            description "Use this attribute to create vpws tenant";
        } // END of vpws-identifier definition.

    } // END of evpn-srv6-tenant-global-config definition.
    grouping evpn-srv6-tenant-config {
        description
            "Grouping for EVPN-SRV6 tenant configuration";
        leaf vrf-name  {
            type  leafref {
                path  "/ipi-network-instance:network-instances/ipi-network-instance:network-instance/ipi-vrf:vrf/ipi-vrf:config/ipi-vrf:vrf-name";
            }
            description "Use this attribute to map vrf to carry EVPN routes";
        } // END of vrf-name definition.

        leaf tenant-description  {
            type  string {
                length "1..1965";
                pattern "[^?' =,>|]+";
            }
            description "Use this attribute to set evpn-srv6 tenant identifier name";
        } // END of tenant-description definition.

        leaf tunnel-policy-name  {
            if-feature feature-list:HAVE_MPLS_SERVICE_MAPPING_OR_HAVE_SRV6;
            type  string {
                length "1..127";
                pattern "[^?' =,>|]+";
            }
            description "Transport Tunnel Selection Policy";
        } // END of tunnel-policy-name definition.

        leaf srv6-locator-name  {
            type  string {
                length "1..1965";
                pattern "[^?' =,>|]+";
            }
            description "Locator name";
        } // END of srv6-locator-name definition.

    } // END of evpn-srv6-tenant-config definition.

    grouping  evpn-srv6-grouping {
    description
        "EVPN-SRV6 global level container";
    container evpn-srv6 {
        if-feature feature-list:HAVE_SRV6_EVPN;
        if-feature feature-list:HAVE_NVO;
        if-feature feature-list:HAVE_SRV6;
        if-feature feature-list:HAVE_BGP_EVPN;
        description
            "EVPN-SRV6 global level container";
        container global {
            when " /ipi-evpn-srv6:evpn-srv6/ipi-evpn-srv6:global/ipi-evpn-srv6:config ";
            description
                "Configuration data for EVPN-SRV6 global capability configuration";
            container config {
                presence "Enable EVPN-SRV6";
                description
                    "Configuration data";
                uses evpn-srv6-global-config;
            } // END of config-container definition.
            container state {
                config false;
                description
                    "Operational state data";
                uses evpn-srv6-global-config;
            } // END of state-container definition.
        } // END of global-container definition.
        uses evpn-srv6-tenant-top;
    } // END of evpn-srv6-container definition.
    } // END of evpn-srv6-grouping definition.

    uses evpn-srv6-grouping;

}
