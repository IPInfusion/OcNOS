/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : cml-data-types.yang
*
*/

module cml-data-types {

    yang-version 1.1;

    namespace   "http://www.ipinfusion.com/yang/ocnos/cml-data-types";

    prefix "cml-data-types";

    import ietf-inet-types {
        prefix inet;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the cml-data-types";


    revision "2022-09-30" {
        description "Add notification severity and class types";
        reference " 0.10.6.";
    }

    revision "2022-04-04" {
        description "Added if-feature whereever needed";
        reference " 0.10.5.";
    }

    revision "2022-03-22" {
        description "Removed datatypes specific to MRIB IPv6 datamodel";
        reference " 0.10.4.";
    }

    revision "2022-03-15" {
        description "Removed datatypes specific to PIM datamodel";
        reference " 0.10.3.";
    }

    revision "2022-02-18" {
        description "Removed datatypes specific to ERPSv2 datamodel";
        reference " 0.10.2.";
    }

    revision "2022-02-04" {
        description "Removed deprecated Authentication data types";
        reference " 0.10.1.";
    }

    revision "2022-01-31" {
        description "Removing datatypes specific to MLD Snooping Datamodel";
        reference " 0.10.0.";
    }

    revision "2022-01-07" {
        description "Removed unused data types ";
        reference " 0.9.0.";
    }

    revision "2021-12-09" {
        description "Removed data types specific to CFM data model";
        reference " 0.8.1.";
    }

    revision "2021-11-15" {
        description "Removed datatypes specific to IGMP datamodel";
        reference " 0.8.0.";
    }

    revision "2021-10-06" {
        description "Change helpstring for provider-mstp and provider-rstp";
        reference " 0.7.0.";
    }

    revision "2021-09-03" {
        description "Update descriptions of attribute";
        reference " 0.6.2.";
    }

    revision "2021-08-09" {
        description "Removed attributes ununsed L2 datatypes and moved L2 specific to it's respective files";
        reference " 0.6.1.";
    }

    revision "2021-07-01" {
        description "Removed attributes specific to MSTP data model";
        reference " 0.6.0.";
    }

    revision "2021-05-03" {
        description "Added support for import by revision-date";
        reference " 0.5.0.";
    }

    revision "2021-03-18" {
        description "Update CML_RAW_STRING_T yang-type";
        reference " 0.4.0.";
    }

    revision "2021-01-27" {
        description "Added CVLAN configurations";
        reference " 0.3.0.";
    }

    revision "2020-12-15" {
        description "Change to have data-types in lower case instead of camel case";
        reference " 0.2.0.";
    }

    revision "2018-06-21" {
        description "Initial Version";
        reference " 0.1.0.";
    }



    typedef  cml_line_t {
        type string {
            pattern "[^?'=,>|]*";
        }
        description "type definition for CML_LINE_T";
    }

    typedef  cml_host_string_t {
        type string;
        description "type definition for CML_HOST_STRING_T";
    }

    typedef  cml_range_t {
        type string {
            pattern "[^?'=>|]*";
        }
        description "type definition for CML_RANGE_T";
    }

    typedef  cml_vm_affinity_t {
        type string {
            pattern "[^?' =>|]*";
        }
        description "type definition for CML_VM_AFFINITY_T";
    }

    typedef  cml_mac_addr_t {
        type string;
        description "type definition for CML_MAC_ADDR_T";
    }

    typedef  cml_hostname_t {
        type union {
            type inet:ip-address {

            }
            type string {

            }
        }
        description "type definition for CML_HOSTNAME_T";
    }

    typedef  cml_hostpname_t {
        type union {
            type inet:ip-address {

            }
            type cml_host_string_t {

            }
        }
        description "type definition for CML_HOSTPNAME_T";
    }

    typedef  cml_ipv4_addr_or_prefix_t {
        type union {
            type inet:ipv4-address {

            }
            type inet:ipv4-prefix {

            }
        }
        description "type definition for CML_IPV4_ADDR_OR_PREFIX_T";
    }

    typedef  cml_ip_prefix_addr_t {
        type union {
            type inet:ipv4-prefix {

            }
            type inet:ipv6-prefix {

            }
        }
        description "type definition for CML_IP_PREFIX_ADDR_T";
    }

    typedef  cml_discardforward_t {
        type enumeration {
            enum discard {
                value 0;
                description "discard";
            }
            enum forward {
                value 1;
                description "forward";
            }
        }
        description "type definition for CML_DISCARDFORWARD_T";
    }

    typedef  cml_enable_disable_t {
        type enumeration {
            enum disable {
                value 0;
                description "Disable";
            }
            enum enable {
                value 1;
                description "Enable";
            }
        }
        description "type definition for CML_ENABLE_DISABLE_T";
    }

    typedef  cml_spanningtree_enable_disable_t {
        type enumeration {
            enum enable {
                value 0;
                description "Enable";
            }
            enum disable {
                value 1;
                description "Disable";
            }
        }
        description "type definition for CML_SPANNINGTREE_ENABLE_DISABLE_T";
    }

    typedef  cml_ifname_t {
        type string;
        description "type definition for CML_IFNAME_T";
    }

    typedef  dhcp6_duid_type_t {
        type enumeration {
            enum ll {
                value 1;
                description "Linklayer address";
            }
            enum llt {
                value 2;
                description "Linklayer address plus timestamp";
            }
        }
        description "type definition for DHCP6_DUID_TYPE_T";
    }

    typedef  cml_nsm_mpls_log_t {
        type bits {
            bit error {
                position 0;
                description "Log Error message in MPLS Forwarder";
            }
            bit warning {
                position 1;
                description "Log Warning message in MPLS Forwarder";
            }
            bit debug {
                position 2;
                description "Log Debug messages in MPLS Forwarder";
            }
            bit notice {
                position 3;
                description "Log Notice messages in MPLS Forwarder";
            }
        }
        description "type definition for CML_NSM_MPLS_LOG_T";
    }

    typedef  cml_on_off_t {
        type enumeration {
            enum off {
                value 0;
                description "off";
            }
            enum on {
                value 1;
                description "on";
            }
        }
        description "type definition for CML_ON_OFF_T";
    }

    typedef  cml_bridge_spanmode_t {
        type enumeration {
            enum stp {
                value 1;
                description "IEEE 801.1Q spanning-tree protocol";
            }
            enum stp-vlan-bridge {
                value 2;
                description "IEEE 801.1Q spanning-tree protocol";
            }
            enum rstp {
                value 3;
                description "IEEE 801.1w rapid spanning-tree protocol";
            }
            enum rstp-vlan-bridge {
                value 4;
                description "IEEE 801.1w rapid spanning-tree protocol";
            }
            enum mstp {
                value 5;
                description "IEEE 802.1s multiple spanning-tree protocol";
            }
            enum provider-rstp {
                value 6;
                description "IEEE 802.1s provider rapid spanning-tree protocol";
            }
            enum provider-mstp {
                value 7;
                description "IEEE 802.1s provider multiple spanning-tree protocol";
            }
            enum rpvst+ {
                value 12;
                description "IEEE 801.1w rapid per VLAN spanning-tree protocol";
            }
        }
        description "type definition for CML_BRIDGE_SPANMODE_T";
    }

    typedef  cml_enablebpdurx_t {
        type enumeration {
            enum disableBPDUrx {
                value 0;
                description "disableBPDUrx";
            }
            enum enableBPDUrx {
                value 1;
                description "enableBPDUrx";
            }
        }
        description "type definition for CML_ENABLEBPDURX_T";
    }

    typedef  cml_backbone_t {
        type enumeration {
            enum backbone {
                value 33;
                description "Specifies the backbone bridge group name";
            }
        }
        description "type definition for CML_BACKBONE_T";
    }

    typedef  cml_tesi_mode_t {
        type enumeration {
            enum passive {
                value 1;
                description "mode from active to passive";
            }
            enum active {
                value 2;
                description "mode from passive to active";
            }
        }
        description "type definition for CML_TESI_MODE_T";
    }

    typedef  cml_pnpadddel_t {
        type enumeration {
            enum add {
                value 1;
                description "deletes the subsequest interface from this tesi";
            }
            enum delete {
                value 2;
                description "interface name";
            }
        }
        description "type definition for CML_PNPADDDEL_T";
    }

    typedef  cml_nsmvlanport_mode_t {
        type enumeration {
            enum pnp {
                value 6;
                description "Default VLAN configured on Provider Network Port";
            }
            enum cnp {
                value 8;
                description "Default VLAN configured on Customer Network Port";
            }
            enum pip {
                value 10;
                description "Default VLAN configured on Provider Instance Port";
            }
            enum cbp {
                value 11;
                description "";
            }
        }
        description "type definition for CML_NSMVLANPORT_MODE_T";
    }

    typedef  cml_cmbckinstance_t {
        type uint32 {
             range 1..16777214;
        }
        description "type definition for CML_CMBCKINSTANCE_T";
    }

    typedef  cml_instance_name_t {
        type string;
        description "type definition for CML_INSTANCE_NAME_T";
    }

    typedef  cml_svlan_instance_name_t {
        type union {
            type cml_cmbckinstance_t {

            }
            type cml_instance_name_t {

            }
        }
        description "type definition for CML_SVLAN_INSTANCE_NAME_T";
    }

    typedef  cml_cmbckbone_instance_t {
        type union {
            type cml_cmbckinstance_t {

            }
            type cml_instance_ifname_t {

            }
        }
        description "type definition for CML_CMBCKBONE_INSTANCE_T";
    }

    typedef  cml_instance_ifname_t {
        type string;
        description "type definition for CML_INSTANCE_IFNAME_T";
    }

    typedef  cml_vip_traffic_t {
        type enumeration {
            enum all {
                value 0;
                description "Ingress/egress allowed";
            }
            enum ingress {
                value 1;
                description "Configures ingress service flow";
            }
            enum egress {
                value 2;
                description "Configures egress service flow";
            }
        }
        description "type definition for CML_VIP_TRAFFIC_T";
    }

    typedef  cml_beb_mode_t {
        type enumeration {
            enum tx {
                value 0;
                description "Transmit only";
            }
            enum rx {
                value 1;
                description "Receive only";
            }
            enum rxtx {
                value 2;
                description "Transmit and Receive";
            }
            enum none {
                value 3;
                description "Neither tx nor rx";
            }
        }
        description "type definition for CML_BEB_MODE_T";
    }

    typedef  cml_bridge_backbone_t {
        type union {
            type cml_backbone_t {

            }
            type uint8 {
                range "1..32";

            }
        }
        description "type definition for CML_BRIDGE_BACKBONE_T";
    }

    typedef  cml_aspteisid_t {
        type enumeration {
            enum add {
                value 1;
                description "adds a new ISID to this aps group";
            }
            enum delete {
                value 2;
                description "deletes an existing ISID from this aps group";
            }
        }
        description "type definition for CML_ASPTEISID_T";
    }

    typedef  cml_cnpins_t {
        type uint32 {
             range 1..16777214;
        }
        description "type definition for CML_CNPINS_T";
    }

    typedef  cml_cnp_instance_t {
        type union {
            type cml_cnpins_t {

            }
            type cml_cnp_instance_ifname_t {

            }
        }
        description "type definition for CML_CNP_INSTANCE_T";
    }

    typedef  cml_cnp_instance_ifname_t {
        type string;
        description "type definition for CML_CNP_INSTANCE_IFNAME_T";
    }

    typedef  cml_vr_protocol_t {
        type bits {
            bit rip {
                position 1;
                description "Routing Information Protocol (RIP)";
            }
            bit ipv6-rip {
                position 2;
                if-feature feature-list:HAVE_IPV6;
                description "Internet Protocol Version 6,Routing Information Protocol (RIP)";
            }
            bit ospf {
                position 3;
                description "Open Shortest Path First (OSPF)";
            }
            bit ipv6-ospf {
                position 4;
                if-feature feature-list:HAVE_IPV6;
                description "Internet Protocol Version 6, Open Shortest Path First (OSPF)";
            }
            bit isis {
                position 5;
                description "Intermediate System - Intermediate System (IS-IS)";
            }
            bit pim {
                position 6;
                description "Protocol Independent Multicast (PIM)";
            }
            bit vrrp {
                position 7;
                description "Virtual Router Redundancy Protocol (VRRP)";
            }
            bit bgp {
                position 9;
                description "Border Gateway Protocol (BGP)";
            }
        }
        description "type definition for CML_VR_PROTOCOL_T";
    }

    typedef  cml_pcep_path_dyn_t {
        type enumeration {
            enum pce {
                value 1;
                description "path computation element";
            }
        }
        description "type definition for CML_PCEP_PATH_DYN_T";
    }

    typedef  cml_rip_direction_t {
        type enumeration {
            enum in {
                value 0;
                description "For incoming updates";
            }
            enum out {
                value 1;
                description "For outgoing updates";
            }
        }
        description "type definition for CML_RIP_DIRECTION_T";
    }

    typedef  cml_rip_metric_t {
        type enumeration {
            enum disable {
                value 0;
                description "Disables updating metric consistent with Cisco";
            }
            enum enable {
                value 1;
                description "Enables updating metric consistent with Cisco";
            }
        }
        description "type definition for CML_RIP_METRIC_T";
    }

    typedef  cml_rip_split_horizon_t {
        type enumeration {
            enum split-horizon {
                value 0;
                description "Perform split horizon";
            }
            enum split-horizon-poisoned {
                value 1;
                description "Perform split horizon,Perform poisoned reverse";
            }
        }
        description "type definition for CML_RIP_SPLIT_HORIZON_T";
    }

    typedef  cml_urpf_mode_t {
        type enumeration {
            enum any {
                value 1;
                description "Source is reachable via any interface";
            }
            enum rx {
                value 2;
                description "Source is reachable via interface on which packet was received";
            }
            enum any-allow-default {
                value 3;
                if-feature feature-list:NOT_HAVE_DUNE;
                description "Source is reachable via any interface, Loose Default Route Unicast Reverse Path Forwarding";
            }
        }
        description "type definition for CML_URPF_MODE_T";
    }

    typedef  cml_ripng_debug_t {
        type bits {
            bit events {
                position 1;
                description "RIP events";
            }
            bit packet-send {
                position 2;
                description "RIP packets,RIP send packets";
            }
            bit packet-recv {
                position 3;
                description "RIP packets, RIP receive packets";
            }
            bit nsm {
                position 5;
                description "RIP NSM information";
            }
            bit rib {
                position 6;
                if-feature feature-list:HAVE_RIBD;
                description "RIP RIB information";
            }
        }
        description "type definition for CML_RIPNG_DEBUG_T";
    }

    typedef  cml_ripng_split_horizon_t {
        type enumeration {
            enum split-horizon {
                value 0;
                description "Perform split horizon";
            }
            enum split-horizon-poisoned {
                value 1;
                description "Perform split horizon,Perform poisoned reverse";
            }
        }
        description "type definition for CML_RIPNG_SPLIT_HORIZON_T";
    }

    typedef  cml_ripng_instance_t {
        type enumeration {
            enum rip {
                value 1;
                description "Routing Information Protocol (RIP)";
            }
        }
        description "type definition for CML_RIPNG_INSTANCE_T";
    }

    typedef  cml_ripng_redist_protos_t {
        type enumeration {
            enum kernel {
                value 0;
                description "Kernel routes";
            }
            enum connected {
                value 1;
                description "Connected";
            }
            enum static {
                value 2;
                description "Static routes";
            }
            enum ospf6 {
                value 3;
                description "Open Shortest Path First (OSPF)";
            }
            enum isis {
                value 4;
                description "ISO IS-IS";
            }
            enum bgp {
                value 5;
                description "Border Gateway Protocol (BGP)";
            }
        }
        description "type definition for CML_RIPNG_REDIST_PROTOS_T";
    }

    typedef  cml_ripng_vrf_redist_protos_t {
        type enumeration {
            enum connected {
                value 1;
                description "Connected";
            }
            enum static {
                value 2;
                description "Static routes";
            }
            enum ospf6 {
                value 3;
                description "Open Shortest Path First (OSPF)";
            }
            enum bgp {
                value 5;
                description "Border Gateway Protocol (BGP)";
            }
        }
        description "type definition for CML_RIPNG_VRF_REDIST_PROTOS_T";
    }

    typedef  cml_ripng_filtering_t {
        type enumeration {
            enum in {
                value 0;
                description "For incoming updates";
            }
            enum out {
                value 1;
                description "For outgoing updates";
            }
        }
        description "type definition for CML_RIPNG_FILTERING_T";
    }

    typedef  cml_ripng_route_t {
        type enumeration {
            enum kernel {
                value 1;
                description "Kernel routes";
            }
            enum connected {
                value 2;
                description "Connected";
            }
            enum static {
                value 3;
                description "Static routes";
            }
            enum isis {
                value 4;
                description "ISO IS-IS";
            }
            enum ospf6 {
                value 5;
                description "Open Shortest Path First (OSPF)";
            }
            enum bgp {
                value 6;
                description "Border Gateway Protocol (BGP)";
            }
            enum rip {
                value 7;
                description "Routing Information Protocol (RIP)";
            }
            enum all {
                value 8;
                description "all of the RIP routing tabl";
            }
        }
        description "type definition for CML_RIPNG_ROUTE_T";
    }

    typedef  cml_confidencetype_t {
        type enumeration {
            enum native {
                value 1;
                description "Confidence level associated with MAC learned after decapsulation of frames";
            }
            enum decap {
                value 2;
                description "Confidence level associated with MAC learned from native frames";
            }
            enum static {
                value 3;
                description "Confidence level associated with MAC that are statically configured";
            }
        }
        description "type definition for CML_CONFIDENCETYPE_T";
    }

    typedef  cml_esadi_t {
        type enumeration {
            enum enable {
                value 1;
                description "Enable ESADI";
            }
            enum disable {
                value 2;
                description "Disable ESADI";
            }
        }
        description "type definition for CML_ESADI_T";
    }

    typedef  cml_trill_t {
        type enumeration {
            enum disable {
                value 0;
                description "Disable VLAN pruning";
            }
            enum enable {
                value 1;
                description "Enable VLAN pruning";
            }
        }
        description "type definition for CML_TRILL_T";
    }

    typedef  cml_isunicast_t {
        type enumeration {
            enum multicast {
                value 0;
                description "Enable Multipath for multicast";
            }
            enum unicast {
                value 1;
                description "Enable Multipath for unicast";
            }
        }
        description "type definition for CML_ISUNICAST_T";
    }

    typedef  cml_configtype_t {
        type enumeration {
            enum broadcast {
                value 1;
                description "Link is broadcast multi-access";
            }
            enum point-to-point {
                value 2;
                description "Link is point-to-point";
            }
        }
        description "type definition for CML_CONFIGTYPE_T";
    }

    typedef  cml_nsm_dcb_qcn_mode_t {
        type enumeration {
            enum admin {
                value 1;
                description "Admin-Mode";
            }
            enum auto {
                value 2;
                description "Automatic mode - LLDP should be enabled";
            }
            enum component {
                value 3;
                description "Defense mode same as the bridge level defense mode";
            }
        }
        description "type definition for CML_NSM_DCB_QCN_MODE_T";
    }

    typedef  cml_mapping_type_t {
        type enumeration {
            enum admin {
                value 1;
                description "Admin-Mode";
            }
            enum auto {
                value 2;
                description "Automatic mode - LLDP should be enabled";
            }
            enum component {
                value 3;
                description "Defense mode same as the bridge level defense mode";
            }
        }
        description "type definition for CML_MAPPING_TYPE_T";
    }

    typedef  cml_ets_mode_t {
        type enumeration {
            enum on {
                value 1;
                description "ON to force enable Enhanced-trasnsmission-selection";
            }
            enum auto {
                value 2;
                description "AUTO to negotiate Enhanced-transmission-selection capabilities)";
            }
        }
        description "type definition for CML_ETS_MODE_T";
    }

    typedef  cml_dcbstate_t {
        type enumeration {
            enum off {
                value 0;
                description "disable";
            }
            enum on {
                value 1;
                description "enable";
            }
        }
        description "type definition for CML_DCBSTATE_T";
    }

    typedef  cml_prioflag_t {
        type enumeration {
            enum remove {
                value 0;
                description "remove";
            }
            enum add {
                value 1;
                description "add";
            }
        }
        description "type definition for CML_PRIOFLAG_T";
    }

    typedef  cml_protoid_t {
        type enumeration {
            enum tcp {
                value 2;
                description "Protocol Type tcp";
            }
            enum udp {
                value 3;
                description "Protocol Type udp";
            }
            enum both-tcp-udp {
                value 4;
                description "Protocol Type both-tcp-udp";
            }
            enum neither-tcp-udp {
                value 5;
                description "Protocol Type neither-tcp-udp";
            }
        }
        description "type definition for CML_PROTOID_T";
    }

    typedef  cml_defensemode_t {
        type enumeration {
            enum disabled {
                value 1;
                description "Disabled Mode";
            }
            enum interior {
                value 2;
                description "Interior Mode";
            }
            enum interior-ready {
                value 3;
                description "Interior Ready Mode";
            }
            enum edge {
                value 4;
                description "Edge Mode";
            }
        }
        description "type definition for CML_DEFENSEMODE_T";
    }

    typedef  cml_vr_config_t {
        type enumeration {
            enum read {
                value 0;
                description "Read file";
            }
            enum write {
                value 1;
                description "Write file";
            }
        }
        description "type definition for CML_VR_CONFIG_T";
    }

    typedef  if_l2process_clear_t {
        type enumeration {
            enum peer {
                value 0;
                description "Clear stats for Peer protocol pkts";
            }
            enum tunnel {
                value 1;
                description "Clear stats for Tunnel protocol pkts";
            }
            enum discard {
                value 2;
                description "Clear stats for Discard protocol pkts";
            }
            enum tunnel-discard {
                value 3;
                description "Clear stats for Tunnel discard protocol pkts";
            }
            enum all {
                value 4;
                description "Clear stats for all protocol pkts";
            }
        }
        description "type definition for IF_L2PROCESS_CLEAR_T";
    }

    typedef  cml_gmpls_lmptype_t {
        type enumeration {
            enum static {
                value 0;
                description "static";
            }
            enum using-lmp {
                value 1;
                description "lmp";
            }
        }
        description "type definition for CML_GMPLS_LMPTYPE_T";
    }

    typedef  cml_gmpls_type_t {
        type enumeration {
            enum data-control {
                value 1;
                description "Data and Conrol";
            }
            enum data {
                value 2;
                description "Data";
            }
            enum control {
                value 3;
                description "Control";
            }
            enum data-numbered {
                value 4;
                description "Data, Numbered";
            }
        }
        description "type definition for CML_GMPLS_TYPE_T";
    }

    typedef  cml_gmpls_link_id_t {
        type union {
            type inet:ipv4-address {

            }
            type uint32 {
                range "1..4294967295";

            }
        }
        description "type definition for CML_GMPLS_LINK_ID_T";
    }

    typedef  cml_gmpls_remote_link_t {
        type union {
            type inet:ipv4-address {

            }
            type uint32 {
                range "1..4294967295";

            }
        }
        description "type definition for CML_GMPLS_REMOTE_LINK_T";
    }

    typedef  cml_mpls_vpls_opcode_t {
        type enumeration {
            enum swap {
                value 3;
                description "Swap incoming label";
            }
            enum vpnpop {
                value 4;
                description "Pop incoming label and forward VPN packet";
            }
        }
        description "type definition for CML_MPLS_VPLS_OPCODE_T";
    }

    typedef  cml_mpls_vpls_popopcode_t {
        type enumeration {
            enum pop {
                value 2;
                description "pop incoming label";
            }
        }
        description "type definition for CML_MPLS_VPLS_POPOPCODE_T";
    }

    typedef  cml_mpls_ipv6opcode_t {
        type enumeration {
            enum swap {
                value 3;
                description "Swap incoming label";
            }
        }
        description "type definition for CML_MPLS_IPV6OPCODE_T";
    }

    typedef  cml_gmpls_bidirectional_flag_t {
        type enumeration {
            enum False {
                value 0;
                description "Bidirectional flag is not set";
            }
            enum True {
                value 1;
                description "Bidirectional flag is set";
            }
        }
        description "type definition for CML_GMPLS_BIDIRECTIONAL_FLAG_T";
    }

    typedef  cml_gmpls_capability_type_t {
        type enumeration {
            enum psc2 {
                value 2;
                if-feature feature-list:NOT_HAVE_TDM;
                description "Packet Switch Capable-2 (PSC2)";
            }
            enum psc3 {
                value 4;
                if-feature feature-list:NOT_HAVE_TDM;
                description "Packet Switch Capable-3 (PSC3)";
            }
            enum psc4 {
                value 8;
                if-feature feature-list:NOT_HAVE_TDM;
                description "Packet Switch Capable-4 (PSC4)";
            }
            enum l2sc {
                value 16;
                if-feature feature-list:HAVE_TDM;
                description "Layer-2 Switch Capable (L2SC)";
            }
            enum tdm {
                value 32;
                if-feature feature-list:HAVE_TDM;
                description "Time-Division-Multiplex Capable (TDM)";
            }
            enum lsc {
                value 64;
                if-feature feature-list:HAVE_TDM;
                description "Lambda-Switch Capable (LSC)";
            }
            enum fsc {
                value 128;
                if-feature feature-list:HAVE_TDM;
                description "Fiber-Switch Capable (FSC)";
            }
            enum pbb-te {
                value 256;
                if-feature feature-list:HAVE_PBB_TE;
                description "Provider Backbone Bridging-Traffic Engineering (PBB-TE)";
            }
            enum psc1 {
                if-feature feature-list:NOT_HAVE_TDM;
                description "Packet Switch Capable-1 (PSC1)";
            }
            enum psc {
                if-feature feature-list:HAVE_TDM;
                description "Packet Switch Capable (PSC)";
            }
        }
        description "type definition for CML_GMPLS_CAPABILITY_TYPE_T";
    }

    typedef  cml_gmpls_encoding_type_t {
        type enumeration {
            enum packet {
                value 1;
                description "Packet";
            }
            enum ethernet {
                value 2;
                description "Ethernet";
            }
            enum pdh {
                value 3;
                description "ANSI/ETSI PDH";
            }
            enum sdh {
                value 5;
                description "SDH ITU-T G.707 / SONET ANSI T1.105";
            }
            enum digital {
                value 7;
                description "Digital Wrapper";
            }
            enum lambda {
                value 8;
                description "Lambda (photonic)";
            }
            enum fiber {
                value 9;
                description "Fiber";
            }
            enum fiber-Channel {
                value 11;
                description "FiberChannel";
            }
            enum g709-oduk {
                value 12;
                description "G.709 ODUk (Digital Path)";
            }
            enum g709-och {
                value 13;
                description "G.709 Optical Channel ";
            }
        }
        description "type definition for CML_GMPLS_ENCODING_TYPE_T";
    }

    typedef  cml_gmpls_protection_type_t {
        type enumeration {
            enum extra-traffic {
                value 1;
                description "Extra-traffic";
            }
            enum unprotected {
                value 2;
                description "Unprotected";
            }
            enum shared {
                value 4;
                description "Shared";
            }
            enum dedicated-one-to-one {
                value 8;
                description "Dedicated 1:1";
            }
            enum dedicated-one-plus-one {
                value 16;
                description "Dedicated 1+1";
            }
            enum enhanced {
                value 32;
                description "Enhanced";
            }
        }
        description "type definition for CML_GMPLS_PROTECTION_TYPE_T";
    }

    typedef  cml_gmpls_framing_type_t {
        type enumeration {
            enum sonet {
                value 17;
                description "SONET";
            }
            enum sdh {
                value 18;
                description "SDH";
            }
            enum otn {
                value 19;
                description "OTN";
            }
        }
        description "type definition for CML_GMPLS_FRAMING_TYPE_T";
    }

    typedef  cml_gmpls_sonet_signal_type_t {
        type enumeration {
            enum vt1.5 {
                value 1;
                description "1.5 Mbits/s";
            }
            enum vt2 {
                value 2;
                description "2.0 Mbits/s";
            }
            enum vt3 {
                value 3;
                description "3.15 Mbits/s";
            }
            enum vt6 {
                value 4;
                description "6.3 Mbits/s";
            }
            enum sts1-spe {
                value 5;
                description "44.1 Mbits/s";
            }
            enum sts-3c {
                value 6;
                description "140 Mbits/s";
            }
            enum sts-1 {
                value 7;
                description "51 Mbits/s";
            }
            enum sts-3 {
                value 8;
                description "155.520 Mbits/s";
            }
            enum sts-12 {
                value 9;
                description "622.080 Mbits/s";
            }
            enum sts-48 {
                value 10;
                description "2488.320 Mbits/s";
            }
            enum sts-192 {
                value 11;
                description "9953.28 Mbits/s";
            }
            enum sts-768 {
                value 12;
                description "39813.12 Mbits/s";
            }
        }
        description "type definition for CML_GMPLS_SONET_SIGNAL_TYPE_T";
    }

    typedef  cml_gmpls_sonet_signal_rate_t {
        type enumeration {
            enum sts-1 {
                value 1;
                description "51 Mbits/s";
            }
            enum sts-3 {
                value 2;
                description "155.520 Mbits/s";
            }
            enum sts-12 {
                value 3;
                description "622.080 Mbits/s";
            }
            enum sts-48 {
                value 4;
                description "2488.320 Mbits/s";
            }
            enum sts-192 {
                value 5;
                description "9953.28 Mbits/s";
            }
            enum sts-768 {
                value 6;
                description "39813.12 Mbits/s";
            }
        }
        description "type definition for CML_GMPLS_SONET_SIGNAL_RATE_T";
    }

    typedef  cml_gmpls_sdh_signal_type_t {
        type enumeration {
            enum vc-11 {
                value 1;
                description "1.5 Mbits/s";
            }
            enum vc-12 {
                value 2;
                description "2.0 Mbits/s";
            }
            enum vc-2 {
                value 4;
                description "6.3 Mbits/s";
            }
            enum vc-3 {
                value 5;
                description "44.1 Mbits/s";
            }
            enum vc-4 {
                value 6;
                description "140 Mbits/s";
            }
            enum stm-0 {
                value 7;
                description "51 Mbits/s";
            }
            enum stm-1 {
                value 8;
                description "155.52 Mbits/s";
            }
            enum stm-4 {
                value 9;
                description "622.08 Mbits/s";
            }
            enum stm-16 {
                value 10;
                description "2488.32 Mbits/s";
            }
            enum stm-64 {
                value 11;
                description "9953.28 Mbits/s";
            }
            enum stm-256 {
                value 12;
                description "39813.12 Mbits/s";
            }
        }
        description "type definition for CML_GMPLS_SDH_SIGNAL_TYPE_T";
    }

    typedef  cml_gmpls_sdh_signal_rate_t {
        type enumeration {
            enum stm-0 {
                value 1;
                description "51 Mbits/s";
            }
            enum stm-1 {
                value 2;
                description "155.52 Mbits/s";
            }
            enum stm-4 {
                value 3;
                description "622.08 Mbits/s";
            }
            enum stm-16 {
                value 4;
                description "2488.32 Mbits/s";
            }
            enum stm-64 {
                value 5;
                description "9953.28 Mbits/s";
            }
            enum stm-256 {
                value 6;
                description "39813.12 Mbits/s";
            }
        }
        description "type definition for CML_GMPLS_SDH_SIGNAL_RATE_T";
    }

    typedef  cml_gmpls_otn_signal_type_t {
        type enumeration {
            enum odu1 {
                value 1;
                description "ODU1 at 2.5 Gbps";
            }
            enum odu2 {
                value 2;
                description "ODU2 at 10 Gbps";
            }
            enum odu3 {
                value 3;
                description "ODU3 at 40 Gbps";
            }
            enum och1 {
                value 6;
                description "OCh at 2.5 Gbps";
            }
            enum och2 {
                value 7;
                description "OCh at 10  Gbps";
            }
            enum och3 {
                value 8;
                description "OCh at 40  Gbps";
            }
        }
        description "type definition for CML_GMPLS_OTN_SIGNAL_TYPE_T";
    }

    typedef  cml_gmpls_bandwidth_type_t {
        type enumeration {
            enum vc-11 {
                value 1;
                description "1.5 Mbits/s";
            }
            enum vc-12 {
                value 2;
                description "2.0 Mbits/s";
            }
            enum vc-2 {
                value 3;
                description "6.3 Mbits/s";
            }
            enum vc-3 {
                value 4;
                description "44.1 Mbits/s";
            }
            enum vc-4 {
                value 5;
                description "140 Mbits/s";
            }
            enum stm-0 {
                value 6;
                description "51 Mbits/s";
            }
            enum stm-1 {
                value 7;
                description "155.52 Mbits/s";
            }
            enum stm-4 {
                value 8;
                description "622.08 Mbits/s";
            }
            enum stm-16 {
                value 9;
                description "2488.32 Mbits/s";
            }
            enum stm-64 {
                value 10;
                description "9953.28 Mbits/s";
            }
            enum stm-256 {
                value 11;
                description "39813.12 Mbits/s";
            }
            enum odu1 {
                value 12;
                description "ODU1 at 2.5 Gbps";
            }
            enum odu2 {
                value 13;
                description "ODU2 at 10 Gbps";
            }
            enum odu3 {
                value 14;
                description "ODU3 at 40 Gbps";
            }
            enum och1 {
                value 15;
                description "OCh at 2.5 Gbps";
            }
            enum och2 {
                value 16;
                description "OCh at 10  Gbps";
            }
            enum och3 {
                value 17;
                description "OCh at 40  Gbps";
            }
            enum vt1.5 {
                value 18;
                description "1.5 Mbits/s";
            }
            enum vt2 {
                value 19;
                description "2.0 Mbits/s";
            }
            enum vt3 {
                value 20;
                description "3.15 Mbits/s";
            }
            enum vt6 {
                value 21;
                description "6.3 Mbits/s";
            }
            enum sts1-spe {
                value 22;
                description "44.1 Mbits/s";
            }
            enum sts-3c {
                value 23;
                description "140 Mbits/s";
            }
            enum sts-1 {
                value 24;
                description "51 Mbits/s";
            }
            enum sts-3 {
                value 25;
                description "155.520 Mbits/s";
            }
            enum sts-12 {
                value 26;
                description "622.080 Mbits/s";
            }
            enum sts-48 {
                value 27;
                description "2488.320 Mbits/s";
            }
            enum sts-192 {
                value 28;
                description "9953.28 Mbits/s";
            }
            enum sts-768 {
                value 29;
                description "39813.12 Mbits/s";
            }
        }
        description "type definition for CML_GMPLS_BANDWIDTH_TYPE_T";
    }

    typedef  cml_gmpls_max_lsp_bandwidth_type_t {
        type enumeration {
            enum stm-0 {
                value 6;
                description "51 Mbits/s";
            }
            enum stm-1 {
                value 7;
                description "155.52 Mbits/s";
            }
            enum stm-4 {
                value 8;
                description "622.08 Mbits/s";
            }
            enum stm-16 {
                value 9;
                description "2488.32 Mbits/s";
            }
            enum stm-64 {
                value 10;
                description "9953.28 Mbits/s";
            }
            enum stm-256 {
                value 11;
                description "39813.12 Mbits/s";
            }
            enum odu1 {
                value 12;
                description "ODU1 at 2.5 Gbps";
            }
            enum odu2 {
                value 13;
                description "ODU2 at 10 Gbps";
            }
            enum odu3 {
                value 14;
                description "ODU3 at 40 Gbps";
            }
            enum och1 {
                value 15;
                description "OCh at 2.5 Gbps";
            }
            enum och2 {
                value 16;
                description "OCh at 10  Gbps";
            }
            enum och3 {
                value 17;
                description "OCh at 40  Gbps";
            }
            enum sts-1 {
                value 24;
                description "51 Mbits/s";
            }
            enum sts-3 {
                value 25;
                description "155.520 Mbits/s";
            }
            enum sts-12 {
                value 26;
                description "622.080 Mbits/s";
            }
            enum sts-48 {
                value 27;
                description "2488.320 Mbits/s";
            }
            enum sts-192 {
                value 28;
                description "9953.28 Mbits/s";
            }
            enum sts-768 {
                value 29;
                description "39813.12 Mbits/s";
            }
        }
        description "type definition for CML_GMPLS_MAX_LSP_BANDWIDTH_TYPE_T";
    }

    typedef  cml_gmpls_sonet_gpid_type_t {
        type enumeration {
            enum ds1-sf-asynchronous {
                value 22;
                description "DS1 SF Asynchronous";
            }
            enum ds1-esf-asynchronous {
                value 23;
                description "DS1 ESF Asynchronous";
            }
            enum ds3-m23-asynchronous {
                value 24;
                description "DS3 M23 Asynchronous";
            }
            enum ds3-cbit-parity-asynchronous {
                value 25;
                description "DS3 C-Bit Parity Asynchronous";
            }
        }
        description "type definition for CML_GMPLS_SONET_GPID_TYPE_T";
    }

    typedef  cml_gmpls_sdh_gpid_type_t {
        type enumeration {
            enum asynchronous-mapping-of-E4 {
                value 5;
                description "Asynchronous mapping of E4";
            }
            enum asynchronous-mapping-of-DS3-T3 {
                value 6;
                description "Asynchronous mapping of DS3/T3";
            }
            enum asynchronous-mapping-of-E3 {
                value 7;
                description "Asynchronous mapping of E3";
            }
            enum bit-synchronous-mapping-of-E3 {
                value 8;
                description "Bit synchronous mapping of E3";
            }
            enum byte-synchronous-mapping-of-E3 {
                value 9;
                description "Byte synchronous mapping of E3";
            }
            enum asynchronous-mapping-of-DS2T2 {
                value 10;
                description "Asynchronous mapping of DS2/T2";
            }
            enum bit-synchronous-mapping-of-DS2T2 {
                value 11;
                description "Bit synchronous mapping of DS2/T2";
            }
            enum asynchronous-mapping-of-E1 {
                value 13;
                description "Asynchronous mapping of E1";
            }
            enum byte-synchronous-mapping-of-E1 {
                value 14;
                description "Byte synchronous mapping of E1";
            }
            enum byte-synchronous-mapping-of-31DS0 {
                value 15;
                description "Byte synchronous mapping of 31 * DS0";
            }
            enum asynchronous-mapping-of-DS1T1 {
                value 16;
                description "Asynchronous mapping of DS1/T1";
            }
            enum bit-synchronous-mapping-of-DS1T1 {
                value 17;
                description "Bit synchronous mapping of DS1/T1";
            }
            enum byte-synchronous-mapping-of-DS1T1 {
                value 18;
                description "Byte synchronous mapping of DS1/T1";
            }
            enum vc-11-in-vc12 {
                value 19;
                description "VC-11 in VC-12";
            }
            enum vt-lovc {
                value 26;
                description "VT-LOVC";
            }
            enum ste-spe-hovc {
                value 27;
                description "STS SPE-HOVC";
            }
            enum pos-noscrambling-16bit-CRC {
                value 28;
                description "POS - No Scrambling, 16 bit CRC";
            }
            enum pos-noscrambling-32bit-CRC {
                value 29;
                description "POS - No Scrambling, 32 bit CRC";
            }
            enum pos-scrambling-16bit-CRC {
                value 30;
                description "POS - Scrambling, 16 bit CRC";
            }
            enum pos-scrambling-32bit-CRC {
                value 31;
                description "POS - Scrambling, 32 bit CRC";
            }
            enum atm {
                value 32;
                description "ATM mapping";
            }
            enum ethernet {
                value 33;
                description "Ethernet";
            }
            enum ansi-etsi-pdh {
                value 38;
                description "ANSI-ETSI PDH";
            }
            enum link-access-protocol-SDH {
                value 40;
                description "Link Access Protocol SDH";
            }
            enum fddi {
                value 41;
                description "FDDI";
            }
            enum dqdb {
                value 42;
                description "DQDB";
            }
            enum hdlc {
                value 44;
                description "HDLC";
            }
            enum ethernet-V2-DIX {
                value 45;
                description "Ethernet V2-DIX";
            }
            enum ethernet-802.3 {
                value 46;
                description "Ethernet 802.3";
            }
        }
        description "type definition for CML_GMPLS_SDH_GPID_TYPE_T";
    }

    typedef  cml_gmpls_otn_gpid_type_t {
        type enumeration {
            enum atm-mapping {
                value 32;
                description "atm-mapping";
            }
            enum eth-phy {
                value 33;
                description "eth-phy";
            }
            enum sonet-sdh {
                value 34;
                description "sonet-sdh";
            }
            enum res-sonet {
                value 35;
                description "res-sonet";
            }
            enum g709-oduj {
                value 47;
                description "g709-oduj";
            }
            enum g709-otukv {
                value 48;
                description "g709_otukv";
            }
            enum cbra {
                value 49;
                description "cbra";
            }
            enum cbrb {
                value 50;
                description "cbrb";
            }
            enum bsot {
                value 51;
                description "bsot";
            }
            enum bsnt {
                value 52;
                description "bsnt";
            }
            enum ip-ppp {
                value 53;
                description "ip-ppp";
            }
            enum eth-mac-framed-gfp {
                value 54;
                description "eth-mac-framed-gfp";
            }
            enum eth-phy-trans-gfp {
                value 55;
                description "eth-phy-trans-gfp";
            }
            enum escon {
                value 56;
                description "escon";
            }
            enum ficon {
                value 57;
                description "ficon";
            }
            enum fiber-channel {
                value 58;
                description "fiber-channel";
            }
        }
        description "type definition for CML_GMPLS_OTN_GPID_TYPE_T";
    }

    typedef  cml_gmpls_otn_reservable_bandwidth_t {
        type enumeration {
            enum odu1 {
                value 1;
                description "ODU1 at 2.5 Gbps";
            }
            enum odu2 {
                value 2;
                description "ODU2 at 10 Gbps";
            }
            enum odu3 {
                value 3;
                description "ODU3 at 40 Gbps";
            }
            enum och1 {
                value 6;
                description "OCh at 2.5 Gbps";
            }
            enum och2 {
                value 7;
                description "OCh at 10  Gbps";
            }
            enum och3 {
                value 8;
                description "OCh at 40  Gbps";
            }
        }
        description "type definition for CML_GMPLS_OTN_RESERVABLE_BANDWIDTH_T";
    }

    typedef  cml_gmpls_transparency_type_t {
        type enumeration {
            enum sec-regen {
                value 1;
                description "Section/Regenerator Section layer";
            }
            enum line-mux {
                value 2;
                description "Line/Multiplex Section layer";
            }
        }
        description "type definition for CML_GMPLS_TRANSPARENCY_TYPE_T";
    }

    typedef  cml_gmpls_sdh_indication_t {
        type enumeration {
            enum std {
                value 0;
                description "Standard SONET/SDH";
            }
            enum arbitrary {
                value 1;
                description "Arbitrary SONET/SDH";
            }
        }
        description "type definition for CML_GMPLS_SDH_INDICATION_T";
    }

    typedef  cml_evpn_service_type_t {
        type enumeration {
            enum vlan-based {
                value 1;
                description "VLAN-based EVPN-Service type";
            }
            enum vlan-aware-bundle {
                value 3;
                description "VLAN aware bundle EVPN-Service type";
            }
        }
        description "type definition for CML_EVPN_SERVICE_TYPE_T";
    }

    typedef  cml_vm_status_t {
        type enumeration {
            enum DOWN {
                value 0;
                description "DOWN";
            }
            enum UP {
                value 1;
                description "UP";
            }
        }
        description "type definition for CML_VM_STATUS_T";
    }

    typedef  cml_mvrf_cms_t {
        type enumeration {
            enum bgp {
                value 1;
                description "bgp";
            }
        }
        description "type definition for CML_MVRF_CMS_T";
    }

    typedef  cml_mvrf_ipmsitunnel_t {
        type enumeration {
            enum rsvp-p2mp {
                value 1;
                description "rsvp-p2mp";
            }
            enum mldp-p2mp {
                value 2;
                description "mldp-p2mp";
            }
            enum ingress-replication {
                value 6;
                description "ingress-replication";
            }
            enum mldp-mp2mp {
                value 7;
                description "mldp-mp2mp";
            }
        }
        description "type definition for CML_MVRF_IPMSITUNNEL_T";
    }

    typedef  cml_mvrf_spmsitunnel_t {
        type enumeration {
            enum rsvp-p2mp {
                value 1;
                description "rsvp-p2mp";
            }
            enum mldp-p2mp {
                value 2;
                description "mldp-p2mp";
            }
            enum ingress-replication {
                value 6;
                description "ingress-replication";
            }
        }
        description "type definition for CML_MVRF_SPMSITUNNEL_T";
    }

    typedef  cml_mvrf_segmented_lsp_t {
        type enumeration {
            enum inter-area-segmented {
                value 1;
                description "inter-area-segmented";
            }
        }
        description "type definition for CML_MVRF_SEGMENTED_LSP_T";
    }

    typedef  cml_mvpn_ipmsimp2mproot_secondary_t {
        type enumeration {
            enum secondary {
                value 1;
                description "secondary root";
            }
        }
        description "type definition for CML_MVPN_IPMSIMP2MPROOT_SECONDARY_T";
    }

    typedef  cml_umh_selection_policy_t {
        type enumeration {
            enum highest-ip {
                value 1;
                description "highest-ip";
            }
            enum hash-based {
                value 2;
                description "hash-based";
            }
        }
        description "type definition for CML_UMH_SELECTION_POLICY_T";
    }

    typedef  cml_gtm_tunnel_t {
        type enumeration {
            enum rsvp-p2mp {
                value 1;
                description "rsvp-p2mp";
            }
            enum mldp-p2mp {
                value 2;
                description "mldp-p2mp";
            }
        }
        description "type definition for CML_GTM_TUNNEL_T";
    }

    typedef  cml_gtm_option_t {
        type enumeration {
            enum option-1 {
                value 1;
                description "Do not use Shared Trees in MPLS Core";
            }
            enum option-2 {
                value 2;
                description "Use Shared Trees in MPLS Core";
            }
        }
        description "type definition for CML_GTM_OPTION_T";
    }

    typedef  evpn_acc_if_t {
        type enumeration {
            enum access-if {
                value 1;
                description "EVPN Access interface mode change";
            }
            enum access-if-evpn {
                value 2;
                description "EVPN Access interface mode change";
            }
        }
        description "type definition for EVPN_ACC_IF_T";
    }

    typedef  cml_notif_class_t {
        type enumeration {
            enum state {
                value 2;
                description "Notification related to state change";
            }
            enum config {
                value 3;
                description "Notification related to config parameter change";
            }
            enum message {
                value 4;
                description "Provides information about some events";
            }
        }
        description "type definition for CML_NOTIF_CLASS_T";
    }

    typedef  cml_notif_severity_t {
        type enumeration {
            enum all {
                value 1;
                description "notification severity all";
            }
            enum info {
                value 2;
                description "notification severity info";
            }
            enum warning {
                value 3;
                description "notification severity warning";
            }
            enum minor {
                value 4;
                description "notification severity minor";
            }
            enum major {
                value 5;
                description "notification severity major";
            }
            enum critical {
                value 6;
                description "notification severity critical";
            }
        }
        description "type definition for CML_NOTIF_SEVERITY_T";
    }

}
