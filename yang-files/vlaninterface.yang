/*
* Copyright (C) 2016 IP Infusion, Inc. 
*  All Rights Reserved.
*
*** Auto generated by zebmdc

* Unless required by applicable law or agreed to in writing,
* software distributed under the License is distributed on an
* "AS IS" BASIS, WITHOUT WARRANTIES OR CONDITIONS OF ANY
* KIND, either express or implied.

* File name : vlaninterface.yang
*
*/

submodule vlaninterface {

    belongs-to  ZebOS { prefix ZebOS; }
    include interface;
    include vlan;
    include bridge;


    import cml_data_types {
        prefix cml_data_types;
    }

    revision "2015-10-08" {
        description "Revisied on 2015-10-08.";    }



    grouping vlaninterface-grouping {
        list vlaninterface {
             

            description
                "vlaninterface";

            config true;
            key "ifName";

            
            leaf vrId  {
                mandatory false;                
                type  leafref {
                    path  "/vr/vrId";
                }
            } // END of vrId definition.

            leaf ifName  {
                mandatory true;                
                type  leafref {
                    path  "/vr/interface/ifName";
                }
            } // END of ifName definition.

            leaf vlanPortMode  {
                mandatory true;                
                type  cml_data_types:CML_VLAN_PORT_MODE_T;  
                config true;
            } // END of vlanPortMode definition.

            leaf vlanPortIngressFilter  {
                mandatory false;                
                type  cml_data_types:CML_ENABLE_DISABLE_T;  
                default "enable";
                config true;
            } // END of vlanPortIngressFilter definition.

            leaf frameType  {
                mandatory false;                
                type  cml_data_types:CML_VLAN_FRAME_TYPE_T;  
                default "all";
                config true;
            } // END of frameType definition.


            list staticMac {
                 

                description
                    "staticMac";

                config true;
                key "macAddr";

                
                leaf vlanIdMac  {
                    mandatory false;                    
                    type  cml_data_types:CML_UINT16_T {
                         range "2..4096";
                    }
                    config true;
                } // END of vlanIdMac definition.

                leaf bridgeId  {
                    mandatory false;                    
                    type  leafref {
                        path  "/vr/bridge/bridgeId";
                    }
                } // END of bridgeId definition.

                leaf macAddr  {
                    mandatory true;                    
                    type  cml_data_types:CML_STRING_T;  
                    config true;
                } // END of macAddr definition.

                leaf discardForward  {
                    mandatory false;                    
                    type  cml_data_types:CML_DISCARDFORWARD_T;  
                    config true;
                } // END of discardForward definition.

                leaf priorityOverWrite  {
                    mandatory false;                    
                    type  cml_data_types:CML_UINT8_T {
                         range "0..7";
                    }
                    config true;
                } // END of priorityOverWrite definition.

                leaf overMacType  {
                    mandatory false;                    
                    type  cml_data_types:CML_OVERMACTYPE_T;  
                    config true;
                } // END of overMacType definition.

            } // End of staticMac-list

            list vlanInterfaceBound {
                 

                description
                    "vlanInterfaceBound";

                config true;
                key "vlanId";

                
                leaf vlanId  {
                    mandatory true;                    
                    type  leafref {
                        path  "/vr/bridge/vlan/vlanId";
                    }
                } // END of vlanId definition.

                leaf vlanPortMode  {
                    mandatory true;                    
                    type  cml_data_types:CML_VLAN_PORT_MODE_T;  
                    config true;
                } // END of vlanPortMode definition.

            } // End of vlanInterfaceBound-list

            list allowedvlan {
                 

                description
                    "allowedvlan";

                config true;
                key "allowedVlanId";

                
                leaf allowedVlanId  {
                    mandatory true;                    
                    type  cml_data_types:CML_UINT16_T;  
                    config true;
                } // END of allowedVlanId definition.

                leaf vlanPortMode  {
                    mandatory true;                    
                    type  cml_data_types:CML_VLAN_PORT_MODE_T;  
                    config true;
                } // END of vlanPortMode definition.

                leaf egrType  {
                    mandatory false;                    
                    type  cml_data_types:CML_ENABLE_DISABLE_T;  
                    config true;
                } // END of egrType definition.

            } // End of allowedvlan-list

            list excludevlan {
                 

                description
                    "excludevlan";

                config true;
                key "excludeVlanId";

                
                leaf excludeVlanId  {
                    mandatory true;                    
                    type  cml_data_types:CML_UINT16_T;  
                    config true;
                } // END of excludeVlanId definition.

                leaf vlanPortMode  {
                    mandatory true;                    
                    type  cml_data_types:CML_VLAN_PORT_MODE_T;  
                    config true;
                } // END of vlanPortMode definition.

            } // End of excludevlan-list

            list vlanUserTable {
                 

                description
                    "vlanUserTable";

                config true;
                key "userPriority";

                
                leaf userPriority  {
                    mandatory true;                    
                    type  cml_data_types:CML_UINT8_T {
                         range "0..7";
                    }
                    config true;
                } // END of userPriority definition.

                leaf regenPriority  {
                    mandatory true;                    
                    type  cml_data_types:CML_UINT8_T {
                         range "0..7";
                    }
                    config true;
                } // END of regenPriority definition.

            } // End of vlanUserTable-list

            list vlanTraffic {
                 

                description
                    "vlanTraffic";

                config true;
                key "userPriority";

                
                leaf userPriority  {
                    mandatory true;                    
                    type  cml_data_types:CML_UINT8_T {
                         range "0..7";
                    }
                    config true;
                } // END of userPriority definition.

                leaf trafficClass  {
                    mandatory false;                    
                    type  cml_data_types:CML_UINT8_T {
                         range "1..8";
                    }
                    config true;
                } // END of trafficClass definition.

                leaf trafficClassValue  {
                    mandatory true;                    
                    type  cml_data_types:CML_UINT8_T {
                         range "0..7";
                    }
                    config true;
                } // END of trafficClassValue definition.

            } // End of vlanTraffic-list
        } // End of vlaninterface-list
    } // END of vlaninterface-grouping definition.


}
