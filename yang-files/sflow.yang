/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : sflow.yang
*
*/

submodule sflow {

    belongs-to  ZebOS { prefix ZebOS; }
    include interface;


    import cml_data_types {
        prefix cml_data_types;
    }

    import feature_list {
        prefix feature_list;
    }

    description
        "sflow configurations";


    revision "2016-12-27" {
        description "Added snmp oid and documentation tag.";
    }

    revision "2016-10-28" {
        description "Initial version of SFLOW datamodel.";
    }


    grouping  sflow-grouping {
    container sflow {
        presence "yes"; 
                config true;

        description
            "sflow";

        leaf sflowInstance  {
            mandatory true;
            type  cml_data_types:CML_BOOL_T;  
            description "sflow";
        } // END of sflowInstance definition.

        leaf collectorIP  {
            if-feature feature_list:HAVE_SFLOW;
            type  cml_data_types:CML_IPV4_ADDR_T;  
        } // END of collectorIP definition.

        leaf port  {
            if-feature feature_list:HAVE_SFLOW;
            type  cml_data_types:CML_INT32_T {
                 range "1024..65535";
            }
            description "sFlow Collector Port Number";
        } // END of port definition.

        leaf receiver-time-out  {
            if-feature feature_list:HAVE_SFLOW;
            type  cml_data_types:CML_UINT32_T {
                 range "0..2147483647";
            }
            description "receiver timeout value in sec";
        } // END of receiver-time-out definition.

        leaf max-datagram-size  {
            if-feature feature_list:HAVE_SFLOW;
            type  cml_data_types:CML_UINT16_T {
                 range "200..9000";
            }
            description "sflow collector";
        } // END of max-datagram-size definition.

        leaf rate  {
            if-feature feature_list:HAVE_SFLOW;
            if-feature feature_list:HAVE_BROADCOM;
            type  cml_data_types:CML_UINT32_T {
                 range "0..32000";
            }
            description "Rate in packets per second";
        } // END of rate definition.

        leaf cache-size  {
            if-feature feature_list:HAVE_SFLOW;
            if-feature feature_list:HAVE_ACL;
            type  cml_data_types:CML_UINT32_T {
                 range "1000..10000";
            }
        } // END of cache-size definition.

        leaf accessrate  {
            if-feature feature_list:HAVE_SFLOW;
            if-feature feature_list:HAVE_ACL;
            if-feature feature_list:HAVE_BROADCOM;
            type  cml_data_types:CML_UINT16_T {
                 range "0..1000";
            }
        } // END of accessrate definition.


        list sflowInterfaceConfigs {
             
            description
                "sampling and polling-interval configs of an interface";

            config true;
            key "ifName";

            
            leaf ifName  {
                type  cml_data_types:CML_STRING_T {
                    length "0..255";
                }
            } // END of ifName definition.

            container pollingInterface {
                                config true;

                description
                    "pollingInterface";

                leaf poll-interval  {
                    type  cml_data_types:CML_UINT8_T {
                         range "5..60";
                    }
                    description "sflow interface poll-interval";
                } // END of poll-interval definition.

            } // END of pollingInterface-container definition.
            container samplingIngress {
                                config true;

                description
                    "samplingIngress";

                leaf ingressInstance  {
                    type  cml_data_types:CML_BOOL_T;  
                    description "direction ingress";
                } // END of ingressInstance definition.

                leaf sampling-rate-Ingress  {
                    type  cml_data_types:CML_UINT32_T {
                         range "1024..1073741823";
                    }
                } // END of sampling-rate-Ingress definition.

                leaf max-header-size-Ingress  {
                    type  cml_data_types:CML_UINT16_T {
                         range "128..256";
                    }
                    description "maximum header size";
                } // END of max-header-size-Ingress definition.

            } // END of samplingIngress-container definition.
            container samplingEgress {
                                config true;

                description
                    "samplingEgress";

                leaf egressInstance  {
                    type  cml_data_types:CML_BOOL_T;  
                    description "direction egress";
                } // END of egressInstance definition.

                leaf sampling-rate-Egress  {
                    type  cml_data_types:CML_UINT32_T {
                         range "1024..1073741823";
                    }
                } // END of sampling-rate-Egress definition.

                leaf max-header-size-Egress  {
                    type  cml_data_types:CML_UINT16_T {
                         range "128..256";
                    }
                    description "maximum header size";
                } // END of max-header-size-Egress definition.

            } // END of samplingEgress-container definition.
            container samplingEnable {
                                config true;

                description
                    "samplingEnable";

                leaf samplingEnable  {
                    type  cml_data_types:CML_BOOL_T;  
                    description "Enable or Disable sampling rate configured on an interface";
                } // END of samplingEnable definition.

            } // END of samplingEnable-container definition.
        } // End of sflowInterfaceConfigs-list
    } // END of sflow-container definition.
    } // END of sflow-container definition.

    grouping  debugsflow-grouping {
    container debugsflow {
                config true;

        description
            "debugsflow";

        leaf debugsflow  {
            if-feature feature_list:HAVE_SFLOW;
            type  cml_data_types:SFLOW_DEBUG_OPTIONS_T;  
            default "all";
        } // END of debugsflow definition.

    } // END of debugsflow-container definition.
    } // END of debugsflow-container definition.


}
