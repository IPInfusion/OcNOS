/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ssh.yang
*
*/

submodule ssh {

    belongs-to  ZebOS { prefix ZebOS; }
    include vrf;


    import cml_data_types {
        prefix cml_data_types;
    }

    import feature_list {
        prefix feature_list;
    }

    description
        "ssh configurations";


    revision "2017-01-19" {
        description "Changed vrf name as normal attr as it is optional parameter.";
    }

    revision "2016-12-27" {
        description "Added snmp oid and documentation tag.";
    }

    revision "2016-10-28" {
        description "Initial version of SSH datamodel.";
    }


    grouping  ssh-grouping {
    container ssh {
                config true;

        description
            "ssh related operations";

        leaf vrfName  {
            type  cml_data_types:CML_STRING_T {
                length "0..255";
            }
            default "default";
        } // END of vrfName definition.

        leaf featuressh  {
            if-feature feature_list:HAVE_SSH_SERVER;
            type  cml_data_types:CML_BOOL_T;  
            description "feature ssh";
        } // END of featuressh definition.

        leaf serverPort  {
            if-feature feature_list:HAVE_SSH_SERVER;
            type  cml_data_types:CML_INT32_T {
                 range "1024..65535";
            }
            description "SSH server port";
        } // END of serverPort definition.

        leaf loginAttempts  {
            if-feature feature_list:HAVE_SSH_SERVER;
            type  cml_data_types:CML_INT32_T;  
            default "3";
            description "ssh login-attempts";
        } // END of loginAttempts definition.

        leaf rsa  {
            if-feature feature_list:HAVE_SSH_SERVER;
            type  cml_data_types:CML_BOOL_T;  
        } // END of rsa definition.

        leaf dsa  {
            if-feature feature_list:HAVE_SSH_SERVER;
            type  cml_data_types:CML_BOOL_T;  
        } // END of dsa definition.

        leaf length  {
            if-feature feature_list:HAVE_SSH_SERVER;
            type  cml_data_types:CML_UINT32_T {
                 range "768..2048";
            }
        } // END of length definition.

        leaf force  {
            if-feature feature_list:HAVE_SSH_SERVER;
            type  cml_data_types:CML_BOOL_T;  
            default false;
        } // END of force definition.

        leaf debugssh  {
            if-feature feature_list:HAVE_SSH_SERVER;
            type  cml_data_types:CML_BOOL_T;  
            default false;
            description "debug ssh server";
        } // END of debugssh definition.

    } // END of ssh-container definition.
    } // END of ssh-container definition.


}
