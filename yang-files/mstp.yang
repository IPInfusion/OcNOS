/*
* Copyright (C) 2016 IP Infusion, Inc. 
*  All Rights Reserved.
*
*** Auto generated by zebmdc

* Unless required by applicable law or agreed to in writing,
* software distributed under the License is distributed on an
* "AS IS" BASIS, WITHOUT WARRANTIES OR CONDITIONS OF ANY
* KIND, either express or implied.

* File name : mstp.yang
*
*/

submodule mstp {

    belongs-to  ZebOS { prefix ZebOS; }
    include interface;
    include vlan;


    import cml_data_types {
        prefix cml_data_types;
    }

    description
        "Layer-2 bridge configurations";


    revision "2015-04-25" {
        description "Revisied on 2015-04-25.";    }



    grouping mstp-grouping {
        list mstp {
             

            description
                "mstp";

            config true;
            key "instanceId";

            
            leaf vrId  {
                mandatory false;                
                type  leafref {
                    path  "/vr/vrId";
                }
            } // END of vrId definition.

            leaf bridgeId  {
                mandatory false;                
                type  leafref {
                    path  "/vr/bridge/bridgeId";
                }
            } // END of bridgeId definition.

            leaf instanceId  {
                mandatory true;                
                type  cml_data_types:CML_INT32_T {
                     range "1..63";
                }
                config true;
            } // END of instanceId definition.

            leaf instPriority  {
                mandatory false;                
                type  cml_data_types:CML_UINT32_T {
                     range "0..61440";
                }
                default "32768";
                config true;
            } // END of instPriority definition.

            leaf-list vlanId  {
                
                type  leafref {
                    path  "/vr/bridge/vlan/vlanId";
                }
            } // END of vlanId definition.

            leaf bridgeEnabled  {
                mandatory true;                
                type  cml_data_types:CML_STRING_T;  
                config false;
            } // END of bridgeEnabled definition.

            leaf topologyChange  {
                mandatory true;                
                type  cml_data_types:CML_STRING_T;  
                config false;
            } // END of topologyChange definition.

            leaf topologychangeDetected  {
                mandatory true;                
                type  cml_data_types:CML_STRING_T;  
                config false;
            } // END of topologychangeDetected definition.

            leaf cistmstpBridge  {
                mandatory true;                
                type  cml_data_types:CML_STRING_T;  
                config false;
            } // END of cistmstpBridge definition.

            leaf externalrootPathcost  {
                mandatory true;                
                type  cml_data_types:CML_UINT32_T;  
                config false;
            } // END of externalrootPathcost definition.

            leaf internalrootPathcost  {
                mandatory true;                
                type  cml_data_types:CML_UINT32_T;  
                config false;
            } // END of internalrootPathcost definition.

            leaf cistbridgePriority  {
                mandatory true;                
                type  cml_data_types:CML_UINT32_T;  
                config false;
            } // END of cistbridgePriority definition.

            leaf cistrootportIfindex  {
                mandatory true;                
                type  cml_data_types:CML_INT32_T;  
                config false;
            } // END of cistrootportIfindex definition.

            leaf totalnumberTopologychange  {
                mandatory true;                
                type  cml_data_types:CML_INT32_T;  
                config false;
            } // END of totalnumberTopologychange definition.

            leaf lasttimeTopologychange  {
                mandatory true;                
                type  cml_data_types:CML_STRING_T;  
                config false;
            } // END of lasttimeTopologychange definition.

            leaf cistdesignatedRoot  {
                mandatory true;                
                type  cml_data_types:CML_STRING_T;  
                config false;
            } // END of cistdesignatedRoot definition.

            leaf cistregisteredRoot  {
                mandatory true;                
                type  cml_data_types:CML_STRING_T;  
                config false;
            } // END of cistregisteredRoot definition.

            leaf cistBridgeid  {
                mandatory true;                
                type  cml_data_types:CML_STRING_T;  
                config false;
            } // END of cistBridgeid definition.

            leaf mstirootportIfindex  {
                mandatory true;                
                type  cml_data_types:CML_INT32_T;  
                config false;
            } // END of mstirootportIfindex definition.

            leaf mstibridgePriority  {
                mandatory true;                
                type  cml_data_types:CML_UINT32_T;  
                config false;
            } // END of mstibridgePriority definition.

            leaf mstibridgeId  {
                mandatory true;                
                type  cml_data_types:CML_UINT8_T;  
                config false;
            } // END of mstibridgeId definition.

            leaf mstidesignatedRoot  {
                mandatory true;                
                type  cml_data_types:CML_UINT32_T;  
                config false;
            } // END of mstidesignatedRoot definition.

            leaf designatedPortid  {
                mandatory true;                
                type  cml_data_types:CML_UINT16_T;  
                config false;
            } // END of designatedPortid definition.

            leaf mstipathCost  {
                mandatory true;                
                type  cml_data_types:CML_UINT32_T;  
                config false;
            } // END of mstipathCost definition.

            leaf mstiPriority  {
                mandatory true;                
                type  cml_data_types:CML_INT32_T;  
                config false;
            } // END of mstiPriority definition.

            leaf messageAge  {
                mandatory true;                
                type  cml_data_types:CML_INT32_T;  
                config false;
            } // END of messageAge definition.

            leaf forwarddelayTimer  {
                mandatory true;                
                type  cml_data_types:CML_INT32_T;  
                config false;
            } // END of forwarddelayTimer definition.

            leaf messageageTimer  {
                mandatory true;                
                type  cml_data_types:CML_INT32_T;  
                config false;
            } // END of messageageTimer definition.

            leaf helloTimer  {
                mandatory true;                
                type  cml_data_types:CML_INT32_T;  
                config false;
            } // END of helloTimer definition.

            leaf instanceportconfbpduSent  {
                mandatory true;                
                type  cml_data_types:CML_UINT32_T;  
                config false;
            } // END of instanceportconfbpduSent definition.

            leaf instanceportconfbpduRecieved  {
                mandatory true;                
                type  cml_data_types:CML_UINT32_T;  
                config false;
            } // END of instanceportconfbpduRecieved definition.

            leaf instanceporttcnbpduSent  {
                mandatory true;                
                type  cml_data_types:CML_UINT32_T;  
                config false;
            } // END of instanceporttcnbpduSent definition.

            leaf instanceporttcnbpduRecieved  {
                mandatory true;                
                type  cml_data_types:CML_UINT32_T;  
                config false;
            } // END of instanceporttcnbpduRecieved definition.

            leaf cistmessageAge  {
                mandatory true;                
                type  cml_data_types:CML_INT32_T;  
                config false;
            } // END of cistmessageAge definition.

            leaf cistforwardTransition  {
                mandatory true;                
                type  cml_data_types:CML_UINT32_T;  
                config false;
            } // END of cistforwardTransition definition.

            leaf portnextState  {
                mandatory true;                
                type  cml_data_types:CML_STRING_T;  
                config false;
            } // END of portnextState definition.

            leaf instanceporttopologyChangetime  {
                mandatory true;                
                type  cml_data_types:CML_INT32_T;  
                config false;
            } // END of instanceporttopologyChangetime definition.

            leaf bridgemacAddress  {
                mandatory true;                
                type  cml_data_types:CML_STRING_T;  
                config false;
            } // END of bridgemacAddress definition.

            leaf stpmulticastAddress  {
                mandatory true;                
                type  cml_data_types:CML_STRING_T;  
                config false;
            } // END of stpmulticastAddress definition.

            leaf instanceTopologychangedetected  {
                mandatory true;                
                type  cml_data_types:CML_STRING_T;  
                config false;
            } // END of instanceTopologychangedetected definition.

            leaf instlastTopologychangerecievedfrom  {
                mandatory true;                
                type  cml_data_types:CML_STRING_T;  
                config false;
            } // END of instlastTopologychangerecievedfrom definition.

            leaf instancemaxAge  {
                mandatory true;                
                type  cml_data_types:CML_UINT32_T;  
                config false;
            } // END of instancemaxAge definition.

            leaf instancetopologychangeInitiator  {
                mandatory true;                
                type  cml_data_types:CML_INT32_T;  
                config false;
            } // END of instancetopologychangeInitiator definition.

            leaf topologychangeInitiator  {
                mandatory true;                
                type  cml_data_types:CML_INT32_T;  
                config false;
            } // END of topologychangeInitiator definition.

            leaf instancetopologyChange  {
                mandatory true;                
                type  cml_data_types:CML_STRING_T;  
                config false;
            } // END of instancetopologyChange definition.

            leaf lasttopologychangeRecievedfrom  {
                mandatory true;                
                type  cml_data_types:CML_STRING_T;  
                config false;
            } // END of lasttopologychangeRecievedfrom definition.

            leaf configFormat  {
                mandatory true;                
                type  cml_data_types:CML_INT32_T;  
                config false;
            } // END of configFormat definition.

            leaf configName  {
                mandatory true;                
                type  cml_data_types:CML_INT32_T;  
                config false;
            } // END of configName definition.

            leaf configRevision  {
                mandatory true;                
                type  cml_data_types:CML_INT32_T;  
                config false;
            } // END of configRevision definition.

            leaf configDigest  {
                mandatory true;                
                type  cml_data_types:CML_INT32_T;  
                config false;
            } // END of configDigest definition.

            leaf instanceMstiporttopologyChangetime  {
                mandatory false;                
                type  cml_data_types:CML_INT32_T;  
                config false;
            } // END of instanceMstiporttopologyChangetime definition.

            leaf instancePortNextState  {
                mandatory false;                
                type  cml_data_types:CML_UINT32_T;  
                config false;
            } // END of instancePortNextState definition.

            leaf instanceTopologuChangeCount  {
                mandatory false;                
                type  cml_data_types:CML_INT32_T;  
                config false;
            } // END of instanceTopologuChangeCount definition.

            leaf mstiInstancedesignatedRoot  {
                mandatory false;                
                type  cml_data_types:CML_STRING_T;  
                config false;
            } // END of mstiInstancedesignatedRoot definition.


            list mstp_interface {
                 

                description
                    "Group of mstp attribute having interface property";

                config true;
                key "ifName";

                
                leaf ifName  {
                    mandatory true;                    
                    type  leafref {
                        path  "/vr/interface/ifName";
                    }
                } // END of ifName definition.

                leaf instportPriority  {
                    mandatory false;                    
                    type  cml_data_types:CML_INT16_T {
                         range "0..240";
                    }
                    default "128";
                    config true;
                } // END of instportPriority definition.

                leaf mstppathCost  {
                    mandatory false;                    
                    type  cml_data_types:CML_UINT32_T {
                         range "1..20000000";
                    }
                    default "20000000";
                    config true;
                } // END of mstppathCost definition.

                leaf cistAdminedge  {
                    mandatory false;                    
                    type  cml_data_types:CML_STRING_T;  
                    config false;
                } // END of cistAdminedge definition.

                leaf cistOperedge  {
                    mandatory false;                    
                    type  cml_data_types:CML_STRING_T;  
                    config false;
                } // END of cistOperedge definition.

                leaf cistPortrole  {
                    mandatory false;                    
                    type  cml_data_types:CML_STRING_T;  
                    config false;
                } // END of cistPortrole definition.

                leaf portName  {
                    mandatory false;                    
                    type  cml_data_types:CML_STRING_T;  
                    config false;
                } // END of portName definition.

                leaf portNumber  {
                    mandatory false;                    
                    type  cml_data_types:CML_UINT32_T;  
                    config false;
                } // END of portNumber definition.

                leaf cistpathCost  {
                    mandatory false;                    
                    type  cml_data_types:CML_UINT32_T;  
                    config false;
                } // END of cistpathCost definition.

                leaf cistPriority  {
                    mandatory false;                    
                    type  cml_data_types:CML_INT32_T;  
                    config false;
                } // END of cistPriority definition.

                leaf cisthelloTime  {
                    mandatory false;                    
                    type  cml_data_types:CML_INT32_T;  
                    config false;
                } // END of cisthelloTime definition.

                leaf cistforwardDelay  {
                    mandatory false;                    
                    type  cml_data_types:CML_INT32_T;  
                    config false;
                } // END of cistforwardDelay definition.

                leaf portspanningTree  {
                    mandatory false;                    
                    type  cml_data_types:CML_STRING_T;  
                    config false;
                } // END of portspanningTree definition.

                leaf porttopChangeack  {
                    mandatory false;                    
                    type  cml_data_types:CML_STRING_T;  
                    config false;
                } // END of porttopChangeack definition.

                leaf configPending  {
                    mandatory false;                    
                    type  cml_data_types:CML_STRING_T;  
                    config false;
                } // END of configPending definition.

                leaf portconfbpduSent  {
                    mandatory false;                    
                    type  cml_data_types:CML_UINT32_T;  
                    config false;
                } // END of portconfbpduSent definition.

                leaf portconfbpduRecieved  {
                    mandatory false;                    
                    type  cml_data_types:CML_UINT32_T;  
                    config false;
                } // END of portconfbpduRecieved definition.

                leaf porttcnbpduSent  {
                    mandatory false;                    
                    type  cml_data_types:CML_UINT32_T;  
                    config false;
                } // END of porttcnbpduSent definition.

                leaf porttcnbpduRecieved  {
                    mandatory false;                    
                    type  cml_data_types:CML_UINT32_T;  
                    config false;
                } // END of porttcnbpduRecieved definition.

                leaf portForwardTransition  {
                    mandatory false;                    
                    type  cml_data_types:CML_UINT32_T;  
                    config false;
                } // END of portForwardTransition definition.

                leaf helloTimerstate  {
                    mandatory false;                    
                    type  cml_data_types:CML_STRING_T;  
                    config false;
                } // END of helloTimerstate definition.

                leaf helloTimervalue  {
                    mandatory false;                    
                    type  cml_data_types:CML_INT32_T;  
                    config false;
                } // END of helloTimervalue definition.

                leaf forwardTimerstate  {
                    mandatory false;                    
                    type  cml_data_types:CML_STRING_T;  
                    config false;
                } // END of forwardTimerstate definition.

                leaf forwardTimervalue  {
                    mandatory false;                    
                    type  cml_data_types:CML_INT32_T;  
                    config false;
                } // END of forwardTimervalue definition.

                leaf messageTimerstate  {
                    mandatory false;                    
                    type  cml_data_types:CML_STRING_T;  
                    config false;
                } // END of messageTimerstate definition.

                leaf messageageTimervalue  {
                    mandatory false;                    
                    type  cml_data_types:CML_INT32_T;  
                    config false;
                } // END of messageageTimervalue definition.

                leaf topologychangeTimerstate  {
                    mandatory false;                    
                    type  cml_data_types:CML_STRING_T;  
                    config false;
                } // END of topologychangeTimerstate definition.

                leaf topologychangeTimervalue  {
                    mandatory false;                    
                    type  cml_data_types:CML_INT32_T;  
                    config false;
                } // END of topologychangeTimervalue definition.

                leaf holdTimerstate  {
                    mandatory false;                    
                    type  cml_data_types:CML_STRING_T;  
                    config false;
                } // END of holdTimerstate definition.

                leaf holdTimervalue  {
                    mandatory false;                    
                    type  cml_data_types:CML_INT32_T;  
                    config false;
                } // END of holdTimervalue definition.

                leaf messageageExpiry  {
                    mandatory false;                    
                    type  cml_data_types:CML_UINT32_T;  
                    config false;
                } // END of messageageExpiry definition.

                leaf similarbpduCount  {
                    mandatory false;                    
                    type  cml_data_types:CML_UINT32_T;  
                    config false;
                } // END of similarbpduCount definition.

                leaf sourcemacCount  {
                    mandatory false;                    
                    type  cml_data_types:CML_INT32_T;  
                    config false;
                } // END of sourcemacCount definition.

                leaf totalsourcemacRecieved  {
                    mandatory false;                    
                    type  cml_data_types:CML_INT32_T;  
                    config false;
                } // END of totalsourcemacRecieved definition.

                leaf portcistnextState  {
                    mandatory false;                    
                    type  cml_data_types:CML_STRING_T;  
                    config false;
                } // END of portcistnextState definition.

                leaf porttopologyChangetime  {
                    mandatory false;                    
                    type  cml_data_types:CML_UINT32_T;  
                    config false;
                } // END of porttopologyChangetime definition.

                leaf designatedrootPathcost  {
                    mandatory false;                    
                    type  cml_data_types:CML_UINT32_T;  
                    config false;
                } // END of designatedrootPathcost definition.

                leaf designatedInsPortid  {
                    mandatory false;                    
                    type  cml_data_types:CML_UINT16_T;  
                    config false;
                } // END of designatedInsPortid definition.

                leaf mstiInstancedesignatedRoot  {
                    mandatory false;                    
                    type  cml_data_types:CML_STRING_T;  
                    config false;
                } // END of mstiInstancedesignatedRoot definition.

                leaf mstiInstanceBridgeId  {
                    mandatory false;                    
                    type  cml_data_types:CML_STRING_T;  
                    config false;
                } // END of mstiInstanceBridgeId definition.

                leaf stpMultiCastAddr  {
                    mandatory false;                    
                    type  cml_data_types:CML_STRING_T;  
                    config false;
                } // END of stpMultiCastAddr definition.

                leaf instanceBridgeMacAddress  {
                    mandatory false;                    
                    type  cml_data_types:CML_STRING_T;  
                    config false;
                } // END of instanceBridgeMacAddress definition.

                leaf instancetopologyChange  {
                    mandatory true;                    
                    type  cml_data_types:CML_STRING_T;  
                    config false;
                } // END of instancetopologyChange definition.

                leaf instanceTopologychangedetected  {
                    mandatory true;                    
                    type  cml_data_types:CML_STRING_T;  
                    config false;
                } // END of instanceTopologychangedetected definition.

                leaf instlastTopologychangerecievedfrom  {
                    mandatory true;                    
                    type  cml_data_types:CML_STRING_T;  
                    config false;
                } // END of instlastTopologychangerecievedfrom definition.

                leaf runtimevlanId  {
                    mandatory false;                    
                    type  cml_data_types:CML_STRING_T;  
                    config false;
                } // END of runtimevlanId definition.

                leaf restrictedTCN  {
                    mandatory false;                    
                    type  cml_data_types:CML_BOOL_T;  
                    default false;
                    config true;
                } // END of restrictedTCN definition.

                leaf restrictedRole  {
                    mandatory false;                    
                    type  cml_data_types:CML_BOOL_T;  
                    default false;
                    config true;
                } // END of restrictedRole definition.

            } // End of mstp_interface-list
        } // End of mstp-list
    } // END of mstp-grouping definition.


}
