/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-rsvp.yang
*
*/

module ipi-rsvp {

    yang-version 1.1;

    namespace   "http://www.ipinfusion.com/yang/ocnos/ipi-rsvp";

    prefix "ipi-rsvp";

    import cml-data-types {
        prefix cml-data-types;
        revision-date 2022-09-30;
    }

    import ipi-rsvp-types {
        prefix ipi-rsvp-types;
        revision-date 2022-06-01;
    }

    import ipi-interface {
        prefix ipi-interface;
        revision-date 2022-08-24;
    }

    import ietf-inet-types {
        prefix inet;
        revision-date 2013-07-15;
    }

    import feature-list {
        prefix feature-list;
        revision-date 2023-02-21;
    }

    include ipi-rsvp-trunk { revision-date 2022-08-10;}
    include ipi-rsvp-interface { revision-date 2022-06-01;}
    include ipi-rsvp-session { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Resource Reservation Protocol";


    revision "2022-08-10" {
        description "Fix for rsvp-path hop addresses delete";
        reference " 0.7.8.";
    }

    revision "2022-07-25" {
        description "Fix for create/replace operation for rsvp-path hop addresses";
        reference " 0.7.7.";
    }

    revision "2022-07-15" {
        description "Added configure dependency tag for ingress multipath group name";
        reference " 0.7.6.";
    }

    revision "2022-07-08" {
        description "Fix for db sync issues for RSVP trunk CLIs deletion";
        reference " 0.7.5.";
    }

    revision "2022-07-07" {
        description "Fix for RSVP debug deletion";
        reference " 0.7.4.";
    }

    revision "2022-06-01" {
        description "Updated the yang file with feature";
        reference " 0.7.3.";
    }

    revision "2022-02-02" {
        description "Added leafref and when conditions for multipath and path dependents";
        reference " 0.7.2.";
    }

    revision "2022-01-05" {
        description "Added selected-ingress-ipv4 and selected-ingress-ipv6 read only attributes";
        reference " 0.7.1.";
    }

    revision "2021-12-22" {
        description "Introduced HAVE_CUSTOM2_MPLS for Dune platforms and replaced HAVE_CUSTOM2_QOS";
        reference " 0.7.0.";
    }

    revision "2021-10-01" {
        description "Added DC flag check for bypass-trunk";
        reference " 0.6.7.";
    }

    revision "2021-09-20" {
        description "Update default value for RSVP_DEBUG";
        reference " 0.6.6.";
    }

    revision "2021-09-17" {
        description "Added DC flag check for entropy command";
        reference " 0.6.5.";
    }

    revision "2021-09-03" {
        description "Update descriptions of attribute";
        reference " 0.6.4.";
    }

    revision "2021-08-27" {
        description "Updated length constraint for rsvp path-name";
        reference " 0.6.3.";
    }

    revision "2021-06-28" {
        description "Modified the attribute name from dscp-exp-max-exp-val to dscp-exp-map-exp-val";
        reference " 0.6.2.";
    }

    revision "2021-06-26" {
        description "Updated multipath runtime attribute for trunk entry";
        reference " 0.6.1.";
    }

    revision "2021-06-25" {
        description "llsp attribute removed for HAVE_CUSTOM2_QOS from bypass trunk";
        reference " 0.6.0.";
    }

    revision "2021-06-01" {
        description "Modified the attribute name from enable-refresh-reduction to disable-refresh-reduction";
        reference " 0.5.1.";
    }

    revision "2021-03-31" {
        description "Addition of PCEP-RSVP related attributes";
        reference " 0.5.0.";
    }

    revision "2021-03-27" {
        description "Added notification for RSVP Tunnel re-optimization";
        reference " 0.4.1.";
    }

    revision "2021-03-22" {
        description "Added SRLG related attribue and Modified dscp related attribute";
        reference " 0.4.0.";
    }

    revision "2021-01-27" {
        description "Updated XPATH to API mappings. Fixed known bugs";
        reference " 0.3.0.";
    }

    revision "2020-12-15" {
        description "Change to have data-types in lower case instead of camel case";
        reference " 0.2.0.";
    }

    revision "2018-06-21" {
        description "Initial Version";
        reference " 0.1.0.";
    }

    grouping rsvp-debug-config {
        description
            "RSVP debug configuration";
        leaf debug-options  {
            type  ipi-rsvp-types:rsvp_debug_t;
            description "Use this attribute to enable all debugging options for an RSVP daemon.
                        Enable RSVP debugs at confgiuration mode";
        } // END of debug-options definition.

    } // END of rsvp-debug-config definition.
    grouping rsvp-snmp-config {
        description
            "RSVP snmp configuration";
        leaf enable-rsvp-trap  {
            if-feature feature-list:HAVE_SNMP;
            type  empty;
            description "Use this attribute to enable/disable the rsvp trap";
        } // END of enable-rsvp-trap definition.

    } // END of rsvp-snmp-config definition.
    grouping rsvp-dscp-state {
        description
            "Operational information of dscp";
        leaf-list supported-dscp-class-name  {
            if-feature feature-list:HAVE_SWFWDR;
            type  string {
                length "1..1965";
                pattern "[^?' =,>|]+";
            }
            description "Supported dscp class name";
        } // END of supported-dscp-class-name definition.

        leaf-list supported-dscp-bits  {
            if-feature feature-list:HAVE_SWFWDR;
            type  string {
                length "1..1965";
                pattern "[^?' =,>|]+";
            }
            description "Supported dscp bits";
        } // END of supported-dscp-bits definition.

        leaf-list class-exp-mapping-name  {
            if-feature feature-list:HAVE_SWFWDR;
            type  string {
                length "1..1965";
                pattern "[^?' =,>|]+";
            }
            description "exp mapping class name";
        } // END of class-exp-mapping-name definition.

        leaf-list class-exp-mapping-bits  {
            if-feature feature-list:HAVE_SWFWDR;
            type  string {
                length "1..1965";
                pattern "[^?' =,>|]+";
            }
            description "exp mapping class bits";
        } // END of class-exp-mapping-bits definition.

        leaf-list class-exp-mapping  {
            if-feature feature-list:NOT_HAVE_SWFWDR;
            type  uint32;
            description "Value of the exp class map";
        } // END of class-exp-mapping definition.

        leaf-list class-exp-mapping-value  {
            if-feature feature-list:NOT_HAVE_SWFWDR;
            type  uint8;
            description "Value of the exp class map";
        } // END of class-exp-mapping-value definition.

    } // END of rsvp-dscp-state definition.
    grouping rsvp-dste-state {
        description
            "Operational parameters of diff serv";
        leaf class-type-name  {
            type  string {
                length "1..1965";
                pattern "[^?' =,>|]+";
            }
            description "DiffServ Class Type Name";
        } // END of class-type-name definition.

        leaf class-type-number  {
            type  uint8;
            description "DiffServ Class Type Number";
        } // END of class-type-number definition.

        leaf te-class-type-name  {
            type  string {
                length "1..1965";
                pattern "[^?' =,>|]+";
            }
            description "DiffServ Traffic Enginnering Class Type Name";
        } // END of te-class-type-name definition.

        leaf te-class-type-number  {
            type  uint8;
            description "DiffServ Traffic Enginnering Class Type Number";
        } // END of te-class-type-number definition.

        leaf te-priority  {
            type  uint8;
            description "Priority of diffserv traffic engineering";
        } // END of te-priority definition.

        leaf dste-enable-status  {
            type  ipi-rsvp-types:rsvp_status_t;
            description "Status of diffserv traffic engineering";
        } // END of dste-enable-status definition.

    } // END of rsvp-dste-state definition.
    grouping rsvp-global-config {
        description
            "configuration parameters for rsvp";
        leaf rsvp  {
            type  ipi-rsvp-types:rsvp_instance_t;
            mandatory true;
            description "Use this attribute to enter router mode from configure mode and to
                        enable the RSVP daemon, if it is not already enabled and Enter in to
                        router rsvp mode from configure mode";
        } // END of rsvp definition.

        leaf enable-explicit-null  {
            type  empty;
            description "Use this attribute to send explicit-null labels for directly-connected
                        forwarding equivalency classes (FECs) instead of implicit-null labels.
                        This command controls the label value advertised to an egress router
                        of an LSP. By default, implicit null label (label 3) is advertised for
                        directly connected FECs. If implicit-null label is advertised, the
                        penultimate hop removes the label and sends the packet as a plain IP
                        packet to the egress router. The explicit-null command advertises
                        label 0 and retains the label so the egress router can pop it. For
                        details about usage of explicit-null, please refer to RFC 3032.Use the
                        no parameter with this command to stop sending explicit-null labels
                        for directly-connected FECs and resume sending implicit-null labels.";
        } // END of enable-explicit-null definition.

        leaf enable-local-protection  {
            type  empty;
            description "Use this attribute to enable/disable the local repair of explicit
                        routes for which this router is a transit node";
        } // END of enable-local-protection definition.

        leaf enable-php  {
            type  empty;
            description "Use this attribute to enable Penultimate-Hop-Popping for the router.
                        An egress router sends either the implicit-null or the explicit-null
                        label for LSPs. If the no-php command has been enabled, the egress
                        router sends non-reserved labels (those labels in the label pool range
                        allotted to RSVP) to the upstream router.";
        } // END of enable-php definition.

        leaf enable-entropy-label-capability  {
            if-feature feature-list:NOT_HAVE_CUSTOM1_MPLS;
            type  empty;
            description "Use this attribute to enable Entropy Label Capability (ELC) for the
                        router. An egress router may insert ELC TLV in Attributes Flags TLV of
                        Resv message. If no entropy-label-capability command has been enabled,
                        the egress router doesnt include ELC TLV in Resv message.";
        } // END of enable-entropy-label-capability definition.

        leaf disable-refresh-resv-parsing  {
            type  empty;
            description "Use this attribute to disable parsing of Refresh RESV messages
                        received from upstream nodes. Use this attribute to minimize message
                        processing by RSVP when you are sure that a particular router does not
                        need to parse Refresh RESV messages to check for changes because LSPs
                        passing through this router are not required to be updated
                        simultaneously.";
        } // END of disable-refresh-resv-parsing definition.

        leaf disable-refresh-path-parsing  {
            type  empty;
            description "Use this attribute to disable parsing of Refresh PATH messages
                        received from upstream nodes. Use this attribute to minimize message
                        processing by RSVP when you are sure that a particular router does not
                        need to parse Refresh-PATH messages to check for changes, because LSPs
                        passing through this router are not required to be updated
                        simultaneously.";
        } // END of disable-refresh-path-parsing definition.

        leaf disable-loop-detection  {
            type  empty;
            description "Use this attribute to turn on loop detection for Path and Reservation
                        messages exchanged between LSRs";
        } // END of disable-loop-detection definition.

        leaf revert-timer  {
            type  uint32 {
                 range "1..65535"  {
                    description "1..65535: Supported range 1 - 65535";
                 }
            }
            default "60";
            description "Use this attribute to Hold-on timer before revert back to primary
                        session";
        } // END of revert-timer definition.

        leaf enable-bundle-send  {
            type  empty;
            description "Use thi attrubute Enable sending of BUNDLE messages for all the
                        interfaces";
        } // END of enable-bundle-send definition.

        leaf ingress  {
            type  inet:ipv4-address;
            description "Use this attribute to specify a .from. IPv4 address for the RSVP
                        daemon. This command can be invoked from either the router rsvp mode
                        or from the rsvp-trunk mode. In the RSVP router mode, this command
                        defines the source address as an IPv4 packet sent out by the RSVP
                        daemon. In the RSVP trunk mode, this command indicates a sender.s
                        address in the sender template object that is used in path messages.";
        } // END of ingress definition.

        leaf ingress-ipv6  {
            if-feature feature-list:HAVE_MPLS_FWD;
            type  inet:ipv6-address;
            description "Use this attribute to specify a .from. IPv6 address for the RSVP
                        daemon. This command can be invoked from either the router rsvp mode
                        or from the rsvp-trunk mode. In the router rsvp mode, this command
                        defines the source address as an IPv4 packet being sent out by the
                        RSVP daemon. In the rsvp trunk mode, this command indicates a
                        sender.saddress in the sender template object that is used in path
                        messages.";
        } // END of ingress-ipv6 definition.

    } // END of rsvp-global-config definition.
    grouping rsvp-global-state {
        description
            "operational parameters for rsvp";
        leaf rsvp-version  {
            type  uint16;
            description "Version of rsvp";
        } // END of rsvp-version definition.

        leaf rsvp-state  {
            type  ipi-rsvp-types:rsvp_status_t;
            description "State of the RSVP protocol";
        } // END of rsvp-state definition.

        leaf refresh-timer  {
            type  uint32;
            units "seconds";
            description "The timer specifies the interval after which Path and/ or Reservation
                        Request";
        } // END of refresh-timer definition.

        leaf keep-multiplier  {
            type  uint32;
            units "seconds";
            description "Reservation lifetime value for a Labeled Switched Path";
        } // END of keep-multiplier definition.

        leaf preemption-type  {
            type  ipi-rsvp-types:rsvp_preemption_type_t;
            description "Type of the preemption";
        } // END of preemption-type definition.

        leaf selected-ingress-ipv4  {
            type  inet:ipv4-address;
            description "Auto Selected IPv4 ingress id when ingress-id is not explicitly
                        configured";
        } // END of selected-ingress-ipv4 definition.

        leaf selected-ingress-ipv6  {
            if-feature feature-list:HAVE_IPV6;
            type  inet:ipv6-address;
            description "Auto Selected IPv6 ingress id when ingress-id is not explicitly
                        configured";
        } // END of selected-ingress-ipv6 definition.

    } // END of rsvp-global-state definition.
    grouping rsvp-protocol-state {
        description
            "RSVP  message counters";
        leaf in-path-messages  {
            type  uint32;
            description "Number of received RSVP Path messages";
        } // END of in-path-messages definition.

        leaf in-path-error-messages  {
            type  uint32;
            description "Number of received RSVP Path Error messages";
        } // END of in-path-error-messages definition.

        leaf in-path-tear-messages  {
            type  uint32;
            description "Number of received RSVP Path Error messages";
        } // END of in-path-tear-messages definition.

        leaf in-reservation-fixed-filter-messages  {
            type  uint32;
            description "Number of received RSVP Resv fixed filter style messages";
        } // END of in-reservation-fixed-filter-messages definition.

        leaf in-reservation-wildcard-filter-messages  {
            type  uint32;
            description "Number of received RSVP Resv wildcard filter style messages";
        } // END of in-reservation-wildcard-filter-messages definition.

        leaf in-reservation-shared-explicit-messages  {
            type  uint32;
            description "Number of received RSVP Resv shared explicit style messages";
        } // END of in-reservation-shared-explicit-messages definition.

        leaf in-reservation-error-messages  {
            type  uint32;
            description "Number of received RSVP Resv Error messages";
        } // END of in-reservation-error-messages definition.

        leaf in-reservation-tear-messages  {
            type  uint32;
            description "Number of received RSVP Resv Tear messages";
        } // END of in-reservation-tear-messages definition.

        leaf in-reservation-conform-messages  {
            type  uint32;
            description "Number of received RSVP Resv Conform messages";
        } // END of in-reservation-conform-messages definition.

        leaf in-hello-messages  {
            type  uint32;
            description "Number of received RSVP hello messages";
        } // END of in-hello-messages definition.

        leaf in-bundle-messages  {
            type  uint32;
            description "Number of received RSVP bundle messages";
        } // END of in-bundle-messages definition.

        leaf in-acknowledge-messages  {
            type  uint32;
            description "Number of received RSVP refresh reduction acknowledge messages";
        } // END of in-acknowledge-messages definition.

        leaf in-srefresh-messages  {
            type  uint32;
            description "Number of received RSVP summary refresh messages";
        } // END of in-srefresh-messages definition.

        leaf in-notify-messages  {
            type  uint32;
            description "Number of received RSVP Notification messages";
        } // END of in-notify-messages definition.

        leaf out-path-messages  {
            type  uint32;
            description "Number of sent RSVP PATH messages";
        } // END of out-path-messages definition.

        leaf out-path-error-messages  {
            type  uint32;
            description "Number of sent RSVP Path Error messages";
        } // END of out-path-error-messages definition.

        leaf out-path-tear-messages  {
            type  uint32;
            description "Number of sent RSVP Path Tear messages";
        } // END of out-path-tear-messages definition.

        leaf out-reservation-fixed-filter-messages  {
            type  uint32;
            description "Number of sent RSVP Resv fixed filter style messages";
        } // END of out-reservation-fixed-filter-messages definition.

        leaf out-reservation-wildcard-filter-messages  {
            type  uint32;
            description "Number of sent RSVP Resv wildcard filter style messages";
        } // END of out-reservation-wildcard-filter-messages definition.

        leaf out-reservatoion-shared-explicit-messages  {
            type  uint32;
            description "Number of sent RSVP Resv shared explicit style messages";
        } // END of out-reservatoion-shared-explicit-messages definition.

        leaf out-reservation-error-messages  {
            type  uint32;
            description "Number of sent RSVP Resv Error messages";
        } // END of out-reservation-error-messages definition.

        leaf out-reservation-tear-messages  {
            type  uint32;
            description "Number of sent RSVP Resv Tear messages";
        } // END of out-reservation-tear-messages definition.

        leaf out-reservation-conform-messages  {
            type  uint32;
            description "Number of sent RSVP Resv Conform messages";
        } // END of out-reservation-conform-messages definition.

        leaf out-hello-messages  {
            type  uint32;
            description "Number of sent RSVP hello messages";
        } // END of out-hello-messages definition.

        leaf out-bundle-messages  {
            type  uint32;
            description "Number of sent RSVP bundle messages";
        } // END of out-bundle-messages definition.

        leaf out-acknowledge-messages  {
            type  uint32;
            description "Number of sent RSVP refresh reduction messages";
        } // END of out-acknowledge-messages definition.

        leaf out-srefresh-messages  {
            type  uint32;
            description "Number of sent RSVP summary refresh messages";
        } // END of out-srefresh-messages definition.

        leaf out-notify-messages  {
            type  uint32;
            description "Number of sent RSVP Notification messages";
        } // END of out-notify-messages definition.

    } // END of rsvp-protocol-state definition.
    grouping rsvp-statistics-state {
        description
            "RSVP protocol statistics";
        leaf total-number-of-sessions  {
            type  int32;
            description "Total number of sessions created";
        } // END of total-number-of-sessions definition.

        leaf active-sessions  {
            type  int32;
            description "Total number of active sessions";
        } // END of active-sessions definition.

        leaf total-ingress-sessions  {
            type  int32;
            description "Total number of ingress sessions on this node";
        } // END of total-ingress-sessions definition.

        leaf active-ingress-sessions  {
            type  int32;
            description "Total number of active ingress sessions on this node";
        } // END of active-ingress-sessions definition.

        leaf total-transit-sessions  {
            type  int32;
            description "Total number of transit sessions on this node";
        } // END of total-transit-sessions definition.

        leaf active-transit-sessions  {
            type  int32;
            description "Total number of active transit sessions on this node";
        } // END of active-transit-sessions definition.

        leaf total-egress-sessions  {
            type  int32;
            description "Total number of egress sessions on this node";
        } // END of total-egress-sessions definition.

        leaf active-egress-sessions  {
            type  int32;
            description "Total number of active egress sessions on this node";
        } // END of active-egress-sessions definition.

    } // END of rsvp-statistics-state definition.
    grouping rsvp-global-cspf-config {
        description
            "configuration parameters for cspf";
        leaf disable-cspf  {
            type  empty;
            description "Use this attribute to disable the use of the Constrained Shortest Path
                        First (CSPF) server for all RSVP sessions.Disable CSPF when no nodes
                        support the required traffic engineering extensions.When this command
                        is executed in Router mode, CSPF is enabled for all configured RSVP
                        sessions, and all RSVP sessions configured from this point forward. If
                        the default CSPF per RSVP session is enabled, it will be disabled. The
                        CSPF status for RSVP sessions can be verified using the show rsvp
                        session command with the detail option";
        } // END of disable-cspf definition.

        leaf cspf-lsp-reoptimization-time  {
            type  uint32 {
                 range "1..240"  {
                    description "1..240: Supported range 1 - 240";
                 }
            }
            default "5";
            description "Use this attribute to configure timer for the reoptimizing lsp.";
        } // END of cspf-lsp-reoptimization-time definition.

    } // END of rsvp-global-cspf-config definition.
    grouping rsvp-global-graceful-restart-config {
        description
            "configuration parameters for graceful-restart";
        leaf enable-graceful-restart  {
            type  empty;
            mandatory true;
            description "Use this attribute to enable RSVP-TE Graceful Restart capability on a
                        router. This is a global parameter. RSVP-TE determines whether or not
                        to send the graceful restart capability object in its hello message.
                        However, this capability also depends on support for graceful restart
                        on the neighbor router.";
        } // END of enable-graceful-restart definition.

        leaf restart-time  {
            type  uint32 {
                 range "10000..600000"  {
                    description "10000..600000: Supported range 10000 - 600000";
                 }
            }
            default "180000";
            description "Use this attribute to set a restart time for an RSVP-TE graceful
                        restart configuration.";
        } // END of restart-time definition.

        leaf recovery-time  {
            type  uint32 {
                 range "60000..3600000"  {
                    description "60000..3600000: Supported range 60000 - 3600000";
                 }
            }
            default "360000";
            description "Use this attribute to set a recovery time for an RSVP-TE graceful
                        restart configuration.";
        } // END of recovery-time definition.

    } // END of rsvp-global-graceful-restart-config definition.
    grouping rsvp-global-graceful-restart-state {
        description
            "Operational parameters for graceful-restart";
        leaf graceful-restart-state  {
            if-feature feature-list:HAVE_RSVP_GRST;
            type  ipi-rsvp-types:rsvp_graceful_restart_status_t;
            description "State of graceful restart operation";
        } // END of graceful-restart-state definition.

        leaf graceful-restart-set-recovery  {
            if-feature feature-list:HAVE_RSVP_GRST;
            type  ipi-rsvp-types:rsvp_graceful_restart_recovery_status_t;
            description "Sending Recovery Time";
        } // END of graceful-restart-set-recovery definition.

        leaf restart-time  {
            if-feature feature-list:HAVE_RSVP_GRST;
            type  uint32;
            units "seconds";
            description "Restart Time";
        } // END of restart-time definition.

        leaf recovery-time  {
            if-feature feature-list:HAVE_RSVP_GRST;
            type  uint32;
            units "seconds";
            description "Recovery Time";
        } // END of recovery-time definition.

        leaf remaining-restart-time  {
            if-feature feature-list:HAVE_RSVP_GRST;
            type  uint32;
            units "seconds";
            description "Remaining Restart Time";
        } // END of remaining-restart-time definition.

        leaf remaining-recovery-time  {
            if-feature feature-list:HAVE_RSVP_GRST;
            type  uint32;
            units "seconds";
            description "Remaining Recovery Time";
        } // END of remaining-recovery-time definition.

    } // END of rsvp-global-graceful-restart-state definition.
    grouping rsvp-global-graceful-restart {
        description
            "Top level groupings for graceful restart";
        container graceful-restart {
            when " /ipi-rsvp:rsvp-te/ipi-rsvp:rsvp-instance/ipi-rsvp:config ";
            if-feature feature-list:HAVE_RSVP_GRST;
            description
                "container for graceful restart";
            container config {
                presence "Enable Rsvp Graceful Restart";
                description
                    "configuration container for graceful-restart";
                uses rsvp-global-graceful-restart-config;
            } // END of config-container definition.
            container state {
                config false;
                description
                    "Operational container for graceful-restart";
                uses rsvp-global-graceful-restart-config;
            } // END of state-container definition.
        } // END of graceful-restart-container definition.
    } // END of rsvp-global-graceful-restart definition.
    grouping rsvp-global-frr-config {
        description
            "global configuration parameters for fast-reroute";
        leaf preemption-type  {
            if-feature feature-list:HAVE_MPLS_FRR;
            type  ipi-rsvp-types:rsvp_preemp_t;
            default "less-lsp-preempted";
            description "Use this attribute to set preemption type for an LSP for the router.
                        Preemption of an LSP or set of LSPs happens based on bandwidth
                        constraints like preempting an LSP cause less number of LSPs be
                        preempted upon satisfying the bandwidth required, preempting an LSP or
                        set of LSPs which results in an LSP having less unused(remaining)
                        bandwidth.";
        } // END of preemption-type definition.

        leaf bypass-lsp-addr-query-interval  {
            if-feature feature-list:HAVE_MPLS_FRR;
            type  uint8 {
                 range "10..60"  {
                    description "10..60: Supported range 10 - 60";
                 }
            }
            default "60";
            description "Modify interval of bypass trunk querying LSP address";
        } // END of bypass-lsp-addr-query-interval definition.

        leaf detour-id  {
            if-feature feature-list:HAVE_MPLS_FRR;
            type  ipi-rsvp-types:rsvp_detour_iden_t;
            default "path";
            description "Use this attribute to set a path-specific detour LSP identification
                        method, using the detour object.";
        } // END of detour-id definition.

    } // END of rsvp-global-frr-config definition.
    grouping rsvp-global-gmpls-config {
        description
            "global configuration parameters for gmpls";
        leaf enable-gmpls-notification  {
            type  empty;
            description "Use this attribute to enable a router.s ability to send notification
                        messages for all GMPLS LSPs configured on the box. This command can be
                        used to enable or disable sending notification messages. By default,
                        notification is enabled for all GMPLS LSPs configured on the box.";
        } // END of enable-gmpls-notification definition.

        leaf enable-pre-program-suggested-label  {
            type  empty;
            description "Enable suggested label feature of gmpls";
        } // END of enable-pre-program-suggested-label definition.

    } // END of rsvp-global-gmpls-config definition.
    grouping rsvp-global-srlg-config {
        description
            "global configuration parameters for Shared Risk Link Groups";
        leaf srlg-disjoint  {
            if-feature feature-list:HAVE_SRLG;
            type  ipi-rsvp-types:rsvp_te_srlg_disjoint_type_t;
            description "Use the attribute to configure the srlg-disjoint path-protection in
                        global mode";
        } // END of srlg-disjoint definition.

    } // END of rsvp-global-srlg-config definition.
    grouping rsvp-global-diff-serv-config {
        description
            "global configuration parameters for diff serv";
        leaf enable-override-diff-serv  {
            if-feature feature-list:HAVE_DIFFSERV;
            type  empty;
            description "Setup a non-diffserv lsp if diffserv obj is not present in Path
                        message";
        } // END of enable-override-diff-serv definition.

    } // END of rsvp-global-diff-serv-config definition.
    grouping rsvp-neighbor-config {
        description
            "configuration parameters for rsvp neighbor";
        leaf address  {
            type  inet:ip-address;
            description "Use this attribute to designate a neighbor IPv4 or IPv6 address to use
                        when exchanging hello messages. Any neighbor hello message that is not
                        explicitly identified is rejected. Use to Identify a directly
                        connected ipv4 neighbor";
        } // END of address definition.

    } // END of rsvp-neighbor-config definition.
    grouping rsvp-neighbor-state {
        description
            "Operational parameters for rsvp neighbor";
        leaf neighbor-ip-address  {
            type  inet:ip-address;
            description "Neighbor ip address";
        } // END of neighbor-ip-address definition.

        leaf session-count  {
            type  uint32;
            description "Number of sessions";
        } // END of session-count definition.

        leaf refresh-reduction  {
            type  ipi-rsvp-types:rsvp_neighbor_refresh_reduction_status_t;
            description "Status of the neighbor refresh reduction";
        } // END of refresh-reduction definition.

        leaf upstream-lsp-count  {
            type  uint32;
            description "Number of upstream LSPs";
        } // END of upstream-lsp-count definition.

        leaf downstream-lsp-count  {
            type  uint32;
            description "Number of downstream LSPs";
        } // END of downstream-lsp-count definition.

        leaf neighbor-state  {
            type  ipi-rsvp-types:rsvp_neighbor_hello_state_t;
            description "Neighbot hello state";
        } // END of neighbor-state definition.

        leaf srefresh-remaining-time  {
            type  uint32;
            units "seconds";
            description "Summary refresh remaining time";
        } // END of srefresh-remaining-time definition.

        leaf neighbor-type  {
            type  ipi-rsvp-types:rsvp_neighbor_type_t;
            description "Type of the neighbor(Implicit/Explicit)";
        } // END of neighbor-type definition.

        leaf max-acknowledge-packet  {
            type  uint16;
            description "Maximum ackonwledge packet";
        } // END of max-acknowledge-packet definition.

        leaf used-acknowledge-packet  {
            type  uint16;
            description "Used ackonwledge packet";
        } // END of used-acknowledge-packet definition.

        leaf max-bundle-packet  {
            type  uint16;
            description "Maximum bundle packets";
        } // END of max-bundle-packet definition.

        leaf used-bundle-packet  {
            type  uint16;
            description "Used bundle packets";
        } // END of used-bundle-packet definition.

    } // END of rsvp-neighbor-state definition.
    grouping rsvp-srefresh-state {
        description
            "Operational parameters for rsvp summary refresh";
        leaf address  {
            type  inet:ip-address;
            description "Neighbor address";
        } // END of address definition.

    } // END of rsvp-srefresh-state definition.
    grouping rsvp-trunk-id-state {
        description
            "Operational parameters for rsvp trunk identifier";
        leaf trunk-id  {
            type  uint32;
            description "rsvp trunk identifier";
        } // END of trunk-id definition.

    } // END of rsvp-trunk-id-state definition.
    grouping rsvp-local-addr-state {
        description
            "Operational parameters for rsvp local ipv4/ipv6 address";
        leaf if-name  {
            type  leafref {
                path  "/ipi-interface:interfaces/ipi-interface:interface/ipi-interface:name";
            }
            description "Name of the interface";
        } // END of if-name definition.

        leaf family  {
            type  ipi-rsvp-types:rsvp_addr_family_t;
            description "Address family";
        } // END of family definition.

        leaf addr  {
            type  inet:ip-address;
            description "ip address";
        } // END of addr definition.

    } // END of rsvp-local-addr-state definition.
    grouping rsvp-nexthop-cache-state {
        description
            "Operational parameters for rsvp Nexthop";
        leaf prefix  {
            type  cml-data-types:cml_ip_prefix_addr_t;
            description "Prefix of this radix";
        } // END of prefix definition.

        leaf number-of-sessions  {
            type  uint32;
            description "Number of sessions";
        } // END of number-of-sessions definition.

        leaf ip-addr  {
            type  inet:ip-address;
            description "ip addrress";
        } // END of ip-addr definition.

        leaf if-name  {
            type  leafref {
                path  "/ipi-interface:interfaces/ipi-interface:interface/ipi-interface:name";
            }
            description "Name of the interface";
        } // END of if-name definition.

    } // END of rsvp-nexthop-cache-state definition.
    grouping rsvp-map-route-state {
        description
            "Operational parameters for rsvp mapped ipv4/ipv6 address";
        leaf lsp-id  {
            type  uint16;
            description "Label switch path id";
        } // END of lsp-id definition.

        leaf dscp-value  {
            type  string {
                length "1..1965";
                pattern "[^?' =,>|]+";
            }
            description "DSCP value";
        } // END of dscp-value definition.

        leaf prefix-len  {
            type  uint8;
            description "Length of the prefix";
        } // END of prefix-len definition.

        leaf family  {
            type  ipi-rsvp-types:rsvp_addr_family_t;
            description "Address family";
        } // END of family definition.

        leaf trunk-identifier  {
            type  uint16;
            description "Trunk identification";
        } // END of trunk-identifier definition.

        leaf destination  {
            type  inet:ip-address;
            description "Destination address";
        } // END of destination definition.

    } // END of rsvp-map-route-state definition.
    grouping rsvp-admin-group-state {
        description
            "Operational parameters of admin group";
        leaf name  {
            type  string {
                length "1..1965";
                pattern "[^?' =,>|]+";
            }
            description "Name of the admin group";
        } // END of name definition.

        leaf value  {
            type  uint32;
            description "Value of the admin group";
        } // END of value definition.

    } // END of rsvp-admin-group-state definition.

    grouping  rsvp-te-grouping {
    description
        "rsvp configurations";
    container rsvp-te {
        if-feature feature-list:HAVE_RSVPD;
        description
            "rsvp configurations";

        list admin-group {
            key "name";
            config false;
            description
                "list for admin group";
            leaf name  {
                type  leafref {
                    path  "../state/name";
                }
                description "Name of the admin group";
            } // END of name definition.

            container state {
                config false;
                description
                    "state parameters related to admin group";
                uses rsvp-admin-group-state;
            } // END of state-container definition.
        } // End of admin-group-list

        list dste {
            if-feature feature-list:HAVE_DSTE;
            key "class-type-number";
            config false;
            description
                "list for diff serv parametrs";
            leaf class-type-number  {
                type  leafref {
                    path  "../state/class-type-number";
                }
                description "DiffServ Class Type Number";
            } // END of class-type-number definition.

            container state {
                config false;
                description
                    "state parameters related to diff serv";
                uses rsvp-dste-state;
            } // END of state-container definition.
        } // End of dste-list
        container debug {
            description
                "container to enable RSVP debug";
            container config {
                description
                    "configuration container for RSVP debug messages";
                uses rsvp-debug-config;
            } // END of config-container definition.
            container state {
                config false;
                description
                    "state parameters related to RSVP debug messages";
                uses rsvp-debug-config;
            } // END of state-container definition.
        } // END of debug-container definition.
        container snmp-configuration {
            description
                "container to configure snmp";
            container config {
                description
                    "configuration container for snmp";
                uses rsvp-snmp-config;
            } // END of config-container definition.
            container state {
                config false;
                description
                    "state parameters related to RSVP snmp";
                uses rsvp-snmp-config;
            } // END of state-container definition.
        } // END of snmp-configuration-container definition.
        container dscp {
            config false;
            description
                "container related to dscp";
            container state {
                config false;
                description
                    "state parameters related to dscp";
                uses rsvp-dscp-state;
            } // END of state-container definition.
        } // END of dscp-container definition.
        container rsvp-instance {
            description
                "";

            list summary-refresh {
                key "address";
                config false;
                description
                    "Top level list for rsvp summary refresh message";
                leaf address  {
                    type  leafref {
                        path  "../state/address";
                    }
                    description "Neighbor address";
                } // END of address definition.

                container state {
                    config false;
                    description
                        "state conatiner for rsvp summary refresh";
                    uses rsvp-srefresh-state;
                    uses rsvp-trunk-id-state;
                    uses rsvp-trunk-common-state;
                } // END of state-container definition.
            } // End of summary-refresh-list

            list local-address-ipv4 {
                key "addr";
                config false;
                description
                    "Top level list for rsvp local ipv4 address";
                leaf addr  {
                    type  leafref {
                        path  "../state/addr";
                    }
                    description "Local addresses known to RSVP on this node";
                } // END of addr definition.

                container state {
                    config false;
                    description
                        "state conatiner for rsvp local ipv4 address";
                    uses rsvp-local-addr-state;
                } // END of state-container definition.
            } // End of local-address-ipv4-list

            list local-address-ipv6 {
                key "addr";
                config false;
                description
                    "Top level list for rsvp local ipv6 address";
                leaf addr  {
                    type  leafref {
                        path  "../state/addr";
                    }
                    description "Local addresses known to RSVP on this node";
                } // END of addr definition.

                container state {
                    config false;
                    description
                        "state conatiner for rsvp local ipv6 address";
                    uses rsvp-local-addr-state;
                } // END of state-container definition.
            } // End of local-address-ipv6-list

            list rsvp-nexthop {
                key "prefix";
                config false;
                description
                    "Top level list for RSVP next hop information";
                leaf prefix  {
                    type  leafref {
                        path  "../state/prefix";
                    }
                    description "Nexthop Prefix address for the RSVP";
                } // END of prefix definition.

                container state {
                    config false;
                    description
                        "state conatiner for rsvp nexthop";
                    uses rsvp-nexthop-cache-state;
                } // END of state-container definition.
            } // End of rsvp-nexthop-list
            container config {
                presence "Enable Rsvp";
                description
                    "configuration container for rsvp";
                uses rsvp-global-config;
            } // END of config-container definition.
            container state {
                config false;
                description
                    "state conatiner for rsvp";
                container counters {
                    config false;
                    description
                        "Platform wide RSVP statistics and counters";
                    uses rsvp-protocol-state;
                    uses rsvp-statistics-state;
                } // END of counters-container definition.
                uses rsvp-global-config;
                uses rsvp-global-state;
            } // END of state-container definition.
            container route-refresh {
                when " /ipi-rsvp:rsvp-te/ipi-rsvp:rsvp-instance/ipi-rsvp:config ";
                description
                    "container for route-refresh";
                container config {
                    description
                        "configuration container for route-refresh";
                    uses rsvp-rr-config;
                } // END of config-container definition.
                container state {
                    config false;
                    description
                        "state parameters related to route-refresh";
                    uses rsvp-rr-config;
                } // END of state-container definition.
            } // END of route-refresh-container definition.
            container fast-reroute {
                when " /ipi-rsvp:rsvp-te/ipi-rsvp:rsvp-instance/ipi-rsvp:config ";
                if-feature feature-list:HAVE_MPLS_FRR;
                description
                    "container for fast-reroute";
                container config {
                    description
                        "configuration container for fast-reroute";
                    uses rsvp-global-frr-config;
                } // END of config-container definition.
                container state {
                    config false;
                    description
                        "state container for fast-reroute";
                    uses rsvp-global-frr-config;
                } // END of state-container definition.
            } // END of fast-reroute-container definition.
            container cspf {
                when " /ipi-rsvp:rsvp-te/ipi-rsvp:rsvp-instance/ipi-rsvp:config ";
                if-feature feature-list:HAVE_CSPF;
                description
                    "container for cspf";
                container config {
                    description
                        "configuration container for cspf";
                    uses rsvp-global-cspf-config;
                } // END of config-container definition.
                container state {
                    config false;
                    description
                        "state container for cspf";
                    uses rsvp-global-cspf-config;
                } // END of state-container definition.
            } // END of cspf-container definition.
            container global {
                when " /ipi-rsvp:rsvp-te/ipi-rsvp:rsvp-instance/ipi-rsvp:config ";
                description
                    "global container for  hello timers and graceful restart";
                uses rsvp-global-hellos;
                uses rsvp-global-graceful-restart;
            } // END of global-container definition.
            container gmpls {
                when " /ipi-rsvp:rsvp-te/ipi-rsvp:rsvp-instance/ipi-rsvp:config ";
                if-feature feature-list:HAVE_GMPLS;
                description
                    "Top level container for gmpls";
                container config {
                    description
                        "configuration container for gmpls";
                    uses rsvp-global-gmpls-config;
                } // END of config-container definition.
                container state {
                    config false;
                    description
                        "state container for gmpls";
                    uses rsvp-global-gmpls-config;
                } // END of state-container definition.
            } // END of gmpls-container definition.
            container srlg {
                when " /ipi-rsvp:rsvp-te/ipi-rsvp:rsvp-instance/ipi-rsvp:config ";
                if-feature feature-list:HAVE_SRLG;
                description
                    "Top level container for Shared Risk Link Groups";
                container config {
                    description
                        "configuration container for Shared Risk Link Groups";
                    uses rsvp-global-srlg-config;
                } // END of config-container definition.
                container state {
                    config false;
                    description
                        "state container for Shared Risk Link Groups";
                    uses rsvp-global-srlg-config;
                } // END of state-container definition.
            } // END of srlg-container definition.
            container diff-serv {
                when " /ipi-rsvp:rsvp-te/ipi-rsvp:rsvp-instance/ipi-rsvp:config ";
                description
                    "Top level container for diff serv";
                container config {
                    description
                        "configuration container for diff serv";
                    uses rsvp-global-diff-serv-config;
                } // END of config-container definition.
                container state {
                    config false;
                    description
                        "state container for diff serv";
                    uses rsvp-global-diff-serv-config;
                } // END of state-container definition.
            } // END of diff-serv-container definition.
            container neighbors {
                when " /ipi-rsvp:rsvp-te/ipi-rsvp:rsvp-instance/ipi-rsvp:config ";
                description
                    "Top level container for rsvp neighbors";

                list neighbor {
                    key "address";
                    description
                        "Top level list for rsvp neighbor";
                    leaf address  {
                        type  leafref {
                            path  "../config/address";
                        }
                        description "Directly connected neighbor";
                    } // END of address definition.

                    container config {
                        description
                            "configuration container for rsvp neighbor";
                        uses rsvp-neighbor-config;
                    } // END of config-container definition.
                    container state {
                        config false;
                        description
                            "state conatiner for rsvp neighbor";
                        uses rsvp-neighbor-config;
                    } // END of state-container definition.
                } // End of neighbor-list

                list protocol-neighbor {
                    key "neighbor-ip-address";
                    config false;
                    description
                        "Top level list for rsvp neighbor state";
                    leaf neighbor-ip-address  {
                        type  leafref {
                            path  "../state/neighbor-ip-address";
                        }
                        description "Neighbor IP Address";
                    } // END of neighbor-ip-address definition.

                    container state {
                        config false;
                        description
                            "state conatiner for rsvp summary refresh";
                        uses rsvp-neighbor-state;
                        uses rsvp-trunk-common-state;
                        uses rsvp-trunk-id-state;
                        uses rsvp-global-graceful-restart-state;
                    } // END of state-container definition.
                } // End of protocol-neighbor-list
            } // END of neighbors-container definition.
        } // END of rsvp-instance-container definition.
        uses rsvp-paths-grouping;
        uses multipaths-grouping;
        uses trunks-grouping;
        uses interfaces-grouping;
    } // END of rsvp-te-container definition.
    } // END of rsvp-te-grouping definition.

    uses rsvp-te-grouping;

    rpc clear-rsvp-session {
        if-feature feature-list:HAVE_RSVPD;
        description "RPC to clear all RSVP session";
    }

    rpc clear-rsvp-trunk {
        if-feature feature-list:HAVE_RSVPD;
        description "RPC to clear RSVP trunk";
        input  {
            leaf trunk-name  {
                type string;
                mandatory true;
                description "Name of RSVP Trunk to be reset";
            }
        }
    }

    rpc clear-rsvp-primary-trunk {
        if-feature feature-list:HAVE_RSVPD;
        description "RPC to clear primary RSVP session for the given trunk";
        input  {
            leaf trunk-name  {
                type string;
                mandatory true;
                description "Name of RSVP Trunk to be reset";
            }
        }
    }

    rpc clear-rsvp-secondary-trunk {
        if-feature feature-list:HAVE_RSVPD;
        description "RPC to clear all secondary RSVP sessions for the given trunk";
        input  {
            leaf trunk-name  {
                type string;
                mandatory true;
                description "Name of RSVP Trunk to be reset";
            }
        }
    }

    rpc clear-rsvp-ingress-trunk {
        if-feature feature-list:HAVE_RSVPD;
        description "RPC to clear RSVP ingress trunk";
        input  {
            leaf trunk-name  {
                type string;
                mandatory true;
                description "Name of RSVP Trunk to be reset";
            }
        }
    }

    rpc clear-rsvp-non-ingress-trunk {
        if-feature feature-list:HAVE_RSVPD;
        description "RPC to clear specific/all non-Ingress RSVP Trunks, to clear all RSVP
                    trunk pass *. E.g clear-rsvp-non-ingress-trunk * and to clear specific
                    trunk pass TRUNKNAME. E.g clear-rsvp-non-ingress-trunk t1";
        input  {
            leaf trunk-name  {
                type string;
                mandatory true;
                description "Name of non-Ingress RSVP Trunk to be reset";
            }
        }
    }

    rpc rsvp-trunk-force-reoptimize-on {
        if-feature feature-list:HAVE_RSVPD;
        description "RPC to trigger CSPF re-optimization for a given trunk";
        input  {
            leaf trunk-name  {
                type string;
                mandatory true;
                description "Name of the RSVP trunk for which to trigger CSPF re-optimization";
            }
        }
    }

    rpc rsvp-trunk-force-switchover-secondary {
        if-feature feature-list:HAVE_RSVPD;
        description "RPC to enable secondary force switchover for the given RSVP trunk";
        input  {
            leaf trunk-name  {
                type string;
                mandatory true;
                description "Name of the RSVP trunk to force secondary switchover to on/off";
            }
            leaf action  {
                type ipi-rsvp-types:rsvp_force_secondary_t;
                mandatory true;
                description "Turn on/off secondary force switchover";
            }
        }
    }

    rpc rsvp-trunk-restart {
        if-feature feature-list:HAVE_RSVPD;
        description "RPC to restart the RSVP trunk";
        input  {
            leaf trunk-name  {
                type string;
                mandatory true;
                description "Name of RSVP Trunk to be reset";
            }
        }
    }

    rpc rsvp-session-reset {
        if-feature feature-list:HAVE_RSVPD;
        description "RPC to reset a RSVP session for the given tunnel-ID, LSP-Id, egress
                    and ingress IP address";
        input  {
            leaf tunnel-id  {
                type uint32;
                mandatory true;
                description "Tunnel id for Session";
            }
            leaf lsp-id  {
                type uint32;
                mandatory true;
                description "LSP id for Session";
            }
            leaf ingress  {
                type inet:ipv4-address;
                mandatory true;
                description "Ingress IP address of the Session";
            }
            leaf egress  {
                type inet:ipv4-address;
                mandatory true;
                description "Egress IP address of the Session";
            }
        }
    }

    rpc clear-rsvp-statistics {
        if-feature feature-list:HAVE_RSVPD;
        description "RPC to reset RSVP statistics";
    }

    rpc rsvp-snmp-restart {
        if-feature feature-list:HAVE_SNMP;
        if-feature feature-list:HAVE_RSVPD;
        description "RPC to restart SNMP";
    }

    rpc rsvp-terminal-debug-on {
        if-feature feature-list:HAVE_RSVPD;
        description "RPC to enable terminal RSVP debug";
        input  {
            leaf rsvp-debug-options  {
                type ipi-rsvp-types:rsvp_debug_t;
                mandatory true;
                description "Enable RSVP debug options";
            }
        }
    }

    rpc rsvp-terminal-debug-off {
        if-feature feature-list:HAVE_RSVPD;
        description "RPC to disable terminal RSVP debug";
        input  {
            leaf rsvp-debug-options  {
                type ipi-rsvp-types:rsvp_debug_t;
                mandatory true;
                description "Disable RSVP debug options";
            }
        }
    }

    rpc restart-rsvp-graceful {
        if-feature feature-list:HAVE_RSVP_GRST;
        if-feature feature-list:HAVE_RSVPD;
        description "RPC to restart RSVP gracefully";
    }

    notification rsvp-session-up {
        if-feature feature-list:HAVE_RSVPD;

        description "If this notification is sent when the value of RSVP 'session-state' enters the operational state..";

        leaf severity {
            type cml-data-types:cml_notif_severity_t;
            description "Notification severity level (value: MINOR)";
        }

        leaf eventClass {
            type cml-data-types:cml_notif_class_t;
            description "Notification event class (value: STATE)";
        }

        leaf session-name {
            type  string;
        description
            "Name of the session";
        }

        leaf trunk-id {
            type  uint32;
        description
            "Trunk identifier";
        }

        leaf extended-tunnel-id {
            type  inet:ip-address;
        description
            "Extended-tunnel identifier of the trunk";
        }

        leaf egress {
            type  inet:ip-address;
        description
            "Egress endpoint address for the trunk";
        }

        leaf lsp-id {
            type  uint16;
        description
            "Label switch path id";
        }

        leaf ingress {
            type  inet:ip-address;
        description
            "Source address of the trunk";
        }

        leaf trunk-session-type {
            type ipi-rsvp-types:rsvp_sess_type_t;
        description
            "Type of the session is either primary or secondary";
        }
    }

    notification rsvp-session-down {
        if-feature feature-list:HAVE_RSVPD;

        description "If this notification is sent when the value of RSVP 'session-state' leaves the operational state..";

        leaf severity {
            type cml-data-types:cml_notif_severity_t;
            description "Notification severity level (value: CRITICAL)";
        }

        leaf eventClass {
            type cml-data-types:cml_notif_class_t;
            description "Notification event class (value: STATE)";
        }

        leaf session-name {
            type  string;
        description
            "Name of the session";
        }

        leaf trunk-id {
            type  uint32;
        description
            "Trunk identifier";
        }

        leaf extended-tunnel-id {
            type  inet:ip-address;
        description
            "Extended-tunnel identifier of the trunk";
        }

        leaf egress {
            type  inet:ip-address;
        description
            "Egress endpoint address for the trunk";
        }

        leaf lsp-id {
            type  uint16;
        description
            "Label switch path id";
        }

        leaf ingress {
            type  inet:ip-address;
        description
            "Source address of the trunk";
        }

        leaf trunk-session-type {
            type ipi-rsvp-types:rsvp_sess_type_t;
        description
            "Type of the session is either primary or secondary";
        }
    }

    notification rsvp-session-force-switchover {
        if-feature feature-list:HAVE_RSVPD;

        description "Trigger the notification when force swicthover occured.";

        leaf severity {
            type cml-data-types:cml_notif_severity_t;
            description "Notification severity level (value: MINOR)";
        }

        leaf eventClass {
            type cml-data-types:cml_notif_class_t;
            description "Notification event class (value: STATE)";
        }

        leaf session-name {
            type  string;
        description
            "Name of the session";
        }

        leaf trunk-id {
            type  uint32;
        description
            "Trunk identifier";
        }

        leaf extended-tunnel-id {
            type  inet:ip-address;
        description
            "Extended-tunnel identifier of the trunk";
        }

        leaf egress {
            type  inet:ip-address;
        description
            "Egress endpoint address for the trunk";
        }

        leaf lsp-id {
            type  uint16;
        description
            "Label switch path id";
        }

        leaf ingress {
            type  inet:ip-address;
        description
            "Source address of the trunk";
        }

        leaf trunk-session-type {
            type ipi-rsvp-types:rsvp_sess_type_t;
        description
            "Type of the session is either primary or secondary";
        }
    }

    notification rsvp-tunnel-reoptimized {
        if-feature feature-list:HAVE_RSVPD;

        description "Trigger the notification when reoptimization occurs.";

        leaf severity {
            type cml-data-types:cml_notif_severity_t;
            description "Notification severity level (value: MINOR)";
        }

        leaf eventClass {
            type cml-data-types:cml_notif_class_t;
            description "Notification event class (value: STATE)";
        }

        leaf session-name {
            type  string;
        description
            "Name of the session";
        }

        leaf trunk-id {
            type  uint32;
        description
            "Trunk identifier";
        }

        leaf extended-tunnel-id {
            type  inet:ip-address;
        description
            "Extended-tunnel identifier of the trunk";
        }

        leaf egress {
            type  inet:ip-address;
        description
            "Egress endpoint address for the trunk";
        }

        leaf lsp-id {
            type  uint16;
        description
            "Label switch path id";
        }

        leaf ingress {
            type  inet:ip-address;
        description
            "Source address of the trunk";
        }

        leaf trunk-session-type {
            type ipi-rsvp-types:rsvp_sess_type_t;
        description
            "Type of the session is either primary or secondary";
        }
    }

}
