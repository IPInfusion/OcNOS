/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-rsvp-trunk.yang
*
*/

submodule ipi-rsvp-trunk {

    yang-version 1.1;

    belongs-to  ipi-rsvp { prefix ipi-rsvp; }

    import feature-list {
        prefix feature-list;
        revision-date 2023-02-21;
    }

    import cml-data-types {
        prefix cml-data-types;
        revision-date 2022-09-30;
    }

    import ipi-rsvp-types {
        prefix ipi-rsvp-types;
        revision-date 2022-06-01;
    }

    import ietf-inet-types {
        prefix inet;
        revision-date 2013-07-15;
    }

    include ipi-rsvp-session { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Resource Reservation Protocol";


    revision "2022-08-10" {
        description "Fix for rsvp-path hop addresses delete";
        reference " 0.7.6.";
    }

    revision "2022-07-25" {
        description "Fix for create/replace operation for rsvp-path hop addresses";
        reference " 0.7.5.";
    }

    revision "2022-07-15" {
        description "Added configure dependency tag for ingress multipath group name";
        reference " 0.7.4.";
    }

    revision "2022-07-08" {
        description "Fix for db sync issues for RSVP trunk CLIs deletion";
        reference " 0.7.3.";
    }

    revision "2022-06-01" {
        description "Updated the yang file with feature";
        reference " 0.7.2.";
    }

    revision "2022-02-02" {
        description "Added leafref and when conditions for multipath and path dependents";
        reference " 0.7.1.";
    }

    revision "2021-12-22" {
        description "Introduced HAVE_CUSTOM2_MPLS for Dune platforms and replaced HAVE_CUSTOM2_QOS";
        reference " 0.7.0.";
    }

    revision "2021-10-01" {
        description "Added DC flag check for bypass-trunk";
        reference " 0.6.4.";
    }

    revision "2021-08-27" {
        description "Updated length constraint for rsvp path-name";
        reference " 0.6.3.";
    }

    revision "2021-06-28" {
        description "Modified the attribute name from dscp-exp-max-exp-val to dscp-exp-map-exp-val";
        reference " 0.6.2.";
    }

    revision "2021-06-26" {
        description "Updated multipath runtime attribute for trunk entry";
        reference " 0.6.1.";
    }

    revision "2021-06-25" {
        description "llsp attribute removed for HAVE_CUSTOM2_QOS from bypass trunk";
        reference " 0.6.0.";
    }

    revision "2021-03-31" {
        description "Addition of PCEP-RSVP related attributes";
        reference " 0.5.0.";
    }

    revision "2021-03-22" {
        description "Added SRLG related attribute";
        reference " 0.4.0.";
    }

    revision "2021-01-27" {
        description "Updated XPATH to API mappings. Fixed known bugs";
        reference " 0.3.0.";
    }

    revision "2020-12-15" {
        description "Change to have data-types in lower case instead of camel case";
        reference " 0.2.0.";
    }

    revision "2018-06-21" {
        description "Initial Version";
        reference " 0.1.0.";
    }

    grouping rsvp-path-config {
        description
            "configuration parameters for rsvp path";
        leaf path-name  {
            type  string {
                length "1..128";
                pattern "[^?' =,>|]+";
            }
            description "Use this attribute to create a new RSVP path or to enter the Path
                        command mode. In this mode, you can add or delete paths and also
                        specify the path to be loose or strict.";
        } // END of path-name definition.

        leaf path-type  {
            type  ipi-rsvp-types:rsvp_path_type_t;
            mandatory true;
            description "Use this attribute to configure rsvp path type is either mpls or
                        gmpls. By default path type is mpls.";
        } // END of path-type definition.

    } // END of rsvp-path-config definition.
    grouping rsvp-path-mpls-config {
        description
            "configuration parameters for rsvp path";
        leaf hop-address  {
            type  inet:ipv4-address;
            description "Use this attribute to define an explicit IPv4 or IPv6 route sub-object
                        as either loose or strict hop. A list of sub-objects specifies an
                        explicit route to the egress router for an LSP";
        } // END of hop-address definition.

        leaf hop-type  {
            type  ipi-rsvp-types:rsvp_path_status_t;
            description "Use this attribute to configure rsvp path hop type as either loose or
                        strict hop.";
        } // END of hop-type definition.

    } // END of rsvp-path-mpls-config definition.
    grouping rsvp-path-gmpls-strict-hop-config {
        description
            "configuration parameters for rsvp path";
        leaf strict-hop-address  {
            type  inet:ipv4-address;
            description "Use this attribute to define an ERO path for a numbered (IPv4)
                        interface. Only strict hops can be configured, and the strict type is
                        implicit.";
        } // END of strict-hop-address definition.

    } // END of rsvp-path-gmpls-strict-hop-config definition.
    grouping rsvp-path-gmpls-config {
        description
            "configuration parameters for rsvp path";
        leaf unnumbered-ip-addr  {
            type  inet:ipv4-address;
            description "Use this attribute to define an ERO path for an unnumbered interface.
                        Both the router ID and the link ID must be entered.";
        } // END of unnumbered-ip-addr definition.

    } // END of rsvp-path-gmpls-config definition.
    grouping rsvp-path-gmpls-link-id-config {
        description
            "configuration parameters for rsvp path";
        leaf link-id  {
            type  uint32 {
                 range "1..4294967295"  {
                    description "1..4294967295: Supported range 1 - 4294967295";
                 }
            }
            description "Use this attribute to define an link ID for the unnumbered interface";
        } // END of link-id definition.

    } // END of rsvp-path-gmpls-link-id-config definition.
    grouping rsvp-trunk-common-config {
        description
            "configuration parameters for rsvp trunk common config";
        leaf ingress  {
            type  inet:ipv4-address;
            description "Use this attribute to specify a from IPv4 address for the RSVP daemon.
                        In the RSVP trunk mode, this command indicates a sender's address in
                        the sender template object that is used in path messages.";
        } // END of ingress definition.

        leaf egress  {
            type  inet:ipv4-address;
            description "Use this attribute to specify an IPv4 egress for an LSP. When
                        configuring an LSP, you must specify the address of the egress router
                        by using this command in the trunk node. An egress definition is a
                        mandatory attribute; no RSVP session is created when an egress is not
                        defined.";
        } // END of egress definition.

        leaf ext-tunnel-id  {
            type  inet:ipv4-address;
            description "Use this attribute to configure an extended-tunnel identifier as an
                        IPv4/IPv6 address. These identifiers are used in RSVP messages. If no
                        extended-tunnel ID is specified, the LSR-ID for the router is used as
                        the extended-tunnel ID for all LSPs. The extended-tunnel ID is a
                        simple way of identifying all LSPs belonging to the same trunk.";
        } // END of ext-tunnel-id definition.

        leaf update-type  {
            type  ipi-rsvp-types:rsvp_update_type_t;
            default "make-before-break";
            description "Use this attribute to change the method of updating attributes for
                        sessions (primary/ secondary) for this trunk as either
                        make-before-break (default) or break-before-make";
        } // END of update-type definition.

    } // END of rsvp-trunk-common-config definition.
    grouping rsvp-trunk-bypass-config {
        description
            "configuration parameters for rsvp bypass trunk";
        leaf bypass-name  {
            type  string {
                length "1..32";
                pattern "[^?' =,>|]+";
            }
            description "Use this attribute to create a new RSVP Bypass Tunnel or to modify
                        existing RSVP Bypass Tunnel";
        } // END of bypass-name definition.

        leaf backup-bandwidth-type  {
            type  ipi-rsvp-types:rsvp_backup_bandwidth_type;
            default "best-effort";
            description "rsvp bypass trunk backup bandwidth type";
        } // END of backup-bandwidth-type definition.

    } // END of rsvp-trunk-bypass-config definition.
    grouping rsvp-trunk-ingress-bypass-config {
        description
            "configuration parameters for rsvp bypass trunk";
        leaf traffic-type  {
            type  ipi-rsvp-types:rsvp_traffic_type_t;
            default "controlled-load";
            description "Use this attribute to identify the traffic type for this RSVP
                        Trunk/bypss/P2MP LSP's";
        } // END of traffic-type definition.

        leaf retry-count  {
            type  uint16 {
                 range "1..65535"  {
                    description "1..65535: Supported range 1 - 65535";
                 }
            }
            description "Use this attribute to specify a retry count for an RSVP Trunk.";
        } // END of retry-count definition.

        leaf retry-interval  {
            type  uint16 {
                 range "1..600"  {
                    description "1..600: Supported range 1 - 600";
                 }
            }
            default "30";
            description "Use this attribute to specify a retry interval for an RSVP Trunk. When
                        an ingress node tries to configure an LSP and the setup fails due to
                        the receipt of a Path Error message, the system waits for the time
                        configured with this command, before retrying the LSP setup process";
        } // END of retry-interval definition.

        leaf disable-route-record  {
            type  empty;
            description "Use this attribute to enable recording of the route taken by Path and
                        Reservation Request (Resv) messages. These messages confirm the
                        establishment of reservations and also identifies errors. Routes are
                        recorded by means of the Route Record Object (RRO) in the RSVP
                        message.";
        } // END of disable-route-record definition.

        leaf enable-reuse-route-record  {
            type  empty;
            description "Use this attribute to use the updated Route Record List as an Explicit
                        Route (with all strict nodes) when a path message is sent out at the
                        next refresh.";
        } // END of enable-reuse-route-record definition.

        leaf cspf-retry-count  {
            if-feature feature-list:HAVE_CSPF;
            type  uint16 {
                 range "1..65535"  {
                    description "1..65535: Supported range 1 - 65535";
                 }
            }
            description "Use this attribute to specify the number of retries that CSPF should
                        carry out for a request received from RSVP.";
        } // END of cspf-retry-count definition.

        leaf cspf-retry-interval  {
            if-feature feature-list:HAVE_CSPF;
            type  uint16 {
                 range "1..600"  {
                    description "1..600: Supported range 1 - 600";
                 }
            }
            default "30";
            description "Use this attribute to specify the time between each retry that CSPF
                        might carry out for a request received from RSVP.";
        } // END of cspf-retry-interval definition.

    } // END of rsvp-trunk-ingress-bypass-config definition.
    grouping rsvp-trunk-cspf-exclude-path-config {
        description
            "configuration parameters for rsvp exclude path";
        leaf exclude-type  {
            type  ipi-rsvp-types:rsvp_exclude_path_type_t;
            mandatory true;
            description "Use this attribute to exclude path typeas either link or node
                        protection";
        } // END of exclude-type definition.

        leaf exclude-addr  {
            type  inet:ipv4-address;
            mandatory true;
            description "Use this attribute to exclude an address link or address node from the
                        LSP creation of the Bypass Tunnel.";
        } // END of exclude-addr definition.

    } // END of rsvp-trunk-cspf-exclude-path-config definition.
    grouping rsvp-trunk-session-psb-config {
        description
            "configuration parameters for the bypass session psb";
        leaf path-name  {
            type  string {
                length "1..1965";
                pattern "[^?' =,>|]+";
            }
            description "Use this attribute to specify an RSVP path to be used.The PATHNAME in
                        this command is the string (name) used to identify an RSVP path
                        defined for the node";
        } // END of path-name definition.

    } // END of rsvp-trunk-session-psb-config definition.
    grouping rsvp-trunk-session-priorities-config {
        description
            "priorities configuration for the bypass trunk";
        leaf hold-priority  {
            type  uint8 {
                 range "0..7"  {
                    description "0..7: Supported range 0 - 7";
                 }
            }
            default "0";
            description "Use this attribute to configure the hold priority value for the
                        selected trunk.";
        } // END of hold-priority definition.

        leaf setup-priority  {
            type  uint8 {
                 range "0..7"  {
                    description "0..7: Supported range 0 - 7";
                 }
            }
            default "7";
            description "Use this attribute to configure the setup priority value for the
                        selected trunk";
        } // END of setup-priority definition.

        leaf enable-label-record  {
            type  empty;
            description "Use this attribute to record all labels exchanged between RSVP-enabled
                        routers during the reservation setup process";
        } // END of enable-label-record definition.

        leaf hop-limit  {
            type  uint16 {
                 range "1..255"  {
                    description "1..255: Supported range 1 - 255";
                 }
            }
            default "255";
            description "Use this attribute to specify a limit of hops for an RSVP trunk.
                        Hop-limit data is sent to the CSPF server if CSPF is used.";
        } // END of hop-limit definition.

        leaf filter-type  {
            type  ipi-rsvp-types:rsvp_filter_type_t;
            default "shared-explicit";
            description "Use this attribute to set the filter to fixed or shared filter style
                        for RSVP trunk.";
        } // END of filter-type definition.

    } // END of rsvp-trunk-session-priorities-config definition.
    grouping rsvp-trunk-frr-bandwidth-config {
        description
            "configuration parameters for the bypass session psb";
        leaf fast-reroute-bandwidth  {
            type  string {
                length "1..1965";
                pattern "[^?' =,>|]+";
            }
            description "Use this attribute to reserve the primary/secondary bandwidth in bits
                        per second for the current trunk.";
        } // END of fast-reroute-bandwidth definition.

    } // END of rsvp-trunk-frr-bandwidth-config definition.
    grouping rsvp-trunk-bandwidth-config {
        description
            "configuration parameters for the bypass session psb";
        leaf bandwidth  {
            type  string {
                length "1..1965";
                pattern "[^?' =,>|]+";
            }
            description "Use this attribute to reserve the primary/secondary bandwidth in bits
                        per second for the current trunk.";
        } // END of bandwidth definition.

    } // END of rsvp-trunk-bandwidth-config definition.
    grouping rsvp-bypass-trunk-dscp-exp-max-config {
        description
            "rsvp ds-info dscp exp max config for the bypass trunk";
        leaf dscp-exp-map-exp-val  {
            type  int32 {
                 range "0..7"  {
                    description "0..7: Supported range 0 - 7";
                 }
            }
            description "Use this attribute to configure the private PHB-EXP (Per-Hop
                        Behavior-Experimental) mapping only used by this ELSP
                        (EXP-Inferred-PSC LSP). This mapping is different from the node level
                        PHB-EXP mapping.";
        } // END of dscp-exp-map-exp-val definition.

        leaf dscp-exp-map-class-name  {
            type  string {
                length "1..1965";
                pattern "[^?' =,>|]+";
            }
            mandatory true;
            description "Use this attribute to configure Diffserv class alias like be ef af11
                        for the class-to-exp-bit mapping";
        } // END of dscp-exp-map-class-name definition.

    } // END of rsvp-bypass-trunk-dscp-exp-max-config definition.
    grouping rsvp-bypass-trunk-dsinfo-llsp-config {
        description
            "rsvp ds-info llsp information for the bypass trunk";
        leaf llsp-class  {
            if-feature feature-list:NOT_HAVE_CUSTOM2_MPLS;
            type  string {
                length "1..1965";
                pattern "[^?' =,>|]+";
            }
            description "to configure a Differentiated Services Label-Only-Inferred-PSC
                        (Diff-Serv L-LSP) that uses Diff-Serv Class as its PHB Scheduling
                        Class (PSC).";
        } // END of llsp-class definition.

    } // END of rsvp-bypass-trunk-dsinfo-llsp-config definition.
    grouping rsvp-bypass-trunk-dsinfo-config {
        description
            "rsvp ds-info information for the bypass trunk";
        leaf elsp-signal  {
            type  empty;
            mandatory true;
            description "Use this attribute to configure a primary Diff-Serv (Differentiated
                        Services) explicitly signaled E-LSP (EXP-InferredPSC LSP) interface.";
        } // END of elsp-signal definition.

        leaf elsp-signal-class1  {
            type  string {
                length "1..1965";
                pattern "[^?' =,>|]+";
            }
            description "Use this attribute to configure a primary Diff-Serv (Differentiated
                        Services) explicitly signaled E-LSP (EXP-InferredPSC LSP) interface
                        class1";
        } // END of elsp-signal-class1 definition.

        leaf elsp-signal-class2  {
            type  string {
                length "1..1965";
                pattern "[^?' =,>|]+";
            }
            description "Use this attribute to configure a primary Diff-Serv (Differentiated
                        Services) explicitly signaled E-LSP (EXP-InferredPSC LSP) interface
                        class2";
        } // END of elsp-signal-class2 definition.

        leaf elsp-signal-class3  {
            type  string {
                length "1..1965";
                pattern "[^?' =,>|]+";
            }
            description "Use this attribute to configure a primary Diff-Serv (Differentiated
                        Services) explicitly signaled E-LSP (EXP-InferredPSC LSP) interface
                        class3";
        } // END of elsp-signal-class3 definition.

        leaf elsp-signal-class4  {
            type  string {
                length "1..1965";
                pattern "[^?' =,>|]+";
            }
            description "Use this attribute to configure a primary Diff-Serv (Differentiated
                        Services) explicitly signaled E-LSP (EXP-InferredPSC LSP) interface
                        class4";
        } // END of elsp-signal-class4 definition.

        leaf elsp-signal-class5  {
            type  string {
                length "1..1965";
                pattern "[^?' =,>|]+";
            }
            description "Use this attribute to configure a primary Diff-Serv (Differentiated
                        Services) explicitly signaled E-LSP (EXP-InferredPSC LSP) interface
                        class5";
        } // END of elsp-signal-class5 definition.

        leaf elsp-signal-class6  {
            type  string {
                length "1..1965";
                pattern "[^?' =,>|]+";
            }
            description "Use this attribute to configure a primary Diff-Serv (Differentiated
                        Services) explicitly signaled E-LSP (EXP-InferredPSC LSP) interface
                        class6";
        } // END of elsp-signal-class6 definition.

        leaf elsp-signal-class7  {
            type  string {
                length "1..1965";
                pattern "[^?' =,>|]+";
            }
            description "Use this attribute to configure a primary Diff-Serv (Differentiated
                        Services) explicitly signaled E-LSP (EXP-InferredPSC LSP) interface
                        class7";
        } // END of elsp-signal-class7 definition.

    } // END of rsvp-bypass-trunk-dsinfo-config definition.
    grouping rsvp-trunk-dscp-exp-max-config {
        description
            "rsvp ds-info dscp exp max config for the rsvp trunk";
        leaf dscp-exp-map-exp-val  {
            type  int32 {
                 range "0..7"  {
                    description "0..7: Supported range 0 - 7";
                 }
            }
            description "Use this attribute to configure the private PHB-EXP (Per-Hop
                        Behavior-Experimental) mapping only used by this ELSP
                        (EXP-Inferred-PSC LSP). This mapping is different from the node level
                        PHB-EXP mapping.";
        } // END of dscp-exp-map-exp-val definition.

        leaf dscp-exp-map-class-name  {
            type  string {
                length "1..1965";
                pattern "[^?' =,>|]+";
            }
            mandatory true;
            description "Use this attribute to configure the Diffserv class alias like be ef
                        af11 for the class-to-exp-bit mapping";
        } // END of dscp-exp-map-class-name definition.

    } // END of rsvp-trunk-dscp-exp-max-config definition.
    grouping rsvp-trunk-dsinfo-llsp-config {
        description
            "rsvp ds-info llsp information for the rsvp trunk";
        leaf llsp-class  {
            if-feature feature-list:NOT_HAVE_CUSTOM2_MPLS;
            type  string {
                length "1..1965";
                pattern "[^?' =,>|]+";
            }
            description "to configure a Differentiated Services Label-Only-Inferred-PSC
                        (Diff-Serv L-LSP) that uses Diff-Serv Class as its PHB Scheduling
                        Class (PSC).";
        } // END of llsp-class definition.

    } // END of rsvp-trunk-dsinfo-llsp-config definition.
    grouping rsvp-trunk-dsinfo-config {
        description
            "rsvp ds-info information for the rsvp trunk";
        leaf elsp-signal  {
            type  empty;
            mandatory true;
            description "Use this attribute to configure a primary Diff-Serv (Differentiated
                        Services) explicitly signaled E-LSP (EXP-InferredPSC LSP) interface.";
        } // END of elsp-signal definition.

        leaf elsp-signal-class1  {
            type  string {
                length "1..1965";
                pattern "[^?' =,>|]+";
            }
            description "Use this attribute to configure a primary Diff-Serv (Differentiated
                        Services) explicitly signaled E-LSP (EXP-InferredPSC LSP) interface
                        class1";
        } // END of elsp-signal-class1 definition.

        leaf elsp-signal-class2  {
            type  string {
                length "1..1965";
                pattern "[^?' =,>|]+";
            }
            description "Use this attribute to configure a primary Diff-Serv (Differentiated
                        Services) explicitly signaled E-LSP (EXP-InferredPSC LSP) interface
                        class2";
        } // END of elsp-signal-class2 definition.

        leaf elsp-signal-class3  {
            type  string {
                length "1..1965";
                pattern "[^?' =,>|]+";
            }
            description "Use this attribute to configure a primary Diff-Serv (Differentiated
                        Services) explicitly signaled E-LSP (EXP-InferredPSC LSP) interface
                        class3";
        } // END of elsp-signal-class3 definition.

        leaf elsp-signal-class4  {
            type  string {
                length "1..1965";
                pattern "[^?' =,>|]+";
            }
            description "Use this attribute to configure a primary Diff-Serv (Differentiated
                        Services) explicitly signaled E-LSP (EXP-InferredPSC LSP) interface
                        class4";
        } // END of elsp-signal-class4 definition.

        leaf elsp-signal-class5  {
            type  string {
                length "1..1965";
                pattern "[^?' =,>|]+";
            }
            description "Use this attribute to configure a primary Diff-Serv (Differentiated
                        Services) explicitly signaled E-LSP (EXP-InferredPSC LSP) interface
                        class5";
        } // END of elsp-signal-class5 definition.

        leaf elsp-signal-class6  {
            type  string {
                length "1..1965";
                pattern "[^?' =,>|]+";
            }
            description "Use this attribute to configure a primary Diff-Serv (Differentiated
                        Services) explicitly signaled E-LSP (EXP-InferredPSC LSP) interface
                        class6";
        } // END of elsp-signal-class6 definition.

        leaf elsp-signal-class7  {
            type  string {
                length "1..1965";
                pattern "[^?' =,>|]+";
            }
            description "Use this attribute to configure a primary Diff-Serv (Differentiated
                        Services) explicitly signaled E-LSP (EXP-InferredPSC LSP) interface
                        class7";
        } // END of elsp-signal-class7 definition.

    } // END of rsvp-trunk-dsinfo-config definition.
    grouping rsvp-trunk-gmpls-config {
        description
            "configuration parameters for rsvp gmpls trunk";
        leaf switching-capability  {
            type  ipi-rsvp-types:rsvp_capability_type_t;
            default "psc-1";
            description "Use this attribute to configure a switching capability for the RSVP
                        Trunk";
        } // END of switching-capability definition.

        leaf direction  {
            type  ipi-rsvp-types:rsvp_direction_type_t;
            default "unidirectional";
            description "Use this attribute to configure a direction for the RSVP Trunk";
        } // END of direction definition.

        leaf generalized-pid  {
            type  ipi-rsvp-types:rsvp_gpid_type_t;
            description "Use this attribute to configure a generalized PID for the RSVP Trunk";
        } // END of generalized-pid definition.

    } // END of rsvp-trunk-gmpls-config definition.
    grouping rsvp-trunk-pce-config {
        description
            "configuration parameters for rsvp path computation element";
        leaf path-option-dynamic  {
            if-feature feature-list:HAVE_PCEP_RSVP;
            type  cml-data-types:cml_pcep_path_dyn_t;
            description "Use the attribute to enable Tunnel to get ERO from Path Computation
                        Element";
        } // END of path-option-dynamic definition.

        leaf pce-entity-identifier  {
            if-feature feature-list:HAVE_PCEP_RSVP;
            type  uint8 {
                 range "1..255"  {
                    description "1..255: Supported range 1 - 255";
                 }
            }
            description "Use this attribute to assign PCE Entity ID for the tunnel";
        } // END of pce-entity-identifier definition.

        leaf pce-state-report  {
            if-feature feature-list:HAVE_PCEP_RSVP;
            type  empty;
            description "Use this attribute to enable or disable lsp state report to PCE";
        } // END of pce-state-report definition.

        leaf pce-lsp-delegate  {
            if-feature feature-list:HAVE_PCEP_RSVP;
            type  empty;
            description "Use this attribute to enable or disable lsp delegation to PCE";
        } // END of pce-lsp-delegate definition.

    } // END of rsvp-trunk-pce-config definition.
    grouping rsvp-multipath-config {
        description
            "configuration parameters for rsvp multipath";
        leaf multipath-name  {
            type  string {
                length "1..1965";
                pattern "[^?' =,>|]+";
            }
            description "Use this attribute to create a new RSVP multipath group or to enter
                        the multipath configure mode. In this mode, you can add or delete
                        description for the multipath group.";
        } // END of multipath-name definition.

    } // END of rsvp-multipath-config definition.
    grouping rsvp-multipath-common-config {
        description
            "configuration parameters for rsvp multipath group";
        leaf description  {
            type  cml-data-types:cml_line_t {
                length "1..1965";
            }
            description "Use this attribute to add description for multipath group";
        } // END of description definition.

        leaf destination  {
            type  inet:ipv4-address;
            description "Use this attribute to add destination prefix for multipath group";
        } // END of destination definition.

    } // END of rsvp-multipath-common-config definition.
    grouping rsvp-multipath-state {
        description
            "rsvp multipath additional information";
        leaf multipath-identifier  {
            type  uint16;
            description "Identifier of multipath group";
        } // END of multipath-identifier definition.

        leaf member-trunk-count  {
            type  uint16;
            description "Number of member trunks of multipath group";
        } // END of member-trunk-count definition.

    } // END of rsvp-multipath-state definition.
    grouping rsvp-multipath-trunk-state {
        description
            "rsvp multipath member trunk information";
        leaf trunk-name  {
            type  string {
                length "1..1965";
                pattern "[^?' =,>|]+";
            }
            description "Name of the member trunk";
        } // END of trunk-name definition.

        leaf trunk-identifier  {
            type  uint32;
            description "Identifier of the member trunk";
        } // END of trunk-identifier definition.

        leaf trunk-status  {
            type  ipi-rsvp-types:rsvp_trunk_status_t;
            description "Status of the member trunk";
        } // END of trunk-status definition.

    } // END of rsvp-multipath-trunk-state definition.
    grouping rsvp-trunk-multipath-config {
        description
            "configuration parameters for rsvp multipath config";
        leaf multipath-group  {
            when " /rsvp-te/multipaths/multipath/config/destination ";
            if-feature feature-list:HAVE_RSVP_MULTIPATH;
            type  leafref {
                path  "/ipi-rsvp:rsvp-te/multipaths/multipath/config/multipath-name";
            }
            description "Use this attribute to configure a multipath group name for the RSVP
                        Trunk";
        } // END of multipath-group definition.

    } // END of rsvp-trunk-multipath-config definition.
    grouping rsvp-trunk-color-config {
        description
            "configuration parameter for rsvp trunk color";
        leaf trunk-color  {
            if-feature feature-list:HAVE_SERVICE_MAPPING;
            type  uint32 {
                 range "1..4294967295"  {
                    description "1..4294967295: Supported range 1 - 4294967295";
                 }
            }
            description "Use this attribute to configure color for RSVP Trunk";
        } // END of trunk-color definition.

    } // END of rsvp-trunk-color-config definition.
    grouping rsvp-trunk-binding-config {
        description
            "configuration parameter for rsvp binding label";
        leaf bsid-value  {
            type  uint32 {
                 range "16..15999"  {
                    description "16..15999: Supported range 16 - 15999";
                 }
            }
            description "Use this attribute to configure static binding segment identifier
                        value";
        } // END of bsid-value definition.

    } // END of rsvp-trunk-binding-config definition.
    grouping rsvp-trunk-config {
        description
            "configuration parameters for rsvp trunk";
        leaf trunk-name  {
            type  string {
                length "1..32";
                pattern "[^?' =,>|]+";
            }
            description "Use this attribute to create a new RSVP trunk. When the trunk is
                        created, the attributes required to configure an explicitly-routed or
                        traditionally-routed LSP are set. Once a trunk is configured with the
                        required attributes, an RSVP session (and PSB) is created for this
                        trunk, which enables the exchange of messages and completes the LSP
                        setup";
        } // END of trunk-name definition.

        leaf trunk-family  {
            type  ipi-rsvp-types:rsvp_trunk_family_t;
            mandatory true;
            description "Use this attribute to configure the trunk type as IPV4 or IPV6 or
                        GMPLS";
        } // END of trunk-family definition.

        leaf enable-igp-shortcut  {
            type  empty;
            description "Use this attrinute to enable Interior Gateway Protocol (IGP) Shortcut.
                        With IGP Shortcut, link-state IGPs calculate IP routes to forward
                        traffic over tunnels configured by TE.";
        } // END of enable-igp-shortcut definition.

        leaf absolute-metric  {
            type  uint32 {
                 range "1..65535"  {
                    description "1..65535: Supported range 1 - 65535";
                 }
            }
            description "Use this attribute to set LSP absolute metric metric for IGP Shortcut
                        use";
        } // END of absolute-metric definition.

        leaf relative-metric  {
            type  int32 {
                 range "-65535..0 | 1..65535"  {
                    description "-65535..0: Supported range -65535 - 0,1..65535: Supported range 1 -
                            65535";
                 }
            }
            description "Use this attribute to set LSP relative metric metric for IGP Shortcut
                        use";
        } // END of relative-metric definition.

        leaf revert-timer  {
            type  uint32 {
                 range "1..65535"  {
                    description "1..65535: Supported range 1 - 65535";
                 }
            }
            default "60";
            description "Use this attribute configure the Hold-on timer before revert back to
                        RSVP session";
        } // END of revert-timer definition.

        leaf enable-reoptimize  {
            type  empty;
            description "Use this attribute to enable the reoptimization for the RSVP Trunk";
        } // END of enable-reoptimize definition.

    } // END of rsvp-trunk-config definition.
    grouping rsvp-trunk-ip-map-route {
        description
            "configuration parametersfor rsvp trunk ipv4 map route";
        leaf address  {
            type  inet:ipv4-prefix;
            description "rsvp trunk ipv4 map route address";
        } // END of address definition.

    } // END of rsvp-trunk-ip-map-route definition.
    grouping rsvp-trunk-map-route {
        description
            "configuration parameters for rsvp trunk map route";
        leaf dst-addr  {
            type  inet:ipv4-prefix;
            mandatory true;
            description "Use this attribute to map a route using an IPv4 to an RSVP trunk. If
                        the primary LSP for a trunk goes down, all mapped routes are sent
                        automatically to a secondary LSP configured as backup for a primary
                        LSP.";
        } // END of dst-addr definition.

        leaf name  {
            if-feature feature-list:HAVE_DIFFSERV;
            type  string {
                length "1..1965";
                pattern "[^?' =,>|]+";
            }
            mandatory true;
            description "Use this attribute to map a route using an IPv4 to Incoming DiffServ
                        Class (for example, be, ef, etc.) to map to the RSVP trunk.";
        } // END of name definition.

    } // END of rsvp-trunk-map-route definition.
    grouping rsvp-trunk-sec-priority-config {
        description
            "secondary priority configurationfor rsvp trunk";
        leaf secondary-priority  {
            type  int32 {
                 range "1..5"  {
                    description "1..5: Supported range 1 - 5";
                 }
            }
            description "Use this attribute to configure the secondary priorities of the RSVP
                        Trunk.";
        } // END of secondary-priority definition.

        leaf priority-path  {
            type  string {
                length "1..1965";
                pattern "[^?' =,>|]+";
            }
            description "Use this attribute to configure the secondary priority path for the
                        RSVP Trunk.";
        } // END of priority-path definition.

        leaf secondary-priority-srlg-disjoint  {
            if-feature feature-list:HAVE_SRLG;
            type  ipi-rsvp-types:rsvp_te_srlg_disjoint_type_t;
            description "Use this attribute to configure the SRLG disjoint path for the RSVP
                        Trunk.";
        } // END of secondary-priority-srlg-disjoint definition.

        leaf hold-priority  {
            type  uint8 {
                 range "0..7"  {
                    description "0..7: Supported range 0 - 7";
                 }
            }
            default "0";
            description "Use this attribute to configure the secondary hold priority for the
                        RSVP Trunk.";
        } // END of hold-priority definition.

        leaf setup-priority  {
            type  uint8 {
                 range "0..7"  {
                    description "0..7: Supported range 0 - 7";
                 }
            }
            default "7";
            description "Use this attribute to configure the secondary setup priority for the
                        RSVP Trunk.";
        } // END of setup-priority definition.

        leaf enable-label-record  {
            type  empty;
            description "Use this attribute to configure the secondary label record for the
                        RSVP Trunk.";
        } // END of enable-label-record definition.

        leaf hop-limit  {
            type  uint16 {
                 range "1..255"  {
                    description "1..255: Supported range 1 - 255";
                 }
            }
            default "255";
            description "Use this attribute to configure the secondary hop limit for the RSVP
                        Trunk.";
        } // END of hop-limit definition.

    } // END of rsvp-trunk-sec-priority-config definition.
    grouping rsvp-trunk-gmpls-label-set {
        description
            "configuration parameters for rsvp gmpls label set";
        leaf action-type  {
            type  boolean;
            mandatory true;
            description "Use this attribute to configure the gmpls label set for the RSVP
                        Trunk.";
        } // END of action-type definition.

        leaf start-label-range  {
            type  int32 {
                 range "16..1048575"  {
                    description "16..1048575: Supported range 16 - 1048575";
                 }
            }
            mandatory true;
            description "Use this attribute to configure the gmpls label set start label";
        } // END of start-label-range definition.

        leaf end-label-range  {
            type  int32 {
                 range "16..1048575"  {
                    description "16..1048575: Supported range 16 - 1048575";
                 }
            }
            mandatory true;
            description "Use this attribute to configure the gmpls label set end label";
        } // END of end-label-range definition.

    } // END of rsvp-trunk-gmpls-label-set definition.
    grouping rsvp-trunk-frr-config {
        description
            "configuration parameters for the frr session";
        leaf protection  {
            if-feature feature-list:HAVE_MPLS_FRR;
            type  ipi-rsvp-types:rsvp_frr_protection_t;
            description "Use this attribute to create an Fast Reroute backup and to set an LSP
                        one-to-one protection mechanism. This command can also be used to
                        create an FRR Facility (Bypass) backup and assign a Facility Backup
                        (Bypass Tunnel) available to the protected LSP.";
        } // END of protection definition.

        leaf enable-node-protection  {
            if-feature feature-list:HAVE_MPLS_FRR;
            type  empty;
            description "Use this attribute to configure fast-reroute node-protection";
        } // END of enable-node-protection definition.

        leaf frr-hold-priority  {
            type  uint32 {
                 range "0..7"  {
                    description "0..7: Supported range 0 - 7";
                 }
            }
            default "0";
            description "Use this attribute to configure the hold priority value for the
                        selected trunk.";
        } // END of frr-hold-priority definition.

        leaf frr-setup-priority  {
            type  uint32 {
                 range "0..7"  {
                    description "0..7: Supported range 0 - 7";
                 }
            }
            default "7";
            description "Use this attribute to configure the setup priority value for the
                        selected trunk";
        } // END of frr-setup-priority definition.

        leaf frr-hop-limit  {
            type  uint32 {
                 range "1..255"  {
                    description "1..255: Supported range 1 - 255";
                 }
            }
            default "255";
            description "Use this attribute to specify a limit of hops for an RSVP trunk.
                        Hop-limit data is sent to the CSPF server if CSPF is used.";
        } // END of frr-hop-limit definition.

    } // END of rsvp-trunk-frr-config definition.
    grouping rsvp-trunk-session-config {
        description
            "configuration parameters for rsvp trunk";
        leaf trunk-session-type  {
            type  ipi-rsvp-types:rsvp_sess_type_t;
            description "Use this attribute to configure the session is primary or secondary";
        } // END of trunk-session-type definition.

        leaf disable-cspf  {
            if-feature feature-list:HAVE_CSPF;
            type  empty;
            description "Use this attribute to enable the use of Constrained Shortest Path
                        First (CSPF) server for an explicit route to the egress, or all RSVP
                        sessions. When CSPF is turned off globally, it cannot be enabled for
                        any LSP.";
        } // END of disable-cspf definition.

        leaf disable-affinity  {
            if-feature feature-list:HAVE_TE;
            type  empty;
            description "Use this attribute to enable sending of session attribute objects with
                        resource affinity data.";
        } // END of disable-affinity definition.

        leaf enable-elsp-pre-config  {
            if-feature feature-list:HAVE_SWFWDR;
            if-feature feature-list:HAVE_DIFFSERV;
            type  empty;
            description "Use this attribute to configure a Differentiated Services (Diff-Serv)
                        pre-configured E-LSP (EXP-Inferred-PSC LSP)";
        } // END of enable-elsp-pre-config definition.

        leaf enable-local-protection  {
            type  empty;
            description "Use this attribute to enable the local repair of explicit routes for
                        which this router is a transit node.";
        } // END of enable-local-protection definition.

    } // END of rsvp-trunk-session-config definition.
    grouping rsvp-trunk-srlg-config {
        description
            "configuration parameters for Shared Risk Link Groups";
        leaf srlg-disjoint-secondary  {
            if-feature feature-list:HAVE_SRLG;
            type  ipi-rsvp-types:rsvp_te_srlg_disjoint_type_t;
            description "Use this attribute to enable secondary srlg disjoint";
        } // END of srlg-disjoint-secondary definition.

    } // END of rsvp-trunk-srlg-config definition.
    grouping rsvp-admin-group-frr-config {
        description
            "configuration parameters for rsvp admin group";
        leaf admin-group-name  {
            type  string {
                length "1..1965";
                pattern "[^?' =,>|]+";
            }
            description "Use this attribute to configure administrative groups for use with a
                        bypass LSP configuration. Administrative groups are assigned
                        attributes that describe the color of links, so that links with the
                        same color are in one class. Administrative groups are used to
                        implement different policy-based LSP setups";
        } // END of admin-group-name definition.

        leaf admin-group-type  {
            type  ipi-rsvp-types:rsvp_frr_admin_type_t;
            description "Use this attribute to configure administrative groups for use with a
                        bypass LSP configuration as either exclude-any or include-any.
                        Administrative groups are assigned attributes that describe the color
                        of links, so that links with the same color are in one class.
                        Administrative groups are used to implement different policy-based LSP
                        setups";
        } // END of admin-group-type definition.

    } // END of rsvp-admin-group-frr-config definition.
    grouping rsvp-admin-group-config {
        description
            "configuration parameters for rsvp admin group";
        leaf name  {
            type  string {
                length "1..1965";
                pattern "[^?' =,>|]+";
            }
            description "iUse this attribute to configure primary administrative groups.
                        Administrative groups are manually assigned attributes that describe
                        the color of links, so that links with the same color are in one
                        class. These groups are used to implement different policy-based LSP
                        setups. Administrative group attributes can be included or excluded
                        for an LSP or for a path's primary and secondary paths";
        } // END of name definition.

        leaf type  {
            type  ipi-rsvp-types:rsvp_admin_type_t;
            description "Use this attribute to configure the type is include-any or include-all
                        or exclude-any";
        } // END of type definition.

    } // END of rsvp-admin-group-config definition.
    grouping rsvp-trunk-psb-config {
        description
            "configuration parameters for rsvp psb session";
        leaf path-name  {
            type  leafref {
                path  "/ipi-rsvp:rsvp-te/rsvp-paths/rsvp-path/config/path-name";
            }
            description "Use this attribute to configure the path";
        } // END of path-name definition.

        leaf class-type-name  {
            if-feature feature-list:HAVE_DSTE;
            type  string {
                length "1..1965";
                pattern "[^?' =,>|]+";
            }
            description "Use this attribute to configure a Class-Type for an LSP session.";
        } // END of class-type-name definition.

    } // END of rsvp-trunk-psb-config definition.
    grouping rsvp-trunk-session-gmpls-attr {
        description
            "configuration parameters for rsvp gmpls session attributes";
        leaf link-protection  {
            type  ipi-rsvp-types:rsvp_protection_type_t;
            default "unprotected";
            description "Use this attribute to configure the gmpls link-protection for the RSVP
                        Trunk";
        } // END of link-protection definition.

    } // END of rsvp-trunk-session-gmpls-attr definition.
    grouping rsvp-explicit-label-fwd-config {
        description
            "configuration parameters for rsvp forward explicit label";
        leaf forward-label-value  {
            type  uint32 {
                 range "16..1048575"  {
                    description "16..1048575: Supported range 16 - 1048575";
                 }
            }
            mandatory true;
            description "Use this attribute to configure the explicit label supported for an
                        LSP.";
        } // END of forward-label-value definition.

        leaf forward-direction  {
            type  ipi-rsvp-types:rsvp_explicit_fwd_dir_t;
            mandatory true;
            description "Use this attribute to configure the explicit label in forward
                        direction";
        } // END of forward-direction definition.

    } // END of rsvp-explicit-label-fwd-config definition.
    grouping rsvp-explicit-label-rev-config {
        description
            "configuration parameters for rsvp reverse explicit label";
        leaf reverse-label-value  {
            type  uint32 {
                 range "16..1048575"  {
                    description "16..1048575: Supported range 16 - 1048575";
                 }
            }
            mandatory true;
            description "Use this attribute to configure the explicit label supported for an
                        LSP.";
        } // END of reverse-label-value definition.

        leaf reverse-direction  {
            type  ipi-rsvp-types:rsvp_explicit_rev_dir_t;
            mandatory true;
            description "Use this attribute to configure the explicit label in reverse
                        direction";
        } // END of reverse-direction definition.

    } // END of rsvp-explicit-label-rev-config definition.

    grouping  rsvp-paths-grouping {
    description
        "container for the rsvp path";
    container rsvp-paths {
        when " /rsvp-te/rsvp-instance/config ";
        if-feature feature-list:HAVE_RSVPD;
        if-feature feature-list:NOT_HAVE_MPLS_TUNNEL;
        description
            "container for the rsvp path";

        list rsvp-path {
        when " /rsvp-te/rsvp-paths/rsvp-path/config/path-type ";
            key "path-name";
            description
                "list of rsvp path";
            leaf path-name  {
                type  leafref {
                    path  "../config/path-name";
                }
                description "Use this attribute to configure the path";
            } // END of path-name definition.

            container config {
                description
                    "configuration container for rsvp path";
                uses rsvp-path-config;
            } // END of config-container definition.
            container state {
                config false;
                description
                    "state parameters related to rsvp paths";
                uses rsvp-path-config;
                uses rsvp-path-state;
            } // END of state-container definition.
            container explicit-route-object {
                description
                    "configuration container for rsvp path ero";

                list mpls-hop {
                    key "hop-address hop-type";

                    ordered-by user;
                    description
                        "list of rsvp mpls path hop";
                    leaf hop-address  {
                        type  leafref {
                            path  "../config/hop-address";
                        }
                        description "Use this attribute to define an explicit IPv4 or IPv6 route sub-object
                                    as either loose or strict hop. A list of sub-objects specifies an
                                    explicit route to the egress router for an LSP";
                    } // END of hop-address definition.

                    leaf hop-type  {
                        type  leafref {
                            path  "../config/hop-type";
                        }
                        description "Use this attribute to configure rsvp path hop type as either loose or
                                    strict hop.";
                    } // END of hop-type definition.

                    container config {
                        description
                            "configuration container for rsvp mpls path hop";
                        uses rsvp-path-mpls-config;
                    } // END of config-container definition.
                    container state {
                        config false;
                        description
                            "state parameters related to rsvp path";
                        uses rsvp-path-mpls-config;
                    } // END of state-container definition.
                } // End of mpls-hop-list

                list gmpls-strict-hop {
                    key "strict-hop-address";
                    description
                        "configuration container for rsvp path gmpls strict hop";
                    leaf strict-hop-address  {
                        type  leafref {
                            path  "../config/strict-hop-address";
                        }
                        description "Use this attribute to define an ERO path for a numbered (IPv4)
                                    interface. Only strict hops can be configured, and the strict type is
                                    implicit.";
                    } // END of strict-hop-address definition.

                    container config {
                        description
                            "configuration container for rsvp path gmpls strict hop";
                        uses rsvp-path-gmpls-strict-hop-config;
                    } // END of config-container definition.
                    container state {
                        config false;
                        description
                            "state parameters related to rsvp path gmpls strict hop";
                        uses rsvp-path-gmpls-strict-hop-config;
                    } // END of state-container definition.
                } // End of gmpls-strict-hop-list
                container gmpls-unnumbered-entry {
                    description
                        "Top level container for rsvp path unnumbered ip address";

                    list gmpls-unnumbered-hop {
                        key "unnumbered-ip-addr link-id";
                        description
                            "objectlist for rsvp path unnumbered path";
                        leaf unnumbered-ip-addr  {
                            type  leafref {
                                path  "../config/unnumbered-ip-addr";
                            }
                            description "Use this attribute to define an ERO path for an unnumbered interface.
                                        Both the router ID and the link ID must be entered.";
                        } // END of unnumbered-ip-addr definition.

                        leaf link-id  {
                            type  leafref {
                                path  "../config/link-id";
                            }
                            description "Use this attribute to define an link ID for the unnumbered interface";
                        } // END of link-id definition.

                        container config {
                            description
                                "configuration container for rsvp unnumbered path with link id";
                            uses rsvp-path-gmpls-config;
                            uses rsvp-path-gmpls-link-id-config;
                        } // END of config-container definition.
                        container state {
                            config false;
                            description
                                "state parameters related to rsvp path unnumbered path with link id";
                            uses rsvp-path-gmpls-config;
                            uses rsvp-path-gmpls-link-id-config;
                        } // END of state-container definition.
                    } // End of gmpls-unnumbered-hop-list
                } // END of gmpls-unnumbered-entry-container definition.
            } // END of explicit-route-object-container definition.
        } // End of rsvp-path-list
    } // END of rsvp-paths-container definition.
    } // END of rsvp-paths-grouping definition.

    grouping  multipaths-grouping {
    description
        "container for the rsvp multipath group";
    container multipaths {
        when " /rsvp-te/rsvp-instance/config ";
        if-feature feature-list:HAVE_RSVP_MULTIPATH;
        if-feature feature-list:HAVE_RSVPD;
        description
            "container for the rsvp multipath group";

        list multipath {
            key "multipath-name";
            description
                "list of rsvp multipath groups";
            leaf multipath-name  {
                type  leafref {
                    path  "../config/multipath-name";
                }
                description "";
            } // END of multipath-name definition.

            container config {
                description
                    "configuration container for rsvp multipath group";
                uses rsvp-multipath-common-config;
                uses rsvp-multipath-config;
            } // END of config-container definition.
            container state {
                config false;
                description
                    "state container for rsvp multipath group";
                uses rsvp-multipath-common-config;
                uses rsvp-multipath-config;
                uses rsvp-multipath-state;
            } // END of state-container definition.
            container member-trunks {
                config false;
                description
                    "State level container for multipath member trunks";

                list member-trunk {
                    key "trunk-name";
                    config false;
                    description
                        "State level list for multipath member trunks";
                    leaf trunk-name  {
                        type  leafref {
                            path  "../state/trunk-name";
                        }
                        description "Name of the member trunk";
                    } // END of trunk-name definition.

                    container state {
                        config false;
                        description
                            "state container for member trunks";
                        uses rsvp-multipath-trunk-state;
                    } // END of state-container definition.
                } // End of member-trunk-list
            } // END of member-trunks-container definition.
        } // End of multipath-list
    } // END of multipaths-container definition.
    } // END of multipaths-grouping definition.

    grouping  trunks-grouping {
    description
        "trunk infomrmation";
    container trunks {
        when " /rsvp-te/rsvp-instance/config ";
        if-feature feature-list:HAVE_RSVPD;
        description
            "trunk infomrmation";

        list bypass-trunk {
            if-feature feature-list:HAVE_MPLS_FRR;
            if-feature feature-list:NOT_HAVE_CUSTOM1_MPLS;
            key "bypass-name";
            description
                "list of bypass trunk";
            leaf bypass-name  {
                type  leafref {
                    path  "../config/bypass-name";
                }
                description "rsvp trunk bypass name";
            } // END of bypass-name definition.

            container config {
                description
                    "configuration container for rsvp bypass trunk";
                uses rsvp-trunk-bypass-config;
                uses rsvp-trunk-common-config;
            } // END of config-container definition.
            container state {
                config false;
                description
                    "state parameters related to rsvp bypass trunk";
                uses rsvp-trunk-bypass-config;
                uses rsvp-trunk-common-config;
            } // END of state-container definition.
            container session {
                description
                    "rsvp bypass trunk session";
                container config {
                    description
                        "configuration container for rsvp session";
                    uses rsvp-trunk-ingress-bypass-config;
                } // END of config-container definition.
                container state {
                    config false;
                    description
                        "state container for rsvp session";
                    uses rsvp-trunk-ingress-bypass-config;
                } // END of state-container definition.
                container exclude-path {
                    if-feature feature-list:HAVE_MPLS_FRR;
                    description
                        "configuration container for rsvp bypass trunk exclude path address";
                    container config {
                        presence "Enable exclude-address";
                        description
                            "configuration container for rsvp exclude path address";
                        uses rsvp-trunk-cspf-exclude-path-config;
                    } // END of config-container definition.
                    container state {
                        config false;
                        description
                            "state container for rsvp exclude path address";
                        uses rsvp-trunk-cspf-exclude-path-config;
                    } // END of state-container definition.
                } // END of exclude-path-container definition.
                container path-state-block {
                    description
                        "configuration container for rsvp bypass trunk psb session";
                    container config {
                        description
                            "configuration container for rsvp session psb";
                        uses rsvp-trunk-bandwidth-config;
                        uses rsvp-trunk-session-psb-config;
                    } // END of config-container definition.
                    container state {
                        config false;
                        description
                            "state container for rsvp session psb";
                        uses rsvp-trunk-bandwidth-config;
                        uses rsvp-trunk-session-psb-config;
                    } // END of state-container definition.
                    container session-attributes {
                        description
                            "configuration container for rsvp bypass trunk psb session attributes";
                        container config {
                            description
                                "configuration container for rsvp session attr";
                            uses rsvp-trunk-bandwidth-config;
                            uses rsvp-trunk-session-priorities-config;
                        } // END of config-container definition.
                        container state {
                            config false;
                            description
                                "state container for rsvp session attr";
                            uses rsvp-trunk-bandwidth-config;
                            uses rsvp-trunk-session-priorities-config;
                        } // END of state-container definition.
                    } // END of session-attributes-container definition.
                } // END of path-state-block-container definition.
                container diff-serv-info {
                    if-feature feature-list:HAVE_MPLS_FRR;
                    if-feature feature-list:HAVE_DIFFSERV;
                    description
                        "configuration container for rsvp bypass trunk diff serve information";

                    list dscp-exp-map {
                    when " /rsvp-te/trunks/bypass-trunk/session/diff-serv-info/dscp-exp-map/config/dscp-exp-map-class-name ";
                        if-feature feature-list:NOT_HAVE_CUSTOM1_MPLS;
                        key "dscp-exp-map-exp-val";
                        description
                            "Top Level list for dscp exp";
                        leaf dscp-exp-map-exp-val  {
                            type  leafref {
                                path  "../config/dscp-exp-map-exp-val";
                            }
                            description "rsvp trunk dsinfo exp val";
                        } // END of dscp-exp-map-exp-val definition.

                        container config {
                            description
                                "configuration container for rsvp bypass trunk dscp exp map";
                            uses rsvp-bypass-trunk-dscp-exp-max-config;
                        } // END of config-container definition.
                        container state {
                            config false;
                            description
                                "State container for rsvp bypass trunk dscp exp map";
                            uses rsvp-bypass-trunk-dscp-exp-max-config;
                        } // END of state-container definition.
                    } // End of dscp-exp-map-list
                    container config {
                        description
                            "configuration container for rsvp bypass trunk llsp class";
                        uses rsvp-bypass-trunk-dsinfo-llsp-config;
                    } // END of config-container definition.
                    container state {
                        config false;
                        description
                            "state container for rsvp bypass trunk llsp class";
                        uses rsvp-bypass-trunk-dsinfo-llsp-config;
                    } // END of state-container definition.
                    container elsp-class {
                        if-feature feature-list:HAVE_DIFFSERV;
                        if-feature feature-list:HAVE_SWFWDR;
                        description
                            "configuration container for rsvp bypass trunk elsp class";
                        container config {
                            description
                                "configuration container for rsvp llsp class";
                            uses rsvp-bypass-trunk-dsinfo-config;
                        } // END of config-container definition.
                        container state {
                            config false;
                            description
                                "state container for rsvp llsp class";
                            uses rsvp-bypass-trunk-dsinfo-config;
                        } // END of state-container definition.
                    } // END of elsp-class-container definition.
                } // END of diff-serv-info-container definition.
            } // END of session-container definition.
        } // End of bypass-trunk-list

        list ingress-trunk {
            key "trunk-name";
            description
                "list of the ingress trunk";
            leaf trunk-name  {
                type  leafref {
                    path  "../config/trunk-name";
                }
                description "rsvp trunk name";
            } // END of trunk-name definition.


            list mapped-ip-route {
                key "address";
                description
                    "list of ingress trunk ipv4 mapped route";
                leaf address  {
                    type  leafref {
                        path  "../config/address";
                    }
                    description "rsvp trunk ipv4 map route address";
                } // END of address definition.

                container config {
                    description
                        "configuration container for rsvp ingress trunk";
                    uses rsvp-trunk-ip-map-route;
                } // END of config-container definition.
                container state {
                    config false;
                    description
                        "state container for rsvp ingress trunk";
                    uses rsvp-trunk-ip-map-route;
                } // END of state-container definition.
            } // End of mapped-ip-route-list

            list mapped-prefix-class-route {
                key "dst-addr";
                description
                    "list of ingress trunk mapped route";
                leaf dst-addr  {
                    type  leafref {
                        path  "../config/dst-addr";
                    }
                    description "rsvp trunk map route address";
                } // END of dst-addr definition.

                container config {
                    description
                        "configuration container for rsvp mapped route";
                    uses rsvp-trunk-map-route;
                } // END of config-container definition.
                container state {
                    config false;
                    description
                        "state container for rsvp mapped route";
                    uses rsvp-trunk-map-route;
                } // END of state-container definition.
            } // End of mapped-prefix-class-route-list

            list secondary-priorities {
                key "secondary-priority";
                description
                    "list of ingress trunk secondary properties";
                leaf secondary-priority  {
                    type  leafref {
                        path  "../config/secondary-priority";
                    }
                    description "Use this attribute to configure the secondary priorities of the RSVP
                                Trunk.";
                } // END of secondary-priority definition.

                container config {
                    description
                        "configuration container for rsvp secondary priority LSP";
                    uses rsvp-trunk-bandwidth-config;
                    uses rsvp-trunk-sec-priority-config;
                } // END of config-container definition.
                container state {
                    config false;
                    description
                        "state container for rsvp mpls path hop";
                    uses rsvp-trunk-bandwidth-config;
                    uses rsvp-trunk-sec-priority-config;
                } // END of state-container definition.
            } // End of secondary-priorities-list
            container config {
                description
                    "configuration container for rsvp ingress trunk";
                uses rsvp-trunk-binding-config;
                uses rsvp-trunk-color-config;
                uses rsvp-trunk-common-config;
                uses rsvp-trunk-config;
                uses rsvp-trunk-multipath-config;
            } // END of config-container definition.
            container state {
                config false;
                description
                    "state container for rsvp ingress trunk";
                uses rsvp-trunk-binding-config;
                uses rsvp-trunk-color-config;
                uses rsvp-trunk-common-config;
                uses rsvp-trunk-config;
                uses rsvp-trunk-multipath-config;
            } // END of state-container definition.
            container path-computation-element {
                if-feature feature-list:HAVE_PCEP_RSVP;
                description
                    "Top level configuration container for path computation element";
                container config {
                    description
                        "configuration container for rsvp path computation element";
                    uses rsvp-trunk-pce-config;
                } // END of config-container definition.
                container state {
                    config false;
                    description
                        "state container for rsvp path computation element";
                    uses rsvp-trunk-pce-config;
                } // END of state-container definition.
            } // END of path-computation-element-container definition.
            container sessions {
                description
                    "configuration container for rsvp ingress trunk sessions container";

                list session {
                    key "trunk-session-type";
                    description
                        "list of ingress trunk session details";
                    leaf trunk-session-type  {
                        type  leafref {
                            path  "../config/trunk-session-type";
                        }
                        description "rsvp trunk session type";
                    } // END of trunk-session-type definition.


                    list admin-group {
                        if-feature feature-list:HAVE_TE;
                        key "name";
                        description
                            "list of ingress trunk admin group";
                        leaf name  {
                            type  leafref {
                                path  "../config/name";
                            }
                            description "rsvp admin group name";
                        } // END of name definition.

                        container config {
                            description
                                "configuration container for rsvp admin group";
                            uses rsvp-admin-group-config;
                        } // END of config-container definition.
                        container state {
                            config false;
                            description
                                "state container for rsvp admin group";
                            uses rsvp-admin-group-config;
                        } // END of state-container definition.
                    } // End of admin-group-list
                    container config {
                        description
                            "configuration container for rsvp session";
                        uses rsvp-trunk-ingress-bypass-config;
                        uses rsvp-trunk-session-config;
                    } // END of config-container definition.
                    container state {
                        config false;
                        description
                            "state container for rsvp session";
                        uses rsvp-trunk-ingress-bypass-config;
                        uses rsvp-trunk-session-config;
                    } // END of state-container definition.
                    container path-state-block {
                        description
                            "configuration container for rsvp ingress trunk psb session";
                        container config {
                            description
                                "configuration container for rsvp session psb";
                            uses rsvp-trunk-bandwidth-config;
                            uses rsvp-trunk-psb-config;
                        } // END of config-container definition.
                        container state {
                            config false;
                            description
                                "state container for rsvp session psb";
                            uses rsvp-trunk-bandwidth-config;
                            uses rsvp-trunk-psb-config;
                        } // END of state-container definition.
                        container session-attributes {
                            description
                                "configuration container for rsvp ingress trunk psb session attributes";
                            container config {
                                description
                                    "configuration container for rsvp session attrs";
                                uses rsvp-trunk-bandwidth-config;
                                uses rsvp-trunk-session-priorities-config;
                            } // END of config-container definition.
                            container state {
                                config false;
                                description
                                    "state container for rsvp session attrs";
                                uses rsvp-trunk-bandwidth-config;
                                uses rsvp-trunk-session-priorities-config;
                            } // END of state-container definition.
                        } // END of session-attributes-container definition.
                    } // END of path-state-block-container definition.
                    container diff-serv-info {
                        if-feature feature-list:HAVE_DIFFSERV;
                        description
                            "configuration container for rsvp ingress trunk diff serve information";

                        list dscp-exp-map {
                        when " /rsvp-te/trunks/ingress-trunk/sessions/session/diff-serv-info/dscp-exp-map/config/dscp-exp-map-class-name ";
                            key "dscp-exp-map-exp-val";
                            description
                                "Top Level list for dscp exp";
                            leaf dscp-exp-map-exp-val  {
                                type  leafref {
                                    path  "../config/dscp-exp-map-exp-val";
                                }
                                description "rsvp trunk dsinfo exp val";
                            } // END of dscp-exp-map-exp-val definition.

                            container config {
                                description
                                    "configuration container for rsvp ingress trunk dscp exp map";
                                uses rsvp-trunk-dscp-exp-max-config;
                            } // END of config-container definition.
                            container state {
                                config false;
                                description
                                    "State container for rsvp ingress trunk dscp exp map";
                                uses rsvp-trunk-dscp-exp-max-config;
                            } // END of state-container definition.
                        } // End of dscp-exp-map-list
                        container config {
                            description
                                "configuration container for rsvp dscp exp mpls";
                            uses rsvp-trunk-dsinfo-llsp-config;
                        } // END of config-container definition.
                        container state {
                            config false;
                            description
                                "state container for rsvp dscp exp mpls";
                            uses rsvp-trunk-dsinfo-llsp-config;
                        } // END of state-container definition.
                        container elsp-class {
                            description
                                "configuration container for rsvp ingress trunk elsp class";
                            container config {
                                description
                                    "configuration container for rsvp elsp class";
                                uses rsvp-trunk-dsinfo-config;
                            } // END of config-container definition.
                            container state {
                                config false;
                                description
                                    "state container for rsvp elsp class";
                                uses rsvp-trunk-dsinfo-config;
                            } // END of state-container definition.
                        } // END of elsp-class-container definition.
                    } // END of diff-serv-info-container definition.
                } // End of session-list
                container fast-reroute {
                    if-feature feature-list:HAVE_MPLS_FRR;
                    description
                        "configuration container for rsvp ingress session fast reroute";

                    list frr-admin-group {
                        if-feature feature-list:HAVE_MPLS_FRR;
                        key "admin-group-name";
                        description
                            "list of ingress trunk fast reroute admin group";
                        leaf admin-group-name  {
                            type  leafref {
                                path  "../config/admin-group-name";
                            }
                            description "rsvp admin group name";
                        } // END of admin-group-name definition.

                        container config {
                            description
                                "configuration container for rsvp fast-reroute-admin-group";
                            uses rsvp-admin-group-frr-config;
                        } // END of config-container definition.
                        container state {
                            config false;
                            description
                                "state container for rsvp fast-reroute-admin-group";
                            uses rsvp-admin-group-frr-config;
                        } // END of state-container definition.
                    } // End of frr-admin-group-list
                    container config {
                        description
                            "configuration container for rsvp sessions fast reroute";
                        uses rsvp-trunk-frr-bandwidth-config;
                        uses rsvp-trunk-frr-config;
                    } // END of config-container definition.
                    container state {
                        config false;
                        description
                            "state container for rsvp sessions fast reroute";
                        uses rsvp-trunk-frr-bandwidth-config;
                        uses rsvp-trunk-frr-config;
                    } // END of state-container definition.
                } // END of fast-reroute-container definition.
                container srlg {
                    if-feature feature-list:HAVE_SRLG;
                    description
                        "Top level container Shared Risk Link Groups for secondary backup LSPs
                                or fast-reroute LSPs";
                    container config {
                        description
                            "configuration container for Shared Risk Link Groups";
                        uses rsvp-trunk-srlg-config;
                    } // END of config-container definition.
                    container state {
                        config false;
                        description
                            "state container for Shared Risk Link Groups";
                        uses rsvp-trunk-srlg-config;
                    } // END of state-container definition.
                } // END of srlg-container definition.
            } // END of sessions-container definition.
        } // End of ingress-trunk-list
        uses trunk-grouping;
    } // END of trunks-container definition.
    } // END of trunks-grouping definition.


}
