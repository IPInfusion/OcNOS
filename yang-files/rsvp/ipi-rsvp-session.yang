/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-rsvp-session.yang
*
*/

submodule ipi-rsvp-session {

    yang-version 1.1;

    belongs-to  ipi-rsvp { prefix ipi-rsvp; }

    import feature-list {
        prefix feature-list;
        revision-date 2023-02-21;
    }

    import ipi-rsvp-types {
        prefix ipi-rsvp-types;
        revision-date 2022-06-01;
    }

    import ietf-inet-types {
        prefix inet;
        revision-date 2013-07-15;
    }

    import cml-data-types {
        prefix cml-data-types;
        revision-date 2022-09-30;
    }

    organization
        "IP Infusion Inc.";

    contact
        "Address: 3965 Freedom Circle, Suite 200, Santa Clara, CA 95054
         Phone: +1 408-400-1900
         E-mail: support@ipinfusion.com
         Web: http://www.ipinfusion.com/";

    description
        "Resource Reservation Protocol";


    revision "2022-06-01" {
        description "Updated the yang file with feature";
        reference " 0.7.0.";
    }

    revision "2021-09-03" {
        description "Update descriptions of attribute";
        reference " 0.6.0.";
    }

    revision "2021-06-26" {
        description "Updated multipath runtime attribute for trunk entry";
        reference " 0.5.0.";
    }

    revision "2021-03-27" {
        description "Added notification for RSVP Tunnel re-optimization";
        reference " 0.4.1.";
    }

    revision "2021-01-27" {
        description "Updated XPATH to API mappings. Fixed known bugs";
        reference " 0.3.0.";
    }

    revision "2020-12-15" {
        description "Change to have data-types in lower case instead of camel case";
        reference " 0.2.0.";
    }

    revision "2018-06-21" {
        description "Initial Version";
        reference " 0.1.0.";
    }



    grouping trunk-grouping {
    description
        "Top level list for rsvp trunk";
        list trunk {
            if-feature feature-list:HAVE_RSVPD;
            key "trunk-id extended-tunnel-id egress";
            config false;
            description
                "Top level list for rsvp trunk";
            leaf trunk-id  {
                type  leafref {
                    path  "../sessions/session/state/trunk-id";
                }
                description "Trunk identifier";
            } // END of trunk-id definition.

            leaf extended-tunnel-id  {
                type  leafref {
                    path  "../sessions/session/state/extended-tunnel-id";
                }
                description "Extended-tunnel identifier of the trunk";
            } // END of extended-tunnel-id definition.

            leaf egress  {
                type  leafref {
                    path  "../sessions/session/state/egress";
                }
                description "Egress endpoint address for the trunk";
            } // END of egress definition.

            leaf multipath-group-name  {
                if-feature feature-list:HAVE_RSVP_MULTIPATH;
                type  string {
                    length "1..1965";
                    pattern "[^?' =,>|]+";
                }
                description "Multipath group name associated with the trunk";
            } // END of multipath-group-name definition.

            leaf multipath-group-identifier  {
                if-feature feature-list:HAVE_RSVP_MULTIPATH;
                type  uint16;
                description "Multipath group identifier associated with the trunk";
            } // END of multipath-group-identifier definition.

            container sessions {
                config false;
                description
                    "State level container for all rsvp session parameters";

                list session {
                    key "session-name";
                    config false;
                    description
                        "State level list for all rsvp session parameters";
                    leaf session-name  {
                        type  leafref {
                            path  "../state/session-name";
                        }
                        description "Name of the session";
                    } // END of session-name definition.

                    container state {
                        config false;
                        description
                            "Top level list for rsvp session parameters";
                        uses rsvp-session-param;
                    } // END of state-container definition.
                } // End of session-list
            } // END of sessions-container definition.
        } // End of trunk-list
    } // END of trunk-grouping definition.
    grouping rsvp-trunk-state {
        description
            "Operational parameters for rsvp trunk";
        leaf trunk-id  {
            type  uint32;
            description "Trunk identifier";
        } // END of trunk-id definition.

        leaf extended-tunnel-id  {
            type  inet:ip-address;
            description "Extended-tunnel identifier of the trunk";
        } // END of extended-tunnel-id definition.

    } // END of rsvp-trunk-state definition.
    grouping rsvp-trunk-common-state {
        description
            "Operational parameters for rsvp neighbor session";
        leaf lsp-id  {
            type  uint16;
            description "Label switch path id";
        } // END of lsp-id definition.

        leaf session-frr-type  {
            type  ipi-rsvp-types:rsvp_session_frr_type_t;
            description "Type of the rsvp session (main session/detour session)";
        } // END of session-frr-type definition.

        leaf ingress  {
            type  inet:ip-address;
            description "Source address of the trunk";
        } // END of ingress definition.

        leaf egress  {
            type  inet:ip-address;
            description "Egress endpoint address for the trunk";
        } // END of egress definition.

        leaf trunk-session-type  {
            type  ipi-rsvp-types:rsvp_sess_type_t;
            description "Type of the session is either primary or secondary";
        } // END of trunk-session-type definition.

    } // END of rsvp-trunk-common-state definition.
    grouping rsvp-trunk-map-route-state {
        description
            "Operational parameters for rsvp map route";
        leaf type-of-service-name  {
            type  string {
                length "1..1965";
                pattern "[^?' =,>|]+";
            }
            description "Name of the mapped route type of service";
        } // END of type-of-service-name definition.

        leaf destination-ip-address  {
            type  inet:ip-address;
            description "Destination Address of the map route";
        } // END of destination-ip-address definition.

        leaf label-switch-path-id  {
            type  uint16;
            description "Label Switch Identifier of the map route";
        } // END of label-switch-path-id definition.

    } // END of rsvp-trunk-map-route-state definition.
    grouping rsvp-session-global-state {
        description
            "Operational parameters for rsvp session";
        leaf session-name  {
            type  string {
                length "1..1965";
                pattern "[^?' =,>|]+";
            }
            description "Name of the session";
        } // END of session-name definition.

        leaf session-role  {
            type  ipi-rsvp-types:rsvp_session_role_t;
            description "rsvp trunk session role";
        } // END of session-role definition.

        leaf is-pseudo-primary  {
            type  ipi-rsvp-types:rsvp_yes_no_t;
            description "Pseudo primary is in use or not";
        } // END of is-pseudo-primary definition.

        leaf lsp-state  {
            type  string {
                length "1..1965";
                pattern "[^?' =,>|]+";
            }
            description "Status of the Label Switch Path";
        } // END of lsp-state definition.

        leaf fsm-state  {
            type  string {
                length "1..1965";
                pattern "[^?' =,>|]+";
            }
            description "Status of the Finite State Machine";
        } // END of fsm-state definition.

        leaf transit-downstream-fsm-state  {
            type  string {
                length "1..1965";
                pattern "[^?' =,>|]+";
            }
            description "Status of the Transit Downstream Finite State Machine";
        } // END of transit-downstream-fsm-state definition.

        leaf establishment-time  {
            type  cml-data-types:cml_line_t {
                length "1..1965";
            }
            description "Establishment Time of the session";
        } // END of establishment-time definition.

        leaf revert-hold-timer  {
            type  ipi-rsvp-types:rsvp_yes_no_t;
            description "Revert Hold timer of the session";
        } // END of revert-hold-timer definition.

        leaf remaining-revert-time  {
            type  uint32;
            units "seconds";
            description "Remaining Time of the session (due to expire in seconds)";
        } // END of remaining-revert-time definition.

        leaf session-filter-style  {
            type  ipi-rsvp-types:rsvp_filter_state_type_t;
            description "rsvp trunk session style";
        } // END of session-filter-style definition.

        leaf in-label  {
            type  uint32;
            description "rsvp trunk session in label";
        } // END of in-label definition.

        leaf out-label  {
            type  uint32;
            description "rsvp trunk session out label";
        } // END of out-label definition.

        leaf bypass-out-label  {
            type  uint32;
            description "rsvp bypass trunk session out label";
        } // END of bypass-out-label definition.

        leaf bypass-out-interface  {
            type  string {
                length "1..1965";
                pattern "[^?' =,>|]+";
            }
            description "rsvp bypass trunk output interface";
        } // END of bypass-out-interface definition.

        leaf gmpls-label-type  {
            type  ipi-rsvp-types:rsvp_gmpls_label_type_t;
            description "rsvp trunk session tech type";
        } // END of gmpls-label-type definition.

        leaf qos-traffic-type  {
            type  ipi-rsvp-types:rsvp_traffic_type_state_t;
            description "rsvp session traffic";
        } // END of qos-traffic-type definition.

        leaf minimum-path-mtu  {
            type  uint32;
            description "rsvp session traffic";
        } // END of minimum-path-mtu definition.

    } // END of rsvp-session-global-state definition.
    grouping rsvp-session-cspf-state {
        description
            "Operational parameters for constrained shortest path factor";
        leaf cspf-state  {
            type  ipi-rsvp-types:rsvp_status_t;
            description "Status of the constrained shortest path factor";
        } // END of cspf-state definition.

        leaf lsp-reoptimization-state  {
            type  ipi-rsvp-types:rsvp_status_t;
            description "Status of the cspf lsp reoptimization";
        } // END of lsp-reoptimization-state definition.

        leaf lsp-reoptimization-timer  {
            type  uint32;
            units "seconds";
            description "Value of the cspf lsp reoptimization timer";
        } // END of lsp-reoptimization-timer definition.

        leaf cspf-client  {
            type  ipi-rsvp-types:rsvp_cspf_client_t;
            description "Client of the cspf (ospf/isis)";
        } // END of cspf-client definition.

    } // END of rsvp-session-cspf-state definition.
    grouping rsvp-session-upstream-downstream-state {
        description
            "Operational parameters for rsvp upstream and downstream";
        leaf upstream-ip-address  {
            type  inet:ip-address;
            description "Ip address of the upstream interface";
        } // END of upstream-ip-address definition.

        leaf upstream-interface-name  {
            type  string {
                length "1..1965";
                pattern "[^?' =,>|]+";
            }
            description "Name of the upstream interface";
        } // END of upstream-interface-name definition.

        leaf downstream-ip-address  {
            type  inet:ip-address;
            description "Ip address of the downstream interface";
        } // END of downstream-ip-address definition.

        leaf downstream-interface-name  {
            type  string {
                length "1..1965";
                pattern "[^?' =,>|]+";
            }
            description "Name of the downstream interface";
        } // END of downstream-interface-name definition.

    } // END of rsvp-session-upstream-downstream-state definition.
    grouping rsvp-session-fast-reroute-state {
        description
            "Operational parameters for rsvp session fast reroute";
        leaf lsp-protection  {
            if-feature feature-list:HAVE_MPLS_FRR;
            type  ipi-rsvp-types:rsvp_frr_protection_t;
            description "Type of the lsp protection(one-to-one/facility)";
        } // END of lsp-protection definition.

        leaf bypass-trunk-name  {
            if-feature feature-list:HAVE_MPLS_FRR;
            type  string {
                length "1..1965";
                pattern "[^?' =,>|]+";
            }
            description "Name of the bypass facilty trunk";
        } // END of bypass-trunk-name definition.

        leaf merge-point-address  {
            if-feature feature-list:HAVE_MPLS_FRR;
            type  inet:ipv4-address;
            description "rsvp session merge point address";
        } // END of merge-point-address definition.

        leaf merge-point-label  {
            if-feature feature-list:HAVE_MPLS_FRR;
            type  uint32;
            description "rsvp session merge point label";
        } // END of merge-point-label definition.

    } // END of rsvp-session-fast-reroute-state definition.
    grouping rsvp-session-spec-state {
        description
            "Operational parameters for traffic specification and filter
                        specification";
        leaf traffic-specification-rate  {
            type  uint32;
            description "Traffic specification rate in path message";
        } // END of traffic-specification-rate definition.

        leaf filter-specification-rate  {
            type  uint32;
            description "Filter specification rate in reserve message";
        } // END of filter-specification-rate definition.

    } // END of rsvp-session-spec-state definition.
    grouping rsvp-session-path-refresh-state {
        description
            "Operational parameters for rsvp session path refresh and lifetime";
        leaf path-refresh-time  {
            type  uint32;
            units "seconds";
            description "Value of the path refresh";
        } // END of path-refresh-time definition.

        leaf remaining-path-refresh-time  {
            type  uint32;
            units "seconds";
            description "Remaining value of the path refresh time";
        } // END of remaining-path-refresh-time definition.

        leaf path-lifetime  {
            type  uint32;
            units "seconds";
            description "Value of the path lifetime";
        } // END of path-lifetime definition.

        leaf remaining-path-lifetime  {
            type  uint32;
            units "seconds";
            description "Remaining value of the path lifetime";
        } // END of remaining-path-lifetime definition.

    } // END of rsvp-session-path-refresh-state definition.
    grouping rsvp-session-reserve-refresh-state {
        description
            "Operational parameters for rsvp session reserve refresh and lifetime";
        leaf reserve-refresh-time  {
            type  uint32;
            units "seconds";
            description "Value of the reserve refresh";
        } // END of reserve-refresh-time definition.

        leaf remaining-reserve-refresh-time  {
            type  uint32;
            units "seconds";
            description "Remaining value of the reserve refresh time";
        } // END of remaining-reserve-refresh-time definition.

        leaf reserve-lifetime  {
            type  uint32;
            units "seconds";
            description "Value of the reserve lifetime";
        } // END of reserve-lifetime definition.

        leaf remaining-reserve-lifetime  {
            type  uint32;
            units "seconds";
            description "Remaining value of the reserve lifetime";
        } // END of remaining-reserve-lifetime definition.

    } // END of rsvp-session-reserve-refresh-state definition.
    grouping rsvp-session-retry-timer-state {
        description
            "Operational parameters for rsvp session retry timer";
        leaf remaining-retry-time  {
            type  uint32;
            units "seconds";
            description "Value of the remaining retry time";
        } // END of remaining-retry-time definition.

        leaf next-retry-time  {
            type  uint32;
            units "seconds";
            description "Value of the next retry";
        } // END of next-retry-time definition.

    } // END of rsvp-session-retry-timer-state definition.
    grouping rsvp-session-explicit-route-object-state {
        description
            "Operational parameters for rsvp session explict route object";
        leaf link-address  {
            type  inet:ip-address;
            description "Explict route object ip address";
        } // END of link-address definition.

        leaf link-type  {
            type  ipi-rsvp-types:rsvp_path_status_t;
            description "Explict route object Path type";
        } // END of link-type definition.

    } // END of rsvp-session-explicit-route-object-state definition.
    grouping rsvp-session-route-record-state {
        description
            "Operational parameters for rsvp session route record";
        leaf-list address  {
            type  inet:ip-address;
            description "Route record object ip address";
        } // END of address definition.

    } // END of rsvp-session-route-record-state definition.
    grouping rsvp-path-state {
        description
            "rsvp path state information rsvp path";
        leaf path-identifier  {
            type  uint16;
            description "Identifier of rsvp path";
        } // END of path-identifier definition.

        leaf hop-count  {
            type  uint16;
            description "Number of hops";
        } // END of hop-count definition.

    } // END of rsvp-path-state definition.
    grouping rsvp-trunk-session-priorities-state {
        description
            "Operational parameters for rsvp session priority";
        leaf setup-priority  {
            type  uint8;
            description "rsvp trunk session setup priority";
        } // END of setup-priority definition.

        leaf hold-priority  {
            type  uint8;
            description "rsvp trunk session hold priority";
        } // END of hold-priority definition.

        leaf hop-limit  {
            type  uint8;
            description "rsvp trunk session hop limit";
        } // END of hop-limit definition.

        leaf bandwidth  {
            type  string {
                length "1..1965";
                pattern "[^?' =,>|]+";
            }
            description "rsvp trunk session bandwidth";
        } // END of bandwidth definition.

    } // END of rsvp-trunk-session-priorities-state definition.
    grouping rsvp-session-param {
        description
            "Top level grouping for parameters used in main session, make Before
                        Break session and Fast Reroute Detour Session";

        list received-explicit-route-object {
            key "link-address";
            config false;
            description
                "Top level list for received explicit route object parameters";
            leaf link-address  {
                type  leafref {
                    path  "../state/link-address";
                }
                description "Explict route object ip address";
            } // END of link-address definition.

            container state {
                config false;
                description
                    "State level container for all rsvp session received explicit route
                            object parameters";
                uses rsvp-session-explicit-route-object-state;
            } // END of state-container definition.
        } // End of received-explicit-route-object-list

        list explicit-route-object {
            key "link-address";
            config false;
            description
                "Top level list for explicit route object parameters";
            leaf link-address  {
                type  leafref {
                    path  "../state/link-address";
                }
                description "Explict route object ip address";
            } // END of link-address definition.

            container state {
                config false;
                description
                    "State level container for all rsvp session explicit route object
                            parameters";
                uses rsvp-session-explicit-route-object-state;
            } // END of state-container definition.
        } // End of explicit-route-object-list
        container constrained-shortest-path {
            config false;
            description
                "Top level container for constrained shortest path";
            container state {
                config false;
                description
                    "State level container for all rsvp session received explicit route
                            object parameters";
                uses rsvp-session-cspf-state;
            } // END of state-container definition.
        } // END of constrained-shortest-path-container definition.
        container fast-reroute {
            if-feature feature-list:HAVE_MPLS_FRR;
            config false;
            description
                "Top level container for Fast Reroute";
            container state {
                config false;
                description
                    "State level container for all rsvp session fast reroute";
                uses rsvp-session-fast-reroute-state;
            } // END of state-container definition.
        } // END of fast-reroute-container definition.
        container upstream-downstream-state {
            config false;
            description
                "Top level container for rsvp upstream and downsteam";
            container state {
                config false;
                description
                    "State level container for all rsvp session upstream and downsteam";
                uses rsvp-session-upstream-downstream-state;
            } // END of state-container definition.
        } // END of upstream-downstream-state-container definition.
        container traffic-flow-specification {
            config false;
            description
                "Top level container for rsvp specification in path and resv messages";
            container state {
                config false;
                description
                    "State level container for all rsvp session path and resv message
                            specification parameters";
                uses rsvp-session-spec-state;
            } // END of state-container definition.
        } // END of traffic-flow-specification-container definition.
        container session-priority {
            config false;
            description
                "Top level container for session priorities";
            container state {
                config false;
                description
                    "State level container for rsvp session priorities";
                uses rsvp-trunk-session-priorities-state;
            } // END of state-container definition.
        } // END of session-priority-container definition.
        container path-refresh-timers {
            config false;
            description
                "Top level container for session path refresh timers";
            container state {
                config false;
                description
                    "State level container for rsvp session path refresh timers";
                uses rsvp-session-path-refresh-state;
            } // END of state-container definition.
        } // END of path-refresh-timers-container definition.
        container reserve-refresh-timers {
            config false;
            description
                "Top level container for session reserve refresh timers";
            container state {
                config false;
                description
                    "State level container for all rsvp session reserve refresh timers";
                uses rsvp-session-reserve-refresh-state;
            } // END of state-container definition.
        } // END of reserve-refresh-timers-container definition.
        container retry-timers {
            config false;
            description
                "Top level container for retrytimers for the session";
            container state {
                config false;
                description
                    "State level container for all rsvp session retry timers";
                uses rsvp-session-retry-timer-state;
            } // END of state-container definition.
        } // END of retry-timers-container definition.
        container upstream-route-record-object {
            config false;
            description
                "Top level container for upstream route record object parameters";
            container state {
                config false;
                description
                    "State level container for all rsvp session upstream route record
                            object parameters";
                uses rsvp-session-route-record-state;
            } // END of state-container definition.
        } // END of upstream-route-record-object-container definition.
        container downstream-route-record-object {
            config false;
            description
                "Top level container for downstream route record object parameters";
            container state {
                config false;
                description
                    "State level container for all rsvp session downstream route record
                            object parameters";
                uses rsvp-session-route-record-state;
            } // END of state-container definition.
        } // END of downstream-route-record-object-container definition.
        uses rsvp-trunk-state;
        uses rsvp-trunk-common-state;
        uses rsvp-session-global-state;
    } // END of rsvp-session-param definition.


}
