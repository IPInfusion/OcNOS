/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-rsvp-types.yang
*
*/

module ipi-rsvp-types {

    yang-version 1.1;

    namespace   "http://www.ipinfusion.com/yang/ocnos/ipi-rsvp-types";

    prefix "ipi-rsvp-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-rsvp-types";


    revision "2022-06-01" {
        description "Updated the yang file with feature";
        reference " 0.6.0.";
    }

    revision "2021-10-01" {
        description "Update DC flag for facility";
        reference " 0.5.0.";
    }

    revision "2021-09-03" {
        description "Update descriptions of attribute";
        reference " 0.4.0.";
    }

    revision "2021-01-27" {
        description "Updated XPATH to API mappings. Fixed known bugs";
        reference " 0.3.0.";
    }

    revision "2020-12-15" {
        description "Change to have data-types in lower case instead of camel case";
        reference " 0.2.0.";
    }

    revision "2018-06-21" {
        description "Initial Version";
        reference " 0.1.0.";
    }



    typedef  rsvp_path_status_t {
        type enumeration {
            enum loose {
                value 0;
                description "Make this node loose";
            }
            enum strict {
                value 1;
                description "Make this node strict";
            }
        }
        description "type definition for RSVP_PATH_STATUS_T";
    }

    typedef  rsvp_frr_admin_type_t {
        type enumeration {
            enum exclude-any {
                value 0;
                description "Exclude-any attribute";
            }
            enum include-any {
                value 1;
                description "Include-any attribute";
            }
        }
        description "type definition for RSVP_FRR_ADMIN_TYPE_T";
    }

    typedef  rsvp_traffic_type_t {
        type enumeration {
            enum controlled-load {
                value 1;
                description "Controlled load traffic";
            }
            enum guaranteed {
                value 2;
                description "Guaranteed traffic";
            }
        }
        description "type definition for RSVP_TRAFFIC_TYPE_T";
    }

    typedef  rsvp_update_type_t {
        type enumeration {
            enum break-before-make {
                value 1;
                description "Break Before Make";
            }
            enum make-before-break {
                value 2;
                description "Make Before Break";
            }
        }
        description "type definition for RSVP_UPDATE_TYPE_T";
    }

    typedef  rsvp_backup_bandwidth_type {
        type enumeration {
            enum best-effort {
                value 0;
                description "best-effort backup bandwidth";
            }
            enum dedicated {
                value 1;
                description "dedicated backup bandwidth";
            }
        }
        description "type definition for RSVP_BACKUP_BANDWIDTH_TYPE";
    }

    typedef  rsvp_capability_type_t {
        type enumeration {
            enum psc-2 {
                value 2;
                description "Packet Switch Capable-2";
            }
            enum psc-3 {
                value 4;
                description "Packet Switch Capable-3";
            }
            enum psc-4 {
                value 8;
                description "Packet Switch Capable-4";
            }
            enum l2sc {
                value 16;
                if-feature feature-list:HAVE_TDM;
                description "Layer-2 Switch Capable (L2SC)";
            }
            enum tdm {
                value 32;
                if-feature feature-list:HAVE_TDM;
                description "Time-Division-Multiplex Capable (TDM)";
            }
            enum lsc {
                value 64;
                if-feature feature-list:HAVE_TDM;
                description "Lambda-Switch Capable (LSC)";
            }
            enum fsc {
                value 128;
                if-feature feature-list:HAVE_TDM;
                description "Fiber-Switch Capable (FSC)";
            }
            enum pbb-te {
                value 256;
                if-feature feature-list:HAVE_PBB_TE;
                description "PBB-TE Switching";
            }
            enum psc-1 {
                description "Packet Switch Capable-1";
            }
            enum psc {
                if-feature feature-list:HAVE_TDM;
                description "Packet Switch Capable (PSC)";
            }
        }
        description "type definition for RSVP_CAPABILITY_TYPE_T";
    }

    typedef  rsvp_direction_type_t {
        type enumeration {
            enum unidirectional {
                value 0;
                description "Unidirectional";
            }
            enum bidirectional {
                value 1;
                description "Bidirectional";
            }
        }
        description "type definition for RSVP_DIRECTION_TYPE_T";
    }

    typedef  rsvp_gpid_type_t {
        type enumeration {
            enum ethernet {
                value 33;
                description "Ethernet gpid type";
            }
            enum ipv4 {
                value 2048;
                description "IPv4 gpid type";
            }
        }
        description "type definition for RSVP_GPID_TYPE_T";
    }

    typedef  rsvp_explicit_fwd_dir_t {
        type enumeration {
            enum forward {
                value 1;
                description "Forward LSP Direction - Ingress to Egress (Downstream)";
            }
            enum packet-forward {
                value 3;
                description "Default label-type is packet, Forward LSP Direction - Ingress to Egress (Downstream)";
            }
        }
        description "type definition for RSVP_EXPLICIT_FWD_DIR_T";
    }

    typedef  rsvp_explicit_rev_dir_t {
        type enumeration {
            enum reverse {
                value 2;
                description "Reverse LSP Direction - Egress to Ingress (Upstream)";
            }
            enum packet-reverse {
                value 4;
                description "Default label-type is packet,Reverse LSP Direction - Egress to Ingress (Upstream)";
            }
        }
        description "type definition for RSVP_EXPLICIT_REV_DIR_T";
    }

    typedef  rsvp_filter_type_t {
        type enumeration {
            enum fixed {
                value 1;
                description "Use a Fixed Filter for this LSP";
            }
            enum shared-explicit {
                value 2;
                description "Use a Shared Explicit Filter for this LSP";
            }
        }
        description "type definition for RSVP_FILTER_TYPE_T";
    }

    typedef  rsvp_protection_type_t {
        type enumeration {
            enum extra-traffic {
                value 1;
                description "Extra-traffic";
            }
            enum unprotected {
                value 2;
                description "Unprotected";
            }
            enum shared {
                value 4;
                description "Shared";
            }
            enum dedicated-one-to-one {
                value 8;
                description "Dedicated 1:1";
            }
            enum dedicated-one-plus-one {
                value 16;
                description "Dedicated 1+1";
            }
            enum enhanced {
                value 32;
                description "Enhanced";
            }
        }
        description "type definition for RSVP_PROTECTION_TYPE_T";
    }

    typedef  rsvp_instance_t {
        type enumeration {
            enum rsvp {
                value 1;
                description "Resource Reservation Protocol (RSVP)";
            }
        }
        description "type definition for RSVP_INSTANCE_T";
    }

    typedef  rsvp_path_type_t {
        type enumeration {
            enum mpls {
                value 0;
                description "Path type is mpls";
            }
            enum gmpls {
                value 1;
                description "Path type is gmpls";
            }
        }
        description "type definition for RSVP_PATH_TYPE_T";
    }

    typedef  rsvp_detour_iden_t {
        type enumeration {
            enum sender-template {
                value 1;
                description "Sender Template specific detour identification method";
            }
            enum path {
                value 2;
                description "Path Secific detour identification method (using detour object)";
            }
        }
        description "type definition for RSVP_DETOUR_IDEN_T";
    }

    typedef  rsvp_cspf_type_t {
        type enumeration {
            enum no-cspf {
                value 0;
                description "Use Hop-by-Hop Routing";
            }
            enum cspf {
                value 1;
                description "Use CSPF for Path Computation";
            }
        }
        description "type definition for RSVP_CSPF_TYPE_T";
    }

    typedef  rsvp_preemp_t {
        type enumeration {
            enum less-lsp-preempted {
                value 0;
                description "less lsp preempted";
            }
            enum less-unused-bandwidth {
                value 1;
                description "less unused bandwidth preempted";
            }
        }
        description "type definition for RSVP_PREEMP_T";
    }

    typedef  rsvp_debug_t {
        type bits {
            bit events {
                position 0;
                description "RSVP events";
            }
            bit packet {
                position 1;
                description "RSVP packet";
            }
            bit packet-in {
                position 2;
                description "RSVP packet,Incoming RSVP packet";
            }
            bit packet-out {
                position 3;
                description "RSVP packet, Outgoing RSVP packet";
            }
            bit hexdump {
                position 4;
                description "RSVP Hexdump";
            }
            bit nsm {
                position 5;
                description "NSM messages";
            }
            bit cspf {
                position 6;
                if-feature feature-list:HAVE_CSPF;
                description "CSPF messages";
            }
            bit fsm-egress {
                position 7;
                description "Enable FSM debugging,Enable RSVP Egress FSM debugging";
            }
            bit fsm-transit-downstream {
                position 8;
                description "Enable FSM debugging, Enable RSVP Transit FSM debugging, Enable RSVP Transit Downstream FSM debugging";
            }
            bit fsm-transit-upstream {
                position 9;
                description "Enable FSM debugging,Enable RSVP Transit FSM debugging,Enable RSVP Transit Upstream FSM dugging";
            }
            bit fsm-ingress {
                position 10;
                description "Enable FSM debugging, Enable RSVP Ingress FSM debugging";
            }
            bit rib {
                position 11;
                if-feature feature-list:HAVE_RIBD;
                description "RIB messages";
            }
        }
        description "type definition for RSVP_DEBUG_T";
    }

    typedef  rsvp_trunk_family_t {
        type enumeration {
            enum gmpls {
                value 1;
                if-feature feature-list:HAVE_GMPLS;
                description "GMPLS enabled trunk";
            }
            enum ipv4 {
                value 2;
                description "IPv4 address family trunk";
            }
            enum ipv6 {
                value 10;
                if-feature feature-list:HAVE_MPLS_FWD;
                description "IPv6 address family trunk";
            }
        }
        description "type definition for RSVP_TRUNK_FAMILY_T";
    }

    typedef  rsvp_frr_protection_t {
        type enumeration {
            enum one-to-one {
                value 1;
                description "One-to-One protection mechanism";
            }
            enum facility {
                value 2;
                if-feature feature-list:NOT_HAVE_CUSTOM1_MPLS;
                description "Facility Backup (Bypass) protection";
            }
        }
        description "type definition for RSVP_FRR_PROTECTION_T";
    }

    typedef  rsvp_admin_type_t {
        type enumeration {
            enum exclude-any {
                value 0;
                description "Exclude-any attribute";
            }
            enum include-any {
                value 1;
                description "Include-any attribute";
            }
            enum include-all {
                value 2;
                description "Include-all attribute";
            }
        }
        description "type definition for RSVP_ADMIN_TYPE_T";
    }

    typedef  rsvp_exclude_path_type_t {
        type enumeration {
            enum link {
                value 1;
                description "Enables a Link Protection - NHOP";
            }
            enum node {
                value 2;
                description "Enables a Node Protection - NNHOP";
            }
        }
        description "type definition for RSVP_EXCLUDE_PATH_TYPE_T";
    }

    typedef  rsvp_sess_type_t {
        type enumeration {
            enum secondary {
                value 0;
                description "Configure secondary LSP option";
            }
            enum primary {
                value 1;
                description "Configure primary LSP option";
            }
        }
        description "type definition for RSVP_SESS_TYPE_T";
    }

    typedef  rsvp_lsp_protection_type_t {
        type enumeration {
            enum full-rerouting {
                value 1;
                description "Full Rerouting";
            }
            enum rerouting-without-extra-traffic {
                value 2;
                description "Rerouting without Extra-traffic";
            }
            enum one-to-one {
                value 4;
                description "1:1 Protection with extra traffic";
            }
            enum one-plus-one-unidirectional {
                value 8;
                description "1+1 Unidirectional Protection";
            }
            enum one-plus-one-bidirectional {
                value 16;
                description "1+1 Bidirectional Protection";
            }
        }
        description "type definition for RSVP_LSP_PROTECTION_TYPE_T";
    }

    typedef  rsvp_crankback_signaling_t {
        type enumeration {
            enum disable {
                value 0;
                description "disable the crankback";
            }
            enum enable {
                value 1;
                description "enable the crankback";
            }
        }
        description "type definition for RSVP_CRANKBACK_SIGNALING_T";
    }

    typedef  rsvp_crankback_operation_t {
        type enumeration {
            enum no-re-routing {
                value 0;
                description "No Re-routing";
            }
            enum end-to-end-rerouting {
                value 1;
                description "End-to-end Re-routing";
            }
            enum boundary-rerouting {
                value 2;
                description "Boundary Re-routing";
            }
            enum segment-based-rerouting {
                value 3;
                description "Segment-based Re-routing";
            }
        }
        description "type definition for RSVP_CRANKBACK_OPERATION_T";
    }

    typedef  rsvp_crankback_reroute_t {
        type enumeration {
            enum not-allow {
                value 0;
                description "Not allowed re-routing";
            }
            enum allow {
                value 1;
                description "Allowed re-routing";
            }
        }
        description "type definition for RSVP_CRANKBACK_REROUTE_T";
    }

    typedef  rsvp_te_srlg_disjoint_type_t {
        type enumeration {
            enum forced {
                value 1;
                description "Forced";
            }
            enum preferred {
                value 2;
                description "Preferred";
            }
        }
        description "type definition for RSVP_TE_SRLG_DISJOINT_TYPE_T";
    }

    typedef  rsvp_trunk_family_p2mp_t {
        type enumeration {
            enum ipv4 {
                value 1;
                description "IPv4 address family rsvp trunk";
            }
        }
        description "type definition for RSVP_TRUNK_FAMILY_P2MP_T";
    }

    typedef  rsvp_interface_type_t {
        type enumeration {
            enum unknown {
                value 0;
                description "Hardware type is Unknown";
            }
            enum ethernet {
                value 2;
                description "Hardware type is Ethernet";
            }
            enum SVI {
                value 7;
                description "Hardware type is SVI Interface";
            }
            enum AGG {
                value 9;
                description "Hardware type is aggrecated ethernet";
            }
            enum frame-relay {
                value 15;
                description "Hardware type is Frame Relay";
            }
            enum atm {
                value 24;
                description "Hardware type is ATM";
            }
        }
        description "type definition for RSVP_INTERFACE_TYPE_T";
    }

    typedef  rsvp_interface_status_t {
        type enumeration {
            enum disable {
                value 0;
                description "Disbale rsvp in interface";
            }
            enum enable {
                value 1;
                description "Enable rsvp in interface";
            }
        }
        description "type definition for RSVP_INTERFACE_STATUS_T";
    }

    typedef  rsvp_label_space_status_t {
        type enumeration {
            enum Invalid {
                value 0;
                description "Label Space status is invaild";
            }
            enum Valid {
                value 1;
                description "Label space status is valid";
            }
        }
        description "type definition for RSVP_LABEL_SPACE_STATUS_T";
    }

    typedef  rsvp_addr_family_t {
        type enumeration {
            enum ipv4 {
                value 1;
                description "IPV4 address family";
            }
            enum ipv6 {
                value 2;
                description "IPV6 address family";
            }
        }
        description "type definition for RSVP_ADDR_FAMILY_T";
    }

    typedef  rsvp_gmpls_label_type_t {
        type enumeration {
            enum packet {
                value 0;
                description "Packet Based Labelling";
            }
            enum pbb-te {
                value 1;
                description "PBB-TE Based Labelling";
            }
            enum otn-odh {
                value 2;
                description "Optical Transport Networks ODH Based Labelling";
            }
            enum otn-och {
                value 3;
                description "Optical Transport Networks OCH Based Labelling";
            }
            enum sdh-sonet {
                value 4;
                description "SONET or SDH Based Labelling ";
            }
            enum port-wave-length {
                value 5;
                description "Port WaveLength Based Labelling";
            }
            enum freedom {
                value 6;
                description "Freedom Based Labelling";
            }
            enum sonet {
                value 7;
                description "SONET Based Labelling";
            }
            enum sdh {
                value 8;
                description "SDH Based Labelling";
            }
            enum waveband {
                value 9;
                description "WaveBand Based Labelling";
            }
            enum time-division-multiplex {
                value 10;
                description "Time Division Multiplex Based Labelling";
            }
            enum lambda-switch-capable {
                value 11;
                description "Lamda Switch Capable Based Labelling";
            }
            enum fiber-switch-capable {
                value 12;
                description "Fiber Swicth Capable Based Labelling";
            }
            enum ethernet-vpn {
                value 13;
                description "Ethernet VPN Based Labelling";
            }
        }
        description "type definition for RSVP_GMPLS_LABEL_TYPE_T";
    }

    typedef  rsvp_neighbor_hello_state_t {
        type enumeration {
            enum up {
                value 0;
                description "rsvp neighbor hello state is up";
            }
            enum down {
                value 1;
                description "rsvp neighbor hello state is down";
            }
        }
        description "type definition for RSVP_NEIGHBOR_HELLO_STATE_T";
    }

    typedef  rsvp_graceful_restart_recovery_status_t {
        type enumeration {
            enum no {
                value 0;
                description "rsvp graceful restart unset recovery";
            }
            enum yes {
                value 1;
                description "rsvp graceful restart set recovery";
            }
        }
        description "type definition for RSVP_GRACEFUL_RESTART_RECOVERY_STATUS_T";
    }

    typedef  rsvp_graceful_restart_status_t {
        type enumeration {
            enum normal {
                value 0;
                description "rsvp neighbor graceful restart state is normal";
            }
            enum restart {
                value 1;
                description "rsvp neighbor graceful restart state is restart";
            }
            enum recovery {
                value 2;
                description "rsvp neighbor graceful restart state is recovery";
            }
        }
        description "type definition for RSVP_GRACEFUL_RESTART_STATUS_T";
    }

    typedef  rsvp_status_t {
        type enumeration {
            enum disable {
                value 0;
                description "Disable";
            }
            enum enable {
                value 1;
                description "Enable";
            }
        }
        description "type definition for RSVP_STATUS_T";
    }

    typedef  rsvp_control_adjacency_status_t {
        type enumeration {
            enum down {
                value 0;
                description "Control adjacency status is down";
            }
            enum up {
                value 1;
                description "Control adjacency status is up";
            }
        }
        description "type definition for RSVP_CONTROL_ADJACENCY_STATUS_T";
    }

    typedef  rsvp_neighbor_refresh_reduction_status_t {
        type enumeration {
            enum not-supported {
                value 0;
                description "Neighbor status is un supported";
            }
            enum supported {
                value 1;
                description "Neighbor status is supported";
            }
        }
        description "type definition for RSVP_NEIGHBOR_REFRESH_REDUCTION_STATUS_T";
    }

    typedef  rsvp_session_role_t {
        type enumeration {
            enum none {
                value 0;
                description "Invalid session role";
            }
            enum ingress {
                value 1;
                description "Session role is ingress";
            }
            enum transit {
                value 2;
                description "Session role is transit";
            }
            enum egress {
                value 3;
                description "Session role is egress";
            }
            enum non-ingress {
                value 4;
                description "Session role is non ingress";
            }
        }
        description "type definition for RSVP_SESSION_ROLE_T";
    }

    typedef  rsvp_neighbor_type_t {
        type enumeration {
            enum implicit {
                value 0;
                description "absoulte lsp metric";
            }
            enum explicit {
                value 1;
                description "relative lsp metric";
            }
        }
        description "type definition for RSVP_NEIGHBOR_TYPE_T";
    }

    typedef  rsvp_yes_no_t {
        type enumeration {
            enum no {
                value 0;
                description "No";
            }
            enum yes {
                value 1;
                description "Yes";
            }
        }
        description "type definition for RSVP_YES_NO_T";
    }

    typedef  rsvp_cspf_client_t {
        type enumeration {
            enum none {
                value 0;
                description "No CSPF client";
            }
            enum ospf {
                value 1;
                description "CSPF client is ospf";
            }
            enum isis {
                value 5;
                description "CSPF client is isis";
            }
        }
        description "type definition for RSVP_CSPF_CLIENT_T";
    }

    typedef  rsvp_force_secondary_t {
        type enumeration {
            enum off {
                value 0;
                description "Disable secondary force switchover";
            }
            enum on {
                value 1;
                description "Enable secondary force switchover";
            }
        }
        description "type definition for RSVP_FORCE_SECONDARY_T";
    }

    typedef  rsvp_session_frr_type_t {
        type enumeration {
            enum main {
                value 0;
                description "Session type is main";
            }
            enum detour {
                value 1;
                description "Session type is detour";
            }
        }
        description "type definition for RSVP_SESSION_FRR_TYPE_T";
    }

    typedef  rsvp_traffic_type_state_t {
        type enumeration {
            enum undefined {
                value 0;
                description "Un Defined traffic";
            }
            enum controlled-load {
                value 1;
                description "Controlled load traffic";
            }
            enum guaranteed {
                value 2;
                description "Guaranteed traffic";
            }
        }
        description "type definition for RSVP_TRAFFIC_TYPE_STATE_T";
    }

    typedef  rsvp_preemption_type_t {
        type enumeration {
            enum Normal {
                value 0;
                description "The preemption type is normal";
            }
        }
        description "type definition for RSVP_PREEMPTION_TYPE_T";
    }

    typedef  rsvp_filter_state_type_t {
        type enumeration {
            enum undefined {
                value 0;
                description "Undefined filter type";
            }
            enum fixed {
                value 1;
                description "Use a Fixed Filter for this LSP";
            }
            enum shared-explicit {
                value 2;
                description "Use a Shared Explicit Filter for this LSP";
            }
        }
        description "type definition for RSVP_FILTER_STATE_TYPE_T";
    }

    typedef  rsvp_trunk_status_t {
        type enumeration {
            enum inactive {
                value 0;
                description "Trunk is inactive";
            }
            enum active {
                value 1;
                description "Trunk is active";
            }
        }
        description "type definition for RSVP_TRUNK_STATUS_T";
    }

}
