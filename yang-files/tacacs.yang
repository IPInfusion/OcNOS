/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : tacacs.yang
*
*/

submodule tacacs {

    belongs-to  ZebOS { prefix ZebOS; }
    include vrf;


    import cml_data_types {
        prefix cml_data_types;
    }

    import feature_list {
        prefix feature_list;
    }

    description
        "Layer-3 tacacs configurations";


    revision "2016-12-27" {
        description "Added snmp oid and documentation tag.";
    }

    revision "2016-10-28" {
        description "Initial version of TAcacs datamodel.";
    }


    grouping  tacacs-grouping {
    container tacacs {
        presence "yes"; 
                config true;

        description
            "tacacs related operations";

        leaf vrfName  {
            type  cml_data_types:CML_STRING_T {
                length "0..255";
            }
            default "default";
        } // END of vrfName definition.

        leaf featureTacacs  {
            mandatory true;
            type  cml_data_types:CML_BOOL_T;  
        } // END of featureTacacs definition.

        leaf key  {
            if-feature feature_list:HAVE_HOSTPD;
            if-feature feature_list:HAVE_AAA;
            if-feature feature_list:HAVE_TACACS_CLIENT;
            type  cml_data_types:CML_BOOL_T;  
            default false;
            description "Global key";
        } // END of key definition.

        leaf tacacsKeyEnable  {
            if-feature feature_list:HAVE_HOSTPD;
            if-feature feature_list:HAVE_AAA;
            if-feature feature_list:HAVE_TACACS_CLIENT;
            type  cml_data_types:CML_HOSTP_KEY_TYPE_T;  
            default "0";
        } // END of tacacsKeyEnable definition.

        leaf tacacsKeyWord  {
            if-feature feature_list:HAVE_HOSTPD;
            if-feature feature_list:HAVE_AAA;
            if-feature feature_list:HAVE_TACACS_CLIENT;
            type  cml_data_types:CML_STRING_T {
                length "0..255";
            }
            description "tacacs-server key";
        } // END of tacacsKeyWord definition.

        leaf tacacsTimeOut  {
            if-feature feature_list:HAVE_HOSTPD;
            if-feature feature_list:HAVE_AAA;
            if-feature feature_list:HAVE_TACACS_CLIENT;
            type  cml_data_types:CML_UINT32_T {
                 range "1..60";
            }
            default "5";
            description "tacacs-server timeout";
        } // END of tacacsTimeOut definition.

        leaf debugtacacs  {
            if-feature feature_list:HAVE_HOSTPD;
            if-feature feature_list:HAVE_AAA;
            if-feature feature_list:HAVE_TACACS_CLIENT;
            type  cml_data_types:CML_BOOL_T;  
            description "debug tacacs+";
        } // END of debugtacacs definition.

        leaf debugtacacsConfig  {
            if-feature feature_list:HAVE_HOSTPD;
            if-feature feature_list:HAVE_AAA;
            if-feature feature_list:HAVE_TACACS_CLIENT;
            type  cml_data_types:CML_BOOL_T;  
            description "Enable/Disable debug";
        } // END of debugtacacsConfig definition.


        list tacacshost {
             
            description
                "tacacshost";

            config true;
            key "hostAddr";

            
            leaf vrfName  {
                type  cml_data_types:CML_STRING_T {
                    length "0..255";
                }
                default "default";
            } // END of vrfName definition.

            leaf hostAddr  {
                type  cml_data_types:CML_HOSTPNAME_T;  
            } // END of hostAddr definition.

            leaf key  {
                if-feature feature_list:HAVE_HOSTPD;
                if-feature feature_list:HAVE_AAA;
                if-feature feature_list:HAVE_TACACS_CLIENT;
                type  cml_data_types:CML_BOOL_T;  
                default false;
            } // END of key definition.

            leaf keyEnable  {
                if-feature feature_list:HAVE_HOSTPD;
                if-feature feature_list:HAVE_AAA;
                if-feature feature_list:HAVE_TACACS_CLIENT;
                type  cml_data_types:CML_HOSTP_KEY_TYPE_T;  
                default "0";
            } // END of keyEnable definition.

            leaf keyWord  {
                if-feature feature_list:HAVE_HOSTPD;
                if-feature feature_list:HAVE_AAA;
                if-feature feature_list:HAVE_TACACS_CLIENT;
                type  cml_data_types:CML_STRING_T {
                    length "0..255";
                }
            } // END of keyWord definition.

            leaf port  {
                if-feature feature_list:HAVE_HOSTPD;
                if-feature feature_list:HAVE_AAA;
                if-feature feature_list:HAVE_TACACS_CLIENT;
                type  cml_data_types:CML_UINT32_T {
                     range "1025..65535";
                }
            } // END of port definition.

            leaf timeout  {
                if-feature feature_list:HAVE_HOSTPD;
                if-feature feature_list:HAVE_AAA;
                if-feature feature_list:HAVE_TACACS_CLIENT;
                type  cml_data_types:CML_UINT32_T {
                     range "1..60";
                }
                default "5";
                description "To represent the timeout configured by the user";
            } // END of timeout definition.

        } // End of tacacshost-list
    } // END of tacacs-container definition.
    } // END of tacacs-container definition.


}
