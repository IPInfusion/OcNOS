/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : plist.yang
*
*/

submodule plist {

    belongs-to  ZebOS { prefix ZebOS; }
    include vr;


    import cml_data_types {
        prefix cml_data_types;
    }


    revision "2016-12-29" {
        description "OSPF module inclusion.";
    }

    revision "2016-10-20" {
        description "Initial version of plist datamodel.";
    }



    grouping prefixMaster-grouping {
        list prefixMaster {
             
            description
                "Master structure";

            config true;
            key "vrId";

            
            leaf vrId  {
                type  cml_data_types:CML_UINT32_T;  
                description "Virtual Router ID";
            } // END of vrId definition.

            leaf seqnum  {
                type  cml_data_types:CML_BOOL_T;  
            } // END of seqnum definition.


            list ipPrefix {
                 
                description
                    "List of struct prefix_list";

                config true;
                key "plistname";

                
                leaf plistname  {
                    type  cml_data_types:CML_STRING_T {
                        length "0..255";
                    }
                } // END of plistname definition.

                leaf description  {
                    type  cml_data_types:CML_STRING_T {
                        length "0..255";
                    }
                    default "NULL";
                } // END of description definition.

                leaf count  {
                    type  cml_data_types:CML_INT32_T;  
                    config false;
                } // END of count definition.

                leaf rangeCount  {
                    type  cml_data_types:CML_INT32_T;  
                    config false;
                } // END of rangeCount definition.


                list ipPrefixEntry {
                     
                    description
                        "Each prefix-list's entry";

                    config true;
                    key "seq";

                    
                    leaf seq  {
                        type  cml_data_types:CML_UINT32_T {
                             range "1..4294967295";
                        }
                    } // END of seq definition.

                    leaf type  {
                        mandatory true;
                        type  cml_data_types:CML_PREFIX_LIST_TYPE;  
                    } // END of type definition.

                    leaf network  {
                        mandatory true;
                        type  cml_data_types:CML_IPV4_ADDR_PREFIX_T;  
                    } // END of network definition.

                    leaf minPrefixLength  {
                        mandatory true;
                        type  cml_data_types:CML_UINT8_T {
                             range "0..32";
                        }
                    } // END of minPrefixLength definition.

                    leaf maxPrefixLength  {
                        mandatory true;
                        type  cml_data_types:CML_UINT8_T {
                             range "0..32";
                        }
                    } // END of maxPrefixLength definition.

                    leaf eqPrefixLength  {
                        mandatory true;
                        type  cml_data_types:CML_UINT8_T {
                             range "0..32";
                        }
                    } // END of eqPrefixLength definition.

                    leaf any  {
                        mandatory true;
                        type  cml_data_types:CML_BOOL_T;  
                    } // END of any definition.

                    leaf refCount  {
                        type  cml_data_types:CML_UINT32_T;  
                        config false;
                    } // END of refCount definition.

                    leaf hitCount  {
                        type  cml_data_types:CML_UINT32_T;  
                        config false;
                    } // END of hitCount definition.

                } // End of ipPrefixEntry-list
            } // End of ipPrefix-list
        } // End of prefixMaster-list
    } // END of prefixMaster-grouping definition.


    grouping prefixMaster6-grouping {
        list prefixMaster6 {
             
            description
                "Master structure of prefix_list";

            config true;
            key "vrId";

            
            leaf vrId  {
                type  cml_data_types:CML_UINT32_T;  
                description "Virtual Router ID";
            } // END of vrId definition.

            leaf ipv6Seqnum  {
                type  cml_data_types:CML_BOOL_T;  
            } // END of ipv6Seqnum definition.


            list ipv6Prefix {
                 
                description
                    "List of struct prefix_list";

                config true;
                key "plistname6";

                
                leaf plistname6  {
                    type  cml_data_types:CML_STRING_T {
                        length "0..255";
                    }
                } // END of plistname6 definition.

                leaf description6  {
                    type  cml_data_types:CML_STRING_T {
                        length "0..255";
                    }
                    default "NULL";
                } // END of description6 definition.

                leaf count6  {
                    type  cml_data_types:CML_INT32_T;  
                    config false;
                } // END of count6 definition.

                leaf rangeCount6  {
                    type  cml_data_types:CML_INT32_T;  
                    config false;
                } // END of rangeCount6 definition.


                list ipv6PrefixEntry {
                     
                    description
                        "Each prefix-list's entry";

                    config true;
                    key "seq6";

                    
                    leaf seq6  {
                        type  cml_data_types:CML_UINT32_T {
                             range "1..4294967295";
                        }
                    } // END of seq6 definition.

                    leaf type6  {
                        mandatory true;
                        type  cml_data_types:CML_PREFIX_LIST_TYPE;  
                    } // END of type6 definition.

                    leaf network6  {
                        mandatory true;
                        type  cml_data_types:CML_IPV6_PREFIX_T;  
                    } // END of network6 definition.

                    leaf minPrefixLength6  {
                        mandatory true;
                        type  cml_data_types:CML_UINT8_T {
                             range "0..128";
                        }
                    } // END of minPrefixLength6 definition.

                    leaf maxPrefixLength6  {
                        mandatory true;
                        type  cml_data_types:CML_UINT8_T {
                             range "0..128";
                        }
                    } // END of maxPrefixLength6 definition.

                    leaf any6  {
                        mandatory true;
                        type  cml_data_types:CML_BOOL_T;  
                    } // END of any6 definition.

                    leaf refCount6  {
                        type  cml_data_types:CML_UINT32_T;  
                        config false;
                    } // END of refCount6 definition.

                    leaf hitCount6  {
                        type  cml_data_types:CML_UINT32_T;  
                        config false;
                    } // END of hitCount6 definition.

                } // End of ipv6PrefixEntry-list
            } // End of ipv6Prefix-list
        } // End of prefixMaster6-list
    } // END of prefixMaster6-grouping definition.


}
