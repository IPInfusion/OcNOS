/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : rip.yang
*
*/

submodule rip {

    belongs-to  ZebOS { prefix ZebOS; }
    include interface;
    include vrf;


    import cml_data_types {
        prefix cml_data_types;
    }

    import feature_list {
        prefix feature_list;
    }

    description
        "Routing Information Protocol";


    revision "2017-02-11" {
        description "Added Config and runtime attributes.";
    }

    grouping ripContents {
                leaf version  {
            type  cml_data_types:CML_UINT8_T {
                 range "1..2";
            }
            default "2";
            description "version";
        } // END of version definition.

        leaf-list enableNetwork  {
            type  cml_data_types:CML_IPV4_PREFIX_T;  
            description "network";
        } // END of enableNetwork definition.

        leaf-list enableInterface  {
            type  cml_data_types:CML_STRING_T {
                length "0..255";
            }
            description "network";
        } // END of enableInterface definition.

        leaf-list neighbor  {
            type  cml_data_types:CML_IPV4_ADDR_T;  
            description "neighbor";
        } // END of neighbor definition.

        leaf defaultInformation  {
            type  cml_data_types:CML_RIP_DEFAULT_ORIGINATE_T;  
            description "default-information originate";
        } // END of defaultInformation definition.

        leaf defaultMapName  {
            type  cml_data_types:CML_STRING_T {
                length "0..255";
            }
            default "NULL";
        } // END of defaultMapName definition.

        leaf defaultMetric  {
            type  cml_data_types:CML_INT32_T {
                 range "1..15";
            }
            description "default-metric";
        } // END of defaultMetric definition.

        leaf metricType  {
            type  cml_data_types:CML_RIP_METRIC_T;  
            default "disable";
            description "cisco-metric-behavior";
        } // END of metricType definition.

        leaf defaultDistance  {
            type  cml_data_types:CML_UINT8_T {
                 range "1..255";
            }
            description "distance";
        } // END of defaultDistance definition.

        leaf pcounter  {
            type  cml_data_types:CML_UINT32_T;  
            config false;
        } // END of pcounter definition.

        leaf pconnect  {
            type  cml_data_types:CML_UINT32_T;  
            config false;
        } // END of pconnect definition.

        leaf protocolUpdateDueTime  {
            type  cml_data_types:CML_UINT32_T;  
            config false;
        } // END of protocolUpdateDueTime definition.


        list ripOffsetDistributeListIfname {
             
            description
                "ripOffsetDistributeListIfname";

            config true;
            key "ifName";

            
            leaf ifName  {
                type  cml_data_types:CML_STRING_T {
                    length "0..255";
                }
            } // END of ifName definition.

            uses ripListCmdsUtility;
        } // End of ripOffsetDistributeListIfname-list

        list distanceTable {
             
            description
                "distanceTable";

            config true;
            key "sourceAddr";

            
            leaf sourceAddr  {
                type  cml_data_types:CML_IPV4_PREFIX_T;  
                description "distance";
            } // END of sourceAddr definition.

            leaf distance  {
                mandatory true;
                type  cml_data_types:CML_UINT8_T {
                     range "1..255";
                }
            } // END of distance definition.

            leaf alistVal  {
                mandatory true;
                type  cml_data_types:CML_STRING_T {
                    length "0..255";
                }
            } // END of alistVal definition.

        } // End of distanceTable-list

        list ripInterface {
             
            description
                "RIP specific interface configuration";

            config false;
            key "ifName";

            
            leaf ifName  {
                type  cml_data_types:CML_STRING_T {
                    length "0..255";
                }
            } // END of ifName definition.

            leaf ifFlags  {
                type  cml_data_types:CML_UINT8_T;  
            } // END of ifFlags definition.

            leaf lock  {
                type  cml_data_types:CML_UINT16_T;  
            } // END of lock definition.

            leaf ifAuthMode  {
                type  cml_data_types:CML_RIP_AUTH_MODE_T;  
            } // END of ifAuthMode definition.

            leaf ifAuthStr  {
                type  cml_data_types:CML_STRING_T {
                    length "0..255";
                }
            } // END of ifAuthStr definition.

            leaf ifKeyChain  {
                type  cml_data_types:CML_STRING_T {
                    length "0..255";
                }
            } // END of ifKeyChain definition.

            leaf ifSplitHorizon  {
                type  cml_data_types:CML_RIP_SPLIT_HORIZON_T;  
            } // END of ifSplitHorizon definition.

            leaf ifSendVersionType  {
                type  cml_data_types:CML_RIP_SEND_VERSION_TYPE_T;  
            } // END of ifSendVersionType definition.

            leaf ifRecvVersionType  {
                type  cml_data_types:CML_RIP_RECV_VERSION_TYPE_T;  
            } // END of ifRecvVersionType definition.

            leaf-list ifAccessList  {
                type  cml_data_types:CML_STRING_T {
                    length "0..255";
                }
            } // END of ifAccessList definition.

            leaf-list ifPrefixList  {
                type  cml_data_types:CML_STRING_T {
                    length "0..255";
                }
            } // END of ifPrefixList definition.

            leaf ifAddr  {
                type  cml_data_types:CML_STRING_T {
                    length "0..255";
                }
            } // END of ifAddr definition.

            leaf sentMcastUpdates  {
                type  cml_data_types:CML_UINT32_T;  
            } // END of sentMcastUpdates definition.

            leaf sentMcastRequests  {
                type  cml_data_types:CML_UINT32_T;  
            } // END of sentMcastRequests definition.

            leaf sentUnicastUpdates  {
                type  cml_data_types:CML_UINT32_T;  
            } // END of sentUnicastUpdates definition.

            leaf sentUnicastRequests  {
                type  cml_data_types:CML_UINT32_T;  
            } // END of sentUnicastRequests definition.

            leaf recvMcastUpdates  {
                type  cml_data_types:CML_UINT32_T;  
            } // END of recvMcastUpdates definition.

            leaf recvMcastRequests  {
                type  cml_data_types:CML_UINT32_T;  
            } // END of recvMcastRequests definition.

            leaf recvUnicastUpdates  {
                type  cml_data_types:CML_UINT32_T;  
            } // END of recvUnicastUpdates definition.

            leaf recvUnicastRequests  {
                type  cml_data_types:CML_UINT32_T;  
            } // END of recvUnicastRequests definition.

            leaf recvBadpackets  {
                type  cml_data_types:CML_UINT32_T;  
            } // END of recvBadpackets definition.

            leaf recvBadroutes  {
                type  cml_data_types:CML_UINT32_T;  
            } // END of recvBadroutes definition.

            leaf sentUpdates  {
                type  cml_data_types:CML_UINT32_T;  
            } // END of sentUpdates definition.

        } // End of ripInterface-list

        list ripDatabase {
             
            description
                "RIP routing information base";

            config false;
            key "prefix";

            
            leaf prefix  {
                type  cml_data_types:CML_STRING_T {
                    length "0..255";
                }
            } // END of prefix definition.

            leaf routeType  {
                type  cml_data_types:CML_INT32_T;  
            } // END of routeType definition.

            leaf subType  {
                type  cml_data_types:CML_INT32_T;  
            } // END of subType definition.

            leaf tag  {
                type  cml_data_types:CML_UINT16_T;  
            } // END of tag definition.

            leaf distance  {
                type  cml_data_types:CML_UINT8_T;  
            } // END of distance definition.

            leaf flags  {
                type  cml_data_types:CML_UINT8_T;  
            } // END of flags definition.

            leaf routeCounter  {
                type  cml_data_types:CML_UINT32_T;  
            } // END of routeCounter definition.


            list nexthop {
                 
                description
                    "RIP nexthop";

                config false;
                key "nextHopAddr";

                
                leaf nextHopAddr  {
                    type  cml_data_types:CML_STRING_T {
                        length "0..255";
                    }
                } // END of nextHopAddr definition.

                leaf from  {
                    type  cml_data_types:CML_STRING_T {
                        length "0..255";
                    }
                } // END of from definition.

                leaf ifindex  {
                    type  cml_data_types:CML_UINT32_T;  
                } // END of ifindex definition.

                leaf nexthopFlags  {
                    type  cml_data_types:CML_UINT8_T;  
                } // END of nexthopFlags definition.

                leaf routeMetric  {
                    type  cml_data_types:CML_UINT32_T;  
                } // END of routeMetric definition.

                leaf timeout  {
                    type  cml_data_types:CML_STRING_T {
                        length "0..255";
                    }
                } // END of timeout definition.

                leaf nextHopOut  {
                    type  cml_data_types:CML_STRING_T {
                        length "0..255";
                    }
                } // END of nextHopOut definition.

                leaf metricSet  {
                    type  cml_data_types:CML_UINT8_T;  
                } // END of metricSet definition.

                leaf metricOut  {
                    type  cml_data_types:CML_UINT32_T;  
                } // END of metricOut definition.

                leaf ifindexOut  {
                    type  cml_data_types:CML_UINT32_T;  
                } // END of ifindexOut definition.

                leaf nexthopTimeoutTime  {
                    type  cml_data_types:CML_UINT32_T;  
                } // END of nexthopTimeoutTime definition.

            } // End of nexthop-list
        } // End of ripDatabase-list

        list ripPeer {
             
            description
                "RIP peer table";

            config false;
            key "peerAddr";

            
            leaf peerAddr  {
                type  cml_data_types:CML_STRING_T {
                    length "0..255";
                }
            } // END of peerAddr definition.

            leaf domain  {
                type  cml_data_types:CML_INT32_T;  
            } // END of domain definition.

            leaf uptime  {
                type  cml_data_types:CML_STRING_T {
                    length "0..255";
                }
            } // END of uptime definition.

            leaf ifindex  {
                type  cml_data_types:CML_INT32_T;  
            } // END of ifindex definition.

            leaf peerVersion  {
                type  cml_data_types:CML_UINT8_T;  
            } // END of peerVersion definition.

            leaf peerFlags  {
                type  cml_data_types:CML_UINT8_T;  
            } // END of peerFlags definition.

            leaf recvBadpackets  {
                type  cml_data_types:CML_INT32_T;  
            } // END of recvBadpackets definition.

            leaf recvBadroutes  {
                type  cml_data_types:CML_INT32_T;  
            } // END of recvBadroutes definition.

        } // End of ripPeer-list
        uses ripListCmdsUtility;
    } // END of ripContents definition.
    grouping ripListCmdsUtility {
        
        list offsetList {
             
            description
                "offsetList";

            config true;
            key "directStr";

            
            leaf alistName  {
                mandatory true;
                type  cml_data_types:CML_STRING_T {
                    length "0..255";
                }
                description "offset-list";
            } // END of alistName definition.

            leaf directStr  {
                type  cml_data_types:CML_RIP_DIRECTION_T;  
            } // END of directStr definition.

            leaf metric  {
                mandatory true;
                type  cml_data_types:CML_UINT32_T {
                     range "0..16";
                }
            } // END of metric definition.

        } // End of offsetList-list

        list distributionList {
             
            description
                "distributionList";

            config true;
            key "directionStr";

            
            leaf listName  {
                mandatory true;
                type  cml_data_types:CML_STRING_T {
                    length "0..255";
                }
                description "distribute-list";
            } // END of listName definition.

            leaf directionStr  {
                type  cml_data_types:CML_RIP_DIRECTION_T;  
            } // END of directionStr definition.

        } // End of distributionList-list

        list distributionPrefixList {
             
            description
                "distributionPrefixList";

            config true;
            key "distributeType";

            
            leaf prefixListName  {
                mandatory true;
                type  cml_data_types:CML_STRING_T {
                    length "0..255";
                }
                description "distribute-list";
            } // END of prefixListName definition.

            leaf distributeType  {
                type  cml_data_types:CML_RIP_DIRECTION_T;  
            } // END of distributeType definition.

        } // End of distributionPrefixList-list
    } // END of ripListCmdsUtility definition.

    grouping  ripConfiguration-grouping {
    container ripConfiguration {
                config true;

        description
            "RIP master for system wide configuration and variables";

        leaf gracePeriod  {
            if-feature feature_list:HAVE_RIP_GR_SUPPORT;
            if-feature feature_list:HAVE_RESTART;
            type  cml_data_types:CML_UINT32_T {
                 range "1..65535";
            }
            default "65535";
            description "rip restart grace-period";
        } // END of gracePeriod definition.

        leaf globalQueries  {
            type  cml_data_types:CML_INT32_T;  
            config false;
        } // END of globalQueries definition.

        leaf globalRouteChanges  {
            type  cml_data_types:CML_INT32_T;  
            config false;
        } // END of globalRouteChanges definition.

        leaf debugFlag  {
            type  cml_data_types:CML_RIP_DEBUG_T;  
            description "debug rip";
        } // END of debugFlag definition.


        list ripIntParam {
             
            description
                "RIP interface parameter pool";

            config true;
            key "ifName";

            
            leaf ifName  {
                type  cml_data_types:CML_STRING_T {
                    length "0..255";
                }
            } // END of ifName definition.

            leaf receivePacket  {
                type  cml_data_types:CML_BOOL_T;  
                description "ip rip receive-packet";
            } // END of receivePacket definition.

            leaf sendPacket  {
                type  cml_data_types:CML_BOOL_T;  
                description "ip rip send-packet";
            } // END of sendPacket definition.

            leaf recvVersionType  {
                type  cml_data_types:CML_RIP_RECV_VERSION_TYPE_T;  
                description "ip rip receive version";
            } // END of recvVersionType definition.

            leaf sendVersionType  {
                type  cml_data_types:CML_RIP_SEND_VERSION_TYPE_T;  
                default "1";
                description "ip rip send version";
            } // END of sendVersionType definition.

            leaf authMode  {
                type  cml_data_types:CML_RIP_AUTH_MODE_T;  
                description "ip rip authentication mode";
            } // END of authMode definition.

            leaf authString  {
                type  cml_data_types:CML_STRING_T {
                    length "0..255";
                }
                description "ip rip authentication string";
            } // END of authString definition.

            leaf keyChain  {
                type  cml_data_types:CML_STRING_T {
                    length "0..255";
                }
                description "ip rip authentication key-chain";
            } // END of keyChain definition.

            leaf splitHorizon  {
                type  cml_data_types:CML_RIP_SPLIT_HORIZON_T;  
                description "ip rip split-horizon";
            } // END of splitHorizon definition.

        } // End of ripIntParam-list
        container rip {
            presence "yes"; 
                        config true;

            description
                "RIP Default instance";

            leaf ripDefaultInstance  {
                mandatory true;
                type  cml_data_types:CML_RIP_INSTANCE_T;  
                description "router rip";
            } // END of ripDefaultInstance definition.

            leaf-list passiveifName  {
                type  cml_data_types:CML_STRING_T {
                    length "0..255";
                }
                description "passive-interface";
            } // END of passiveifName definition.

            leaf-list route  {
                type  cml_data_types:CML_IPV4_ADDR_T;  
                description "route";
            } // END of route definition.

            leaf BFDfalloverCheck  {
                if-feature feature_list:HAVE_BFD;
                type  cml_data_types:CML_BOOL_T;  
            } // END of BFDfalloverCheck definition.

            leaf-list bfdNeighborAddr  {
                if-feature feature_list:HAVE_BFD;
                type  cml_data_types:CML_IPV4_ADDR_T;  
            } // END of bfdNeighborAddr definition.

            leaf updateTime  {
                type  cml_data_types:CML_UINT32_T {
                     range "5..2147483647";
                }
                default "30";
            } // END of updateTime definition.

            leaf timeoutTime  {
                type  cml_data_types:CML_UINT32_T {
                     range "5..2147483647";
                }
                default "180";
            } // END of timeoutTime definition.

            leaf garbageTime  {
                type  cml_data_types:CML_UINT32_T {
                     range "5..2147483647";
                }
                default "120";
                description "timers basic";
            } // END of garbageTime definition.

            leaf maxPrefixString  {
                type  cml_data_types:CML_UINT32_T {
                     range "1..65535";
                }
                default "1";
                description "maximum-prefix";
            } // END of maxPrefixString definition.

            leaf thresholdStr  {
                type  cml_data_types:CML_INT32_T {
                     range "1..100";
                }
                default "75";
            } // END of thresholdStr definition.

            leaf recvBufsize  {
                type  cml_data_types:CML_UINT32_T {
                     range "8192..2147483647";
                }
                default "8192";
                description "recv-buffer-size";
            } // END of recvBufsize definition.


            list redistributeMap {
                 
                description
                    "redistributeMap";

                config true;
                key "routeTypeVal";

                
                leaf routeTypeVal  {
                    type  cml_data_types:CML_RIP_REDIST_PROTOS_T;  
                    description "redistribute";
                } // END of routeTypeVal definition.

                leaf metric  {
                    mandatory true;
                    type  cml_data_types:CML_INT32_T {
                         range "0..16";
                    }
                } // END of metric definition.

                leaf routeMap  {
                    mandatory true;
                    type  cml_data_types:CML_STRING_T {
                        length "0..255";
                    }
                } // END of routeMap definition.

            } // End of redistributeMap-list

            list vrfRip {
                                 if-feature feature_list:HAVE_VRF_RIP;

                description
                    "Configure a RIP address family for each VRF configured";

                config true;
                key "vrfName";

                
                leaf vrfName  {
                    type  cml_data_types:CML_STRING_T {
                        length "0..255";
                    }
                } // END of vrfName definition.


                list redistributeMapVRF {
                     
                    description
                        "redistributeMapVRF";

                    config true;
                    key "vrfRouteType";

                    
                    leaf vrfRouteType  {
                        type  cml_data_types:CML_RIP_VRF_REDIST_PROTOS_T;  
                        description "redistribute";
                    } // END of vrfRouteType definition.

                    leaf metric  {
                        mandatory true;
                        type  cml_data_types:CML_INT32_T {
                             range "0..16";
                        }
                    } // END of metric definition.

                    leaf vrfRouteMap  {
                        mandatory true;
                        type  cml_data_types:CML_STRING_T {
                            length "0..255";
                        }
                    } // END of vrfRouteMap definition.

                } // End of redistributeMapVRF-list
                uses ripContents;
            } // End of vrfRip-list
            uses ripContents;
        } // END of rip-container definition.
    } // END of ripConfiguration-container definition.
    } // END of ripConfiguration-container definition.


}
