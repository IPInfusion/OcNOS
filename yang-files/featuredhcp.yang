/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : featuredhcp.yang
*
*/

submodule featuredhcp {

    belongs-to  ZebOS { prefix ZebOS; }


    import cml_data_types {
        prefix cml_data_types;
    }

    description
        "feature_dhcp_configuration";


    revision "2016-12-27" {
        description "Added support for multi module installation.";
    }

    revision "2016-10-28" {
        description "Initial version of featuredhcp datamodel.";
    }


    grouping  featuredhcp-grouping {
    container featuredhcp {
                config true;

        description
            "featuredhcp";

        leaf dhcp  {
            type  cml_data_types:CML_BOOL_T;  
        } // END of dhcp definition.

    } // END of featuredhcp-container definition.
    } // END of featuredhcp-container definition.


}
