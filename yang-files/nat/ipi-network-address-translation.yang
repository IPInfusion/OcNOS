/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-network-address-translation.yang
*
*/

module ipi-network-address-translation {

    yang-version 1.1;

    namespace   "http://www.ipinfusion.com/yang/ocnos/ipi-network-address-translation";

    prefix "ipi-network-address-translation";

    import ietf-inet-types {
        prefix inet;
        revision-date 2013-07-15;
    }

    import ipi-network-address-translation-types {
        prefix ipi-network-address-translation-types;
        revision-date 2022-06-01;
    }

    import feature-list {
        prefix feature-list;
        revision-date 2023-02-21;
    }

    include ipi-network-address-translation-interface { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Network Address Translation.";


    revision "2022-06-01" {
        description "Updated the yang file with feature";
        reference " 0.3.0.";
    }

    revision "2021-10-12" {
        description "Review corrections";
        reference " 0.2.1.";
    }

    revision "2021-08-27" {
        description "Restructured module in accordance with OpenConfig style";
        reference " 0.2.0.";
    }

    revision "2018-06-21" {
        description "Initial Version";
        reference " 0.1.0.";
    }

    grouping nat-protocol-rules-global-address-config {
        description
            "Grouping Network Address Translation Protocol Global Address
                        Configuration";
        leaf address  {
            type  inet:ipv4-address;
            description "Network Address Translation Address global address";
        } // END of address definition.

        leaf global-port  {
            type  uint16 {
                 range "0..65535"  {
                    description "0..65535: Supported range 0 - 65535";
                 }
            }
            mandatory true;
            description "Destination port number";
        } // END of global-port definition.

    } // END of nat-protocol-rules-global-address-config definition.
    grouping nat-protocol-rules-global-address-top {
        description
            "Grouping Network Address Translation Global Address Protocol Rules Top";
        container global-addresses {
            description
                "Network Address Translation Address Global Address";

            list global-address {
            when " /ipi-network-address-translation:network-address-translation/ipi-network-address-translation:ip-rules/ipi-network-address-translation:outgoing/ipi-network-address-translation:protocol-rule-mapping-entries/ipi-network-address-translation:protocol-rule-mapping-entry/ipi-network-address-translation:global-addresses/ipi-network-address-translation:global-address/ipi-network-address-translation:config/ipi-network-address-translation:global-port ";
                key "address";
                description
                    "Network Address Translation Address Global Address";
                leaf address  {
                    type  leafref {
                        path  "../config/address";
                    }
                    description "Network Address Translation global address";
                } // END of address definition.

                container config {
                    description
                        "Network Address Translation Address Global Address configuration";
                    uses nat-protocol-rules-global-address-config;
                } // END of config-container definition.
                container state {
                    config false;
                    description
                        "Network Address Translation Address Global Address state";
                    uses nat-protocol-rules-global-address-config;
                } // END of state-container definition.
            } // End of global-address-list
        } // END of global-addresses-container definition.
    } // END of nat-protocol-rules-global-address-top definition.
    grouping nat-protocol-rules-config {
        description
            "Grouping Network Address Translation IP Protocol Rules Configuration";
        leaf protocol  {
            type  ipi-network-address-translation-types:nat_protocol_t;
            description "Network Address Translation protocol";
        } // END of protocol definition.

        leaf local-address  {
            type  inet:ipv4-address;
            description "Network Address Translation Address local address";
        } // END of local-address definition.

        leaf port  {
            type  uint16 {
                 range "0..65535"  {
                    description "0..65535: Supported range 0 - 65535";
                 }
            }
            description "Network Address Translation Address destination port";
        } // END of port definition.

    } // END of nat-protocol-rules-config definition.
    grouping nat-protocol-rules-top {
        description
            "Grouping Network Address Translation IP Protocol Rules Top";
        container protocol-rule-mapping-entries {
            description
                "Network Address Translation Address IP Protocol Rules";

            list protocol-rule-mapping-entry {
                key "protocol local-address port";
                description
                    "Network Address Translation Address IP Protocol entry";
                leaf protocol  {
                    type  leafref {
                        path  "../config/protocol";
                    }
                    description "Network Address Translation protocol";
                } // END of protocol definition.

                leaf local-address  {
                    type  leafref {
                        path  "../config/local-address";
                    }
                    description "Network Address Translation Address local address";
                } // END of local-address definition.

                leaf port  {
                    type  leafref {
                        path  "../config/port";
                    }
                    description "Network Address Translation Address destination port";
                } // END of port definition.

                container config {
                    description
                        "Network Address Translation Address Destination Protocol configuration";
                    uses nat-protocol-rules-config;
                } // END of config-container definition.
                container state {
                    config false;
                    description
                        "Network Address Translation Address Destination Protocol state";
                    uses nat-protocol-rules-config;
                } // END of state-container definition.
                uses nat-protocol-rules-global-address-top;
            } // End of protocol-rule-mapping-entry-list
        } // END of protocol-rule-mapping-entries-container definition.
    } // END of nat-protocol-rules-top definition.
    grouping nat-ip-rules-config {
        description
            "Grouping Network Address Translation IP Rules Source Configuration";
        leaf local-address  {
            type  inet:ipv4-address;
            description "Network Address Translation Address local address";
        } // END of local-address definition.

        leaf global-address  {
            type  inet:ipv4-address;
            description "Network Address Translation global address";
        } // END of global-address definition.

    } // END of nat-ip-rules-config definition.
    grouping nat-ip-rules-destination-top {
        description
            "Grouping Network Address Translation IP Rules Destination Top";
        container destination-mapping-entries {
            description
                "Network Address Translation Address IP Destination Rules";

            list destination-mapping-entry {
                key "local-address global-address";
                description
                    "Network Address Translation Address IP Destination entry";
                leaf local-address  {
                    type  leafref {
                        path  "../config/local-address";
                    }
                    description "Network Address Translation Address local address";
                } // END of local-address definition.

                leaf global-address  {
                    type  leafref {
                        path  "../config/global-address";
                    }
                    description "Network Address Translation Address global address";
                } // END of global-address definition.

                container config {
                    description
                        "Network Address Translation Address Destination configuration";
                    uses nat-ip-rules-config;
                } // END of config-container definition.
                container state {
                    config false;
                    description
                        "Network Address Translation Address Destination state";
                    uses nat-ip-rules-config;
                } // END of state-container definition.
            } // End of destination-mapping-entry-list
        } // END of destination-mapping-entries-container definition.
    } // END of nat-ip-rules-destination-top definition.
    grouping nat-ip-rules-source-top {
        description
            "Grouping Network Address Translation IP Rules Source Top";
        container source-mapping-entries {
            description
                "Network Address Translation Address IP Source Rules";

            list source-mapping-entry {
                key "local-address global-address";
                description
                    "Network Address Translation Address IP Source Entry";
                leaf local-address  {
                    type  leafref {
                        path  "../config/local-address";
                    }
                    description "Network Address Translation Address local address";
                } // END of local-address definition.

                leaf global-address  {
                    type  leafref {
                        path  "../config/global-address";
                    }
                    description "Network Address Translation Address global address";
                } // END of global-address definition.

                container config {
                    description
                        "Network Address Translation Address Source configuration";
                    uses nat-ip-rules-config;
                } // END of config-container definition.
                container state {
                    config false;
                    description
                        "Network Address Translation Address Source state";
                    uses nat-ip-rules-config;
                } // END of state-container definition.
            } // End of source-mapping-entry-list
        } // END of source-mapping-entries-container definition.
    } // END of nat-ip-rules-source-top definition.
    grouping nat-ip-rules-outgoing-top {
        description
            "Grouping Network Address Translation IP Rules Outgoing Top";
        container outgoing {
            description
                "Network Address Translation Address IP Outgoing Rules";
            uses nat-ip-rules-source-top;
            uses nat-ip-rules-destination-top;
            uses nat-protocol-rules-top;
        } // END of outgoing-container definition.
    } // END of nat-ip-rules-outgoing-top definition.
    grouping nat-ip-rules-incoming-top {
        description
            "Grouping Network Address Translation IP Rules Incoming Top";
        container incoming {
            description
                "Network Address Translation Address IP Incomming Rules";
            uses nat-ip-rules-source-top;
            uses nat-ip-rules-destination-top;
        } // END of incoming-container definition.
    } // END of nat-ip-rules-incoming-top definition.
    grouping nat-ip-rules-top {
        description
            "Grouping Network Address Translation IP Rules";
        container ip-rules {
            description
                "Network Address Translation Address IP Rules";
            uses nat-ip-rules-incoming-top;
            uses nat-ip-rules-outgoing-top;
        } // END of ip-rules-container definition.
    } // END of nat-ip-rules-top definition.
    grouping nat-timeouts-config {
        description
            "Grouping Network Address Translation Timeouts Configuration";
        leaf generic-timeout  {
            type  uint32 {
                 range "0..536870"  {
                    description "0..536870: Supported range 0 - 536870";
                 }
            }
            units "seconds";
            default "0";
            description "Generic time-out for NAT translations";
        } // END of generic-timeout definition.

        leaf icmp-timeout  {
            type  uint32 {
                 range "0..536870"  {
                    description "0..536870: Supported range 0 - 536870";
                 }
            }
            units "seconds";
            default "0";
            description "ICMP timeout for NAT translations";
        } // END of icmp-timeout definition.

        leaf tcp-timeout  {
            type  uint32 {
                 range "0..536870"  {
                    description "0..536870: Supported range 0 - 536870";
                 }
            }
            units "seconds";
            default "0";
            description "TCP timeout for NAT translation";
        } // END of tcp-timeout definition.

        leaf udp-timeout  {
            type  uint32 {
                 range "0..536870"  {
                    description "0..536870: Supported range 0 - 536870";
                 }
            }
            units "seconds";
            default "0";
            description "UDP timeout for NAT translations";
        } // END of udp-timeout definition.

        leaf tcp-fin-timeout  {
            type  uint32 {
                 range "0..536870"  {
                    description "0..536870: Supported range 0 - 536870";
                 }
            }
            units "seconds";
            default "0";
            description "TCP FIN timeout for NAT translations";
        } // END of tcp-fin-timeout definition.

    } // END of nat-timeouts-config definition.
    grouping nat-timeouts-top {
        description
            "Grouping Network Address Translation Timeouts";
        container timeouts {
            description
                "Network Address Translation timeouts";
            container config {
                description
                    "IPV6 Router Advertisement Interface configuration";
                uses nat-timeouts-config;
            } // END of config-container definition.
            container state {
                config false;
                description
                    "IPV6 Router Advertisement Interface state";
                uses nat-timeouts-config;
            } // END of state-container definition.
        } // END of timeouts-container definition.
    } // END of nat-timeouts-top definition.

    grouping  network-address-translation-grouping {
    description
        "Network Address Translation Datamodel";
    container network-address-translation {
        if-feature feature-list:HAVE_NAT;
        if-feature feature-list:HAVE_IMI;
        description
            "Network Address Translation Datamodel";
        uses nat-timeouts-top;
        uses nat-ip-rules-top;
        uses interfaces-grouping;
    } // END of network-address-translation-container definition.
    } // END of network-address-translation-grouping definition.

    uses network-address-translation-grouping;

}
