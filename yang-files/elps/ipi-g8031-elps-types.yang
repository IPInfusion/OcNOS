/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-g8031-elps-types.yang
*
*/

module ipi-g8031-elps-types {

    yang-version 1.1;

    namespace   "http://www.ipinfusion.com/yang/ocnos/ipi-g8031-elps-types";

    prefix "ipi-g8031-elps-types";

    organization
        "IP Infusion Inc.";

    contact
        "Address: 3965 Freedom Circle, Suite 200, Santa Clara, CA 95054
         Phone: +1 408-400-1900
         E-mail: support@ipinfusion.com
         Web: http://www.ip    infusion.com/";

    description
        "YANG version of the ipi-g8031-elps-types";


    revision "2021-05-14" {
        description "Initial Version";
        reference " 0.1.0.";
    }



    typedef  g8031_elps_protection_type_t {
        type enumeration {
            enum one-plus-one-bidirectional {
                value 1;
                description "1+1 bidirectional mode";
            }
            enum one-plus-one-unidirectional {
                value 2;
                description "1+1 unidirectional mode";
            }
            enum one-and-one-bidirectional {
                value 3;
                description "1:1 bidirectional mode";
            }
        }
        description "type definition for G8031_ELPS_PROTECTION_TYPE_T";
    }

}
