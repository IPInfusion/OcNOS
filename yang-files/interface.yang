/*
* Copyright (C) 2016 IP Infusion, Inc. 
*  All Rights Reserved.
*
*** Auto generated by zebmdc

* Unless required by applicable law or agreed to in writing,
* software distributed under the License is distributed on an
* "AS IS" BASIS, WITHOUT WARRANTIES OR CONDITIONS OF ANY
* KIND, either express or implied.

* File name : interface.yang
*
*/

submodule interface {

    belongs-to  ZebOS { prefix ZebOS; }
    include vrf;


    import cml_data_types {
        prefix cml_data_types;
    }

    description
        "Interface";


    revision "2015-10-08" {
        description "Revisied on 2015-10-08.";    }



    grouping interface-grouping {
        list interface {
             

            description
                "interface";

            config true;
            key "ifName";

            
            leaf vrId  {
                mandatory false;                
                type  leafref {
                    path  "/vr/vrId";
                }
            } // END of vrId definition.

            leaf ifName  {
                mandatory true;                
                type  cml_data_types:CML_STRING_T;  
                config true;
            } // END of ifName definition.

            leaf mtu  {
                mandatory false;                
                type  cml_data_types:CML_INT32_T {
                     range "64..65536";
                }
                default "1500";
                config true;
            } // END of mtu definition.

            leaf macAddr  {
                mandatory false;                
                type  cml_data_types:CML_STRING_T;  
                config true;
            } // END of macAddr definition.

            leaf ipAddr  {
                mandatory false;                
                type  cml_data_types:CML_STRING_T;  
                default "NULL";
                config true;
            } // END of ipAddr definition.

            leaf prefixlen  {
                mandatory false;                
                type  cml_data_types:CML_UINT8_T;  
                config true;
            } // END of prefixlen definition.

            leaf ipLabel  {
                mandatory false;                
                type  cml_data_types:CML_STRING_T;  
                default "NULL";
                config true;
            } // END of ipLabel definition.

            leaf vrfName  {
                mandatory false;                
                type  cml_data_types:CML_STRING_T;  
                config true;
            } // END of vrfName definition.

            leaf ipForwarding  {
                mandatory false;                
                type  cml_data_types:CML_STRING_T;  
                config false;
            } // END of ipForwarding definition.

            leaf ipv6Forwarding  {
                mandatory false;                
                type  cml_data_types:CML_STRING_T;  
                config false;
            } // END of ipv6Forwarding definition.

            leaf mauType  {
                mandatory false;                
                type  cml_data_types:CML_MAUTYPE_T;  
                default "dot3MauType0dot0";
                config true;
            } // END of mauType definition.

            leaf duplex  {
                mandatory false;                
                type  cml_data_types:CML_DUPLEX_T;  
                default "auto";
                config true;
            } // END of duplex definition.

            leaf maxBandwidthStr  {
                mandatory false;                
                type  cml_data_types:CML_STRING_T;  
                default "0";
                config true;
            } // END of maxBandwidthStr definition.

            leaf reservableBandwidthStr  {
                mandatory false;                
                type  cml_data_types:CML_STRING_T;  
                default "0";
                config true;
            } // END of reservableBandwidthStr definition.

            leaf adminGrpName  {
                mandatory false;                
                type  cml_data_types:CML_STRING_T;  
                config true;
            } // END of adminGrpName definition.

            leaf bandwidthConstraintMode  {
                mandatory false;                
                type  cml_data_types:CML_STRING_T;  
                config true;
            } // END of bandwidthConstraintMode definition.

            leaf linkStatus  {
                mandatory false;                
                type  cml_data_types:CML_BOOL_T;  
                default false;
                config true;
            } // END of linkStatus definition.

            leaf switchportStatus  {
                mandatory false;                
                type  cml_data_types:CML_BOOL_T;  
                default false;
                config true;
            } // END of switchportStatus definition.

            leaf adminState  {
                mandatory false;                
                type  cml_data_types:CML_BOOL_T;  
                default false;
                config true;
            } // END of adminState definition.

            leaf multicast  {
                mandatory false;                
                type  cml_data_types:CML_BOOL_T;  
                config true;
            } // END of multicast definition.

            leaf labelSwitching  {
                mandatory false;                
                type  cml_data_types:CML_BOOL_T;  
                config true;
            } // END of labelSwitching definition.

            leaf isRunning  {
                mandatory false;                
                type  cml_data_types:CML_STRING_T;  
                config false;
            } // END of isRunning definition.

            leaf rpfType  {
                mandatory false;                
                type  cml_data_types:CML_STRING_T;  
                config false;
            } // END of rpfType definition.

            leaf adminRunState  {
                mandatory false;                
                type  cml_data_types:CML_INTERFACE_ADMIN_STATE_T;  
                config false;
            } // END of adminRunState definition.

            leaf dhcpConfigured  {
                mandatory false;                
                type  cml_data_types:CML_INT32_T;  
                config false;
            } // END of dhcpConfigured definition.

            leaf gmplsType  {
                mandatory false;                
                type  cml_data_types:CML_STRING_T;  
                config false;
            } // END of gmplsType definition.

            leaf vrfId  {
                mandatory false;                
                type  cml_data_types:CML_INT32_T;  
                config false;
            } // END of vrfId definition.

            leaf multipathNum  {
                mandatory false;                
                type  cml_data_types:CML_INT32_T;  
                config false;
            } // END of multipathNum definition.

            leaf routeTotal  {
                mandatory false;                
                type  cml_data_types:CML_UINT32_T;  
                config false;
            } // END of routeTotal definition.

            leaf counterFib  {
                mandatory false;                
                type  cml_data_types:CML_UINT32_T;  
                config false;
            } // END of counterFib definition.

            leaf ip6Addr  {
                mandatory false;                
                type  cml_data_types:CML_STRING_T;  
                config false;
            } // END of ip6Addr definition.

            leaf ingressfilterStatus  {
                mandatory false;                
                type  cml_data_types:CML_STRING_T;  
                config false;
            } // END of ingressfilterStatus definition.

            leaf frameTypes  {
                mandatory false;                
                type  cml_data_types:CML_STRING_T;  
                config false;
            } // END of frameTypes definition.

            leaf nativeVlan  {
                mandatory false;                
                type  cml_data_types:CML_UINT32_T;  
                config false;
            } // END of nativeVlan definition.

            leaf defaultVlan  {
                mandatory false;                
                type  cml_data_types:CML_UINT32_T;  
                config false;
            } // END of defaultVlan definition.

            leaf confVlan  {
                mandatory false;                
                type  cml_data_types:CML_UINT32_T;  
                config false;
            } // END of confVlan definition.

            leaf vId  {
                mandatory false;                
                type  cml_data_types:CML_INT32_T;  
                config false;
            } // END of vId definition.

            leaf transvId  {
                mandatory false;                
                type  cml_data_types:CML_INT32_T;  
                config false;
            } // END of transvId definition.

            leaf hwType  {
                mandatory false;                
                type  cml_data_types:CML_STRING_T;  
                config false;
            } // END of hwType definition.

            leaf hwAddr  {
                mandatory false;                
                type  cml_data_types:CML_STRING_T;  
                config false;
            } // END of hwAddr definition.

            leaf staticFlag  {
                mandatory false;                
                type  cml_data_types:CML_STRING_T;  
                config false;
            } // END of staticFlag definition.

            leaf interfaceDesc  {
                mandatory false;                
                type  cml_data_types:CML_STRING_T;  
                config false;
            } // END of interfaceDesc definition.

            leaf autoNeg  {
                mandatory false;                
                type  cml_data_types:CML_STRING_T;  
                config false;
            } // END of autoNeg definition.

            leaf vrxFlag  {
                mandatory false;                
                type  cml_data_types:CML_STRING_T;  
                config false;
            } // END of vrxFlag definition.

            leaf maxlabelValue  {
                mandatory false;                
                type  cml_data_types:CML_INT32_T;  
                config false;
            } // END of maxlabelValue definition.

            leaf ifoutputErrors  {
                mandatory false;                
                type  cml_data_types:CML_STRING_T;  
                config false;
            } // END of ifoutputErrors definition.

            leaf ifCollisions  {
                mandatory false;                
                type  cml_data_types:CML_STRING_T;  
                config false;
            } // END of ifCollisions definition.

            leaf servString  {
                mandatory false;                
                type  cml_data_types:CML_STRING_T;  
                config false;
            } // END of servString definition.

            leaf vcgroupName  {
                mandatory false;                
                type  cml_data_types:CML_STRING_T;  
                config false;
            } // END of vcgroupName definition.

            leaf bwconstraintMode  {
                mandatory false;                
                type  cml_data_types:CML_STRING_T;  
                config false;
            } // END of bwconstraintMode definition.

            leaf classtypeNumber  {
                mandatory false;                
                type  cml_data_types:CML_STRING_T;  
                config false;
            } // END of classtypeNumber definition.

            leaf teclpriorityBw  {
                mandatory false;                
                type  cml_data_types:CML_STRING_T;  
                config false;
            } // END of teclpriorityBw definition.

            leaf ifinputStats  {
                mandatory false;                
                type  cml_data_types:CML_STRING_T;  
                config false;
            } // END of ifinputStats definition.

            leaf ifoutputStats  {
                mandatory false;                
                type  cml_data_types:CML_STRING_T;  
                config false;
            } // END of ifoutputStats definition.

            leaf ifinputErrors  {
                mandatory false;                
                type  cml_data_types:CML_STRING_T;  
                config false;
            } // END of ifinputErrors definition.

            leaf ifIndex  {
                mandatory false;                
                type  cml_data_types:CML_INT32_T;  
                config false;
            } // END of ifIndex definition.

            leaf ifMetric  {
                mandatory false;                
                type  cml_data_types:CML_INT32_T;  
                config false;
            } // END of ifMetric definition.

            leaf arpageingTimeout  {
                mandatory false;                
                type  cml_data_types:CML_INT32_T;  
                config false;
            } // END of arpageingTimeout definition.

            leaf labelSpace  {
                mandatory false;                
                type  cml_data_types:CML_INT32_T;  
                config false;
            } // END of labelSpace definition.

            leaf minlabelValue  {
                mandatory false;                
                type  cml_data_types:CML_INT32_T;  
                config false;
            } // END of minlabelValue definition.

            leaf fromLabel  {
                mandatory false;                
                type  cml_data_types:CML_STRING_T;  
                config false;
            } // END of fromLabel definition.

            leaf toLabel  {
                mandatory false;                
                type  cml_data_types:CML_STRING_T;  
                config false;
            } // END of toLabel definition.

            leaf vplsName  {
                mandatory false;                
                type  cml_data_types:CML_STRING_T;  
                config false;
            } // END of vplsName definition.

            leaf vcName  {
                mandatory false;                
                type  cml_data_types:CML_STRING_T;  
                config false;
            } // END of vcName definition.

            leaf vcType  {
                mandatory false;                
                type  cml_data_types:CML_STRING_T;  
                config false;
            } // END of vcType definition.

            leaf mplsClassTypeName  {
                mandatory false;                
                type  cml_data_types:CML_STRING_T;  
                config false;
            } // END of mplsClassTypeName definition.

            leaf mplsclasstypeNumber  {
                mandatory false;                
                type  cml_data_types:CML_INT32_T;  
                config false;
            } // END of mplsclasstypeNumber definition.

            leaf mplsPriority  {
                mandatory false;                
                type  cml_data_types:CML_INT32_T;  
                config false;
            } // END of mplsPriority definition.

            leaf mplsteclassId  {
                mandatory false;                
                type  cml_data_types:CML_STRING_T;  
                config false;
            } // END of mplsteclassId definition.

            leaf ifinputPkts  {
                mandatory false;                
                type  cml_data_types:CML_UINT32_T;  
                config false;
            } // END of ifinputPkts definition.

            leaf ifinputOctets  {
                mandatory false;                
                type  cml_data_types:CML_UINT32_T;  
                config false;
            } // END of ifinputOctets definition.

            leaf ifinputDrops  {
                mandatory false;                
                type  cml_data_types:CML_UINT32_T;  
                config false;
            } // END of ifinputDrops definition.

            leaf ifinputmcastPkts  {
                mandatory false;                
                type  cml_data_types:CML_UINT32_T;  
                config false;
            } // END of ifinputmcastPkts definition.

            leaf ifbadCrc  {
                mandatory false;                
                type  cml_data_types:CML_UINT32_T;  
                config false;
            } // END of ifbadCrc definition.

            leaf ifundersizedPkts  {
                mandatory false;                
                type  cml_data_types:CML_UINT32_T;  
                config false;
            } // END of ifundersizedPkts definition.

            leaf ifoutputPkts  {
                mandatory false;                
                type  cml_data_types:CML_UINT32_T;  
                config false;
            } // END of ifoutputPkts definition.

            leaf ifoutputOctets  {
                mandatory false;                
                type  cml_data_types:CML_UINT32_T;  
                config false;
            } // END of ifoutputOctets definition.

            leaf ifoutputDrops  {
                mandatory false;                
                type  cml_data_types:CML_UINT32_T;  
                config false;
            } // END of ifoutputDrops definition.

            leaf ifoutputBcastPkts  {
                mandatory false;                
                type  cml_data_types:CML_UINT32_T;  
                config false;
            } // END of ifoutputBcastPkts definition.

            leaf ifoversizedPkts  {
                mandatory false;                
                type  cml_data_types:CML_UINT32_T;  
                config false;
            } // END of ifoversizedPkts definition.

            leaf ifoutputmcastPkts  {
                mandatory false;                
                type  cml_data_types:CML_UINT32_T;  
                config false;
            } // END of ifoutputmcastPkts definition.


            list secondary {
                 

                description
                    "IPv4 Address";

                config true;
                key "secIpAddr";

                
                leaf secIpAddr  {
                    mandatory true;                    
                    type  cml_data_types:CML_STRING_T;  
                    config true;
                } // END of secIpAddr definition.

                leaf secondaryFlag  {
                    mandatory true;                    
                    type  cml_data_types:CML_BOOL_T;  
                    config true;
                } // END of secondaryFlag definition.

                leaf ipLabel  {
                    mandatory true;                    
                    type  cml_data_types:CML_STRING_T;  
                    config true;
                } // END of ipLabel definition.

            } // End of secondary-list

            list bandwidthConstraint {
                 

                description
                    "set bandwidth constraint";

                config true;
                key "constraintName";

                
                leaf constraintName  {
                    mandatory true;                    
                    type  cml_data_types:CML_STRING_T;  
                    config true;
                } // END of constraintName definition.

                leaf bandwidthStr  {
                    mandatory true;                    
                    type  cml_data_types:CML_STRING_T {
                        length "1..10000000000";
                    }
                    config true;
                } // END of bandwidthStr definition.

            } // End of bandwidthConstraint-list

            list ipv6Addr {
                 

                description
                    "IPv6 Address";

                config true;
                key "ipv6Addr";

                
                leaf ipv6Addr  {
                    mandatory true;                    
                    type  cml_data_types:CML_STRING_T;  
                    config true;
                } // END of ipv6Addr definition.

                leaf anycast  {
                    mandatory true;                    
                    type  cml_data_types:CML_BOOL_T;  
                    config true;
                } // END of anycast definition.

            } // End of ipv6Addr-list

            list ipRouteSummary {
                 

                description
                    "ipRouteSummary";

                config false;
                key "routeType";

                
                leaf routeType  {
                    mandatory true;                    
                    type  cml_data_types:CML_STRING_T;  
                    config false;
                } // END of routeType definition.

                leaf counterType  {
                    mandatory false;                    
                    type  cml_data_types:CML_UINT32_T;  
                    config false;
                } // END of counterType definition.

            } // End of ipRouteSummary-list
        } // End of interface-list
    } // END of interface-grouping definition.


}
