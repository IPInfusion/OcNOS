/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-rib-types.yang
*
*/

module ipi-rib-types {

    yang-version 1.1;

    namespace   "http://www.ipinfusion.com/yang/ocnos/ipi-rib-types";

    prefix "ipi-rib-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-rib-types";


    revision "2022-06-01" {
        description "Updated the yang file with feature";
        reference " 0.7.0.";
    }

    revision "2022-02-14" {
        description "Added new datatye RIB_OBJECT_TRACKING_REACHABILITY_STATUS_T to show object-tracking operational status";
        reference " 0.6.0.";
    }

    revision "2021-09-03" {
        description "Update descriptions of attribute";
        reference " 0.5.0.";
    }

    revision "2021-03-15" {
        description "Removed configuration of Interface name as nexthop for ipv6 mroute commands";
        reference " 0.4.0.";
    }

    revision "2021-01-27" {
        description "Removed 'kernel' debug option";
        reference " 0.3.0.";
    }

    revision "2020-12-15" {
        description "Change to have data-types in lower case instead of camel case";
        reference " 0.2.0.";
    }

    revision "2020-09-07" {
        description "Datamodel restructuring";
        reference " 0.1.0.";
    }



    typedef  rib_fib_retain_t {
        type union {
            type rib_fib_retain_time_t {

            }
            type rib_fib_retain_forever_t {

            }
        }
        description "type definition for RIB_FIB_RETAIN_T";
    }

    typedef  rib_fib_retain_forever_t {
        type enumeration {
            enum forever {
                value 0;
                description "Retain FIB forever";
            }
        }
        description "type definition for RIB_FIB_RETAIN_FOREVER_T";
    }

    typedef  rib_fib_retain_time_t {
        type uint32 {
             range 1..65535;
        }
        description "type definition for RIB_FIB_RETAIN_TIME_T";
    }

    typedef  rib_conf_debug_type_t {
        type bits {
            bit events {
                position 1;
                description "RIB events";
            }
            bit packet-send {
                position 3;
                description "RIB packets,RIB send packets";
            }
            bit packet-recv {
                position 4;
                description "RIB packets,RIB receive packets";
            }
            bit packet-send-detail {
                position 6;
                description "RIB packets,RIB send packets,Detailed information display";
            }
            bit packet-recv-detail {
                position 7;
                description "RIB packets,RIB receive packets,Detailed information display";
            }
            bit ha {
                position 9;
                if-feature feature-list:HAVE_HA;
                description "RIB High Availability";
            }
            bit ha-all {
                position 10;
                if-feature feature-list:HAVE_HA;
                description "RIB High Availability,All RIB High Availability events";
            }
            bit nsm {
                position 11;
                description "NSM messages";
            }
            bit bfd {
                position 12;
                if-feature feature-list:HAVE_BFD;
                description "BFD messages";
            }
            bit monitor {
                position 13;
                if-feature feature-list:NOT_PNE_VERSION_3_7;
                if-feature feature-list:NOT_PNE_VERSION_6_9;
                description "Enable Monitor route netlink";
            }
            bit hal-events {
                position 18;
                if-feature feature-list:HAVE_HAL;
                if-feature feature-list:NOT_HAVE_SWFWDR;
                description "Hardware Abstraction Layer,RIB events";
            }
        }
        description "type definition for RIB_CONF_DEBUG_TYPE_T";
    }

    typedef  rib_debug_type_t {
        type bits {
            bit events {
                position 1;
                description "RIB events";
            }
            bit packet-send {
                position 3;
                description "RIB packets,RIB send packets";
            }
            bit packet-recv {
                position 4;
                description "RIB packets,RIB receive packets";
            }
            bit packet-send-detail {
                position 6;
                description "RIB packets,RIB send packets,Detailed information display";
            }
            bit packet-recv-detail {
                position 7;
                description "RIB packets,RIB receive packets,Detailed information display";
            }
            bit ha {
                position 9;
                if-feature feature-list:HAVE_HA;
                description "RIB High Availability";
            }
            bit ha-all {
                position 10;
                if-feature feature-list:HAVE_HA;
                description "RIB High Availability,All RIB High Availability events";
            }
            bit nsm {
                position 11;
                description "NSM messages";
            }
            bit bfd {
                position 12;
                if-feature feature-list:HAVE_BFD;
                description "BFD messages";
            }
            bit monitor {
                position 13;
                if-feature feature-list:NOT_PNE_VERSION_3_7;
                if-feature feature-list:NOT_PNE_VERSION_6_9;
                description "Enable Monitor route netlink";
            }
            bit hal-events {
                position 18;
                if-feature feature-list:HAVE_HAL;
                if-feature feature-list:NOT_HAVE_SWFWDR;
                description "Hardware Abstraction Layer,RIB events";
            }
            bit hal-ipc {
                position 19;
                if-feature feature-list:HAVE_HAL;
                if-feature feature-list:HAVE_ASYNC;
                description "Hardware Abstraction Layer,Async Debugging";
            }
        }
        description "type definition for RIB_DEBUG_TYPE_T";
    }

    typedef  rib_debug_routing_type_t {
        type bits {
            bit routing-add-route {
                position 21;
                description "Enable debugging for routing events,Add route events";
            }
            bit routing-delete-route {
                position 22;
                description "Enable debugging for routing events, Delete route events";
            }
            bit routing-mod-route {
                position 23;
                description "Enable debugging for routing events, Modify route events";
            }
        }
        description "type definition for RIB_DEBUG_ROUTING_TYPE_T";
    }

    typedef  rib_bfd_state {
        type enumeration {
            enum enable {
                value 0;
                description "enable BFD";
            }
            enum disable {
                value 1;
                description "disable BFD";
            }
        }
        description "type definition for RIB_BFD_STATE";
    }

    typedef  rib_mroute_route_type_t {
        type enumeration {
            enum default {
                value 0;
                description "Default route type";
            }
            enum static {
                value 3;
                description "Static routes";
            }
            enum rip {
                value 4;
                description "Routing Information Protocol (RIP)";
            }
            enum ospf {
                value 6;
                description "Open Shortest Patch First (OSPF)";
            }
            enum bgp {
                value 8;
                description "Border Gateway Protocol (BGP)";
            }
            enum isis {
                value 9;
                description "ISO IS-IS";
            }
        }
        description "type definition for RIB_MROUTE_ROUTE_TYPE_T";
    }

    typedef  rib_mroute_ipv6_route_type_t {
        type enumeration {
            enum default {
                value 0;
                description "Default route type";
            }
            enum static {
                value 3;
                description "Static routes";
            }
            enum rip {
                value 5;
                description "Routing Information Protocol (RIP)";
            }
            enum ospf {
                value 7;
                description "Open Shortest Patch First (OSPF)";
            }
            enum bgp {
                value 8;
                description "Border Gateway Protocol (BGP)";
            }
            enum isis {
                value 9;
                description "ISO IS-IS";
            }
        }
        description "type definition for RIB_MROUTE_IPV6_ROUTE_TYPE_T";
    }

    typedef  rib_static_bfd_enable_disable_t {
        type enumeration {
            enum disable {
                value 0;
                description "Override global bfd enable";
            }
            enum enable {
                value 1;
                description "Enable static fall-over bfd";
            }
        }
        description "type definition for RIB_STATIC_BFD_ENABLE_DISABLE_T";
    }

    typedef  rib_route_type_t {
        type enumeration {
            enum kernel {
                value 1;
                description "Kernel routes";
            }
            enum connected {
                value 2;
                description "Connected";
            }
            enum static {
                value 3;
                description "Static routes";
            }
            enum rip {
                value 4;
                description "Routing Information Protocol (RIP)";
            }
            enum ripng {
                value 5;
                description "Routing Information Protocol (RIP)";
            }
            enum ospf {
                value 6;
                description "Open Shortest Path First (OSPF)";
            }
            enum ospf6 {
                value 7;
                description "Open Shortest Path First (OSPF)";
            }
            enum bgp {
                value 8;
                description "Border Gateway Protocol (BGP)";
            }
            enum isis {
                value 9;
                description "ISO IS-IS";
            }
        }
        description "type definition for RIB_ROUTE_TYPE_T";
    }

    typedef  rib_route_sub_type_t {
        type enumeration {
            enum IA {
                value 1;
                description "OSPF IA";
            }
            enum NI {
                value 2;
                description "OSPF NSSA 1";
            }
            enum N2 {
                value 3;
                description "OSPF NSSA 2";
            }
            enum E1 {
                value 4;
                description "OSPF EXTERNAL 1";
            }
            enum E2 {
                value 5;
                description "OSPF EXTERNAL 2";
            }
            enum L1 {
                value 8;
                description "ISIS L1";
            }
            enum L2 {
                value 9;
                description "ISIS L2";
            }
            enum ia {
                value 10;
                description "ISIS IA";
            }
        }
        description "type definition for RIB_ROUTE_SUB_TYPE_T";
    }

    typedef  rib_object_tracking_reachability_status_t {
        type enumeration {
            enum down {
                value 0;
                description "object tracking reachability status is down";
            }
            enum up {
                value 1;
                description "object tracking reachability status is up";
            }
        }
        description "type definition for RIB_OBJECT_TRACKING_REACHABILITY_STATUS_T";
    }

}
