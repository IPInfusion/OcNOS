/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : switchportinterface.yang
*
*/

submodule switchportinterface {

    belongs-to  ZebOS { prefix ZebOS; }
    include interface;
    include vlan;
    include bridge;


    import cml_data_types {
        prefix cml_data_types;
    }

    import feature_list {
        prefix feature_list;
    }

    description
        "switchport configuration";


    revision "2017-03-03" {
        description "vlaninterface datamodel has been changed to switchportinterface.";
    }

    revision "2017-02-25" {
        description "added support for show cml running-config.";
    }

    revision "2017-02-14" {
        description "adding missing flag for cli generation.";
    }

    revision "2017-02-10" {
        description "modified customer-edge commands.";
    }

    revision "2017-01-27" {
        description "added support for l2protocol commands.";
    }



    grouping switchportInterface-grouping {
        list switchportInterface {
             
            description
                "switchportInterface";

            config true;
            key "ifName";

            
            leaf vrId  {
                type  cml_data_types:CML_INT32_T;  
                default "0";
            } // END of vrId definition.

            leaf ifName  {
                type  cml_data_types:CML_STRING_T {
                    length "0..255";
                }
            } // END of ifName definition.

            leaf switchPortMode  {
                mandatory true;
                type  cml_data_types:CML_VLAN_PORT_MODE_T;  
            } // END of switchPortMode definition.

            leaf vlanAddExcept  {
                type  cml_data_types:CML_VLAN_EXCEPT_T;  
            } // END of vlanAddExcept definition.

            leaf vlanId  {
                type  cml_data_types:CML_UINT16_T {
                     range "2..4094";
                }
                description "switchport (access|hybrid|native trunk)";
            } // END of vlanId definition.

            leaf nativeVlanId  {
                type  cml_data_types:CML_UINT16_T {
                     range "2..4094";
                }
                description "switchport trunk native";
            } // END of nativeVlanId definition.

            leaf allowedVlanRange  {
                type  cml_data_types:CML_STRING_T;  
                description "switchport (access|hybrid|native trunk)";
            } // END of allowedVlanRange definition.

            leaf exceptVlanRange  {
                type  cml_data_types:CML_STRING_T;  
                description "switchport (access|hybrid|native trunk)";
            } // END of exceptVlanRange definition.

            leaf customerEdgeType  {
                type  cml_data_types:CML_VLAN_PORT_MODE_T;  
            } // END of customerEdgeType definition.

            leaf edgeVlanType  {
                type  cml_data_types:CML_EDGE_VLAN_TYPE_T;  
            } // END of edgeVlanType definition.

            leaf vlanOperType  {
                type  cml_data_types:CML_VLAN_OPER_TYPE_T;  
            } // END of vlanOperType definition.

            leaf cvlanRegWord  {
                type  cml_data_types:CML_STRING_T {
                    length "0..255";
                }
            } // END of cvlanRegWord definition.

            leaf edgevlanId  {
                type  cml_data_types:CML_UINT16_T;  
            } // END of edgevlanId definition.

            leaf-list transVlanId  {
                type  cml_data_types:CML_UINT16_T;  
            } // END of transVlanId definition.

            leaf edgevlanIdRange  {
                type  cml_data_types:CML_STRING_T;  
            } // END of edgevlanIdRange definition.

            leaf egressTagged  {
                type  cml_data_types:CML_EGERSS_TAGGED_TYPE_T;  
            } // END of egressTagged definition.

            leaf edgeSvlan  {
                type  cml_data_types:CML_UINT16_T;  
            } // END of edgeSvlan definition.

            leaf allowedVlan  {
                type  cml_data_types:CML_ALLOWEDVLAN_T;  
            } // END of allowedVlan definition.

            leaf egrType  {
                type  cml_data_types:CML_EGERSS_TAGGED_TYPE_T;  
            } // END of egrType definition.

            leaf vlanPbrPortMode  {
                type  cml_data_types:CML_UINT8_T;  
            } // END of vlanPbrPortMode definition.

            leaf vlanPortIngressFilter  {
                type  cml_data_types:CML_ENABLE_DISABLE_T;  
                default "enable";
                description "switchport mode hybrid ingress-filter";
            } // END of vlanPortIngressFilter definition.

            leaf frameType  {
                type  cml_data_types:CML_VLAN_FRAME_TYPE_T;  
                default "all";
                description "switchport mode hybrid acceptable-frame-type";
            } // END of frameType definition.


            list staticMac {
                 
                description
                    "staticMac";

                config true;
                key "macAddr";

                
                leaf vlanIdMac  {
                    type  cml_data_types:CML_UINT16_T;  
                } // END of vlanIdMac definition.

                leaf svlanId  {
                    type  cml_data_types:CML_UINT16_T {
                         range "2..4094";
                    }
                } // END of svlanId definition.

                leaf bridgeId  {
                    type  cml_data_types:CML_STRING_T {
                        length "1..32";
                    }
                    description "mac Address";
                } // END of bridgeId definition.

                leaf macAddr  {
                    type  cml_data_types:CML_STRING_T {
                        length "0..255";
                    }
                    description "mac Address";
                } // END of macAddr definition.

                leaf discardForward  {
                    type  cml_data_types:CML_DISCARDFORWARD_T;  
                } // END of discardForward definition.

                leaf priorityOverWrite  {
                    type  cml_data_types:CML_UINT8_T {
                         range "0..7";
                    }
                } // END of priorityOverWrite definition.

                leaf overMacType  {
                    type  cml_data_types:CML_OVERMACTYPE_T;  
                } // END of overMacType definition.

            } // End of staticMac-list

            list vlanUserTable {
                 
                description
                    "vlanUserTable";

                config true;
                key "userPriority";

                
                leaf userPriority  {
                    type  cml_data_types:CML_UINT8_T {
                         range "0..7";
                    }
                } // END of userPriority definition.

                leaf regenPriority  {
                    mandatory true;
                    type  cml_data_types:CML_UINT8_T {
                         range "0..7";
                    }
                } // END of regenPriority definition.

            } // End of vlanUserTable-list

            list vlanTraffic {
                 
                description
                    "vlanTraffic";

                config true;
                key "userPriority";

                
                leaf userPriority  {
                    type  cml_data_types:CML_UINT8_T {
                         range "0..7";
                    }
                } // END of userPriority definition.

                leaf trafficClass  {
                    type  cml_data_types:CML_UINT8_T {
                         range "1..8";
                    }
                } // END of trafficClass definition.

                leaf trafficClassValue  {
                    mandatory true;
                    type  cml_data_types:CML_UINT8_T {
                         range "0..7";
                    }
                } // END of trafficClassValue definition.

            } // End of vlanTraffic-list
        } // End of switchportInterface-list
    } // END of switchportInterface-grouping definition.


    grouping macAddressTable-grouping {
        list macAddressTable {
             
            description
                "macAddressTable";

            config true;
            key "macTable";

            
            leaf macTable  {
                type  cml_data_types:CML_INT32_T;  
            } // END of macTable definition.

            leaf bridgeId  {
                type  cml_data_types:CML_STRING_T {
                    length "1..32";
                }
                description "mac Address";
            } // END of bridgeId definition.

            leaf macLimit  {
                type  cml_data_types:CML_INT32_T;  
            } // END of macLimit definition.

            leaf macLimitRange  {
                type  cml_data_types:CML_INT32_T {
                     range "5..32768";
                }
            } // END of macLimitRange definition.

            leaf vlanRange  {
                type  cml_data_types:CML_STRING_T {
                    length "0..255";
                }
                description "bridge instance vlan";
            } // END of vlanRange definition.

            leaf macLearn  {
                type  cml_data_types:CML_INT32_T;  
                default "0";
            } // END of macLearn definition.

        } // End of macAddressTable-list
    } // END of macAddressTable-grouping definition.


    grouping vlanStacking-grouping {
        list vlanStacking {
             
            description
                "vlanStacking";

            config true;
            key "ifName";

            
            leaf ifName  {
                type  cml_data_types:CML_STRING_T {
                    length "0..255";
                }
            } // END of ifName definition.

            leaf vlanStackEnable  {
                type  cml_data_types:CML_VLANSTACK_T;  
            } // END of vlanStackEnable definition.

            leaf etherType  {
                type  cml_data_types:CML_STRING_T {
                    length "0..255";
                }
                default "0x8100";
            } // END of etherType definition.

        } // End of vlanStacking-list
    } // END of vlanStacking-grouping definition.


    grouping l2protocol-grouping {
        list l2protocol {
                         if-feature feature_list:HAVE_PROVIDER_BRIDGE;

            description
                "l2protocol";

            config true;
            key "ifName";

            
            leaf ifName  {
                type  cml_data_types:CML_STRING_T {
                    length "0..255";
                }
            } // END of ifName definition.

            leaf l2protocolType  {
                type  cml_data_types:CML_L2_PROTOCOL_T;  
            } // END of l2protocolType definition.

            leaf l2discardprotocolType  {
                type  cml_data_types:CML_DISCARD_L2_PROTOCOL_T;  
            } // END of l2discardprotocolType definition.

            leaf discard  {
                type  cml_data_types:CML_BOOL_T;  
            } // END of discard definition.

            leaf peer  {
                type  cml_data_types:CML_BOOL_T;  
            } // END of peer definition.

            leaf tunnelVlan  {
                type  cml_data_types:CML_INT32_T;  
            } // END of tunnelVlan definition.

        } // End of l2protocol-list
    } // END of l2protocol-grouping definition.


}
