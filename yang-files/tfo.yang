/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : tfo.yang
*
*/

submodule tfo {

    belongs-to  ZebOS { prefix ZebOS; }
    include interface;


    import cml_data_types {
        prefix cml_data_types;
    }

    import feature_list {
        prefix feature_list;
    }

    description
        "tfo_configuration";


    revision "2016-12-27" {
        description "Added snmp oid and documentation tag.";
    }

    revision "2016-10-28" {
        description "Initial version of TFO datamodel.";
    }


    grouping  tfo-grouping {
    container tfo {
                config true;

        description
            "tfo";

        leaf tfostate  {
            if-feature feature_list:HAVE_TFO;
            type  cml_data_types:CML_ENABLE_DISABLE_T;  
            description "TFO";
        } // END of tfostate definition.


        list fog_id {
                         if-feature feature_list:HAVE_TFO;

            description
                "structure list will be list of struct fog_info";

            config true;
            key "fogid";

            
            leaf fogid  {
                type  cml_data_types:CML_UINT32_T {
                     range "1..64";
                }
                description "FOG tfc";
            } // END of fogid definition.

            leaf fogen  {
                mandatory true;
                type  cml_data_types:CML_ENABLE_DISABLE_T;  
                description "FOG status";
            } // END of fogen definition.

            leaf tfc  {
                if-feature feature_list:HAVE_TFO;
                type  cml_data_types:CML_UINT32_T {
                     range "0..63";
                }
                description "fog tfc";
            } // END of tfc definition.

            leaf mpg_link_failure_cnt  {
                type  cml_data_types:CML_INT64_T;  
                config false;
                description "MPG Failure detection count";
            } // END of mpg_link_failure_cnt definition.

            leaf mpg_link_recover_cnt  {
                type  cml_data_types:CML_INT64_T;  
                config false;
                description "MPG link recover count";
            } // END of mpg_link_recover_cnt definition.

            leaf cpg_auto_disable_cnt  {
                type  cml_data_types:CML_INT64_T;  
                config false;
                description "CPG Auto Disable Count";
            } // END of cpg_auto_disable_cnt definition.

            leaf cpg_auto_enable_cnt  {
                type  cml_data_types:CML_INT64_T;  
                config false;
                description "CPG auto enable count";
            } // END of cpg_auto_enable_cnt definition.

            leaf cpg_disable_status  {
                type  cml_data_types:CML_INT64_T;  
                config false;
                description "To track CPG status";
            } // END of cpg_disable_status definition.

            leaf mpg_disable_status  {
                type  cml_data_types:CML_INT64_T;  
                config false;
                description "To track MPG status";
            } // END of mpg_disable_status definition.

        } // End of fog_id-list

        list tfo_interface {
                         if-feature feature_list:HAVE_TFO;

            description
                "structure list will be list of strict interface. which will point MPG links and CPG links";

            config true;
            key "ifName";

            
            leaf ifName  {
                type  cml_data_types:CML_STRING_T {
                    length "0..255";
                }
            } // END of ifName definition.

            leaf fog  {
                type  cml_data_types:CML_UINT32_T {
                     range "1..64";
                }
            } // END of fog definition.

            leaf fog_type  {
                type  cml_data_types:CML_FOG_IFCTYPE_T;  
                description "fog type";
            } // END of fog_type definition.

            leaf link_type  {
                type  cml_data_types:CML_FOG_LINK_TYPE_T;  
                description "link type";
            } // END of link_type definition.

        } // End of tfo_interface-list
    } // END of tfo-container definition.
    } // END of tfo-container definition.


}
