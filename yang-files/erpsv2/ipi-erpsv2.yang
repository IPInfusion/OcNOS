/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-erpsv2.yang
*
*/

module ipi-erpsv2 {

    yang-version 1.1;

    namespace   "http://www.ipinfusion.com/yang/ocnos/ipi-erpsv2";

    prefix "ipi-erpsv2";

    import ietf-yang-types {
        prefix yang;
        revision-date 2013-07-15;
    }

    import cml-data-types {
        prefix cml-data-types;
        revision-date 2022-09-30;
    }

    import ipi-erpsv2-types {
        prefix ipi-erpsv2-types;
        revision-date 2022-06-28;
    }

    import ipi-interface {
        prefix ipi-interface;
        revision-date 2022-08-24;
    }

    import ipi-network-instance {
        prefix ipi-network-instance;
        revision-date 2022-06-01;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module describes configuration and operational data model for
                ITU.T G.8032 Ethernet Ring Protocol (ERP)";

    reference "Rec. ITU-T G.8032/Y.1344 (08/2015)";

    revision "2022-06-28" {
        description "Changed validation of when tag on virtual-channel";
        reference " 0.7.0.";
    }

    revision "2022-06-06" {
        description "Added when tag to erp-instance on tcn-propagation, non-virtual-channel, virtual-channel and rpl";
        reference " 0.6.0.";
    }

    revision "2022-06-01" {
        description "Updated the yang file with feature";
        reference " 0.5.0.";
    }

    revision "2022-04-19" {
        description "Added debug support for g8032";
        reference " 0.4.0.";
    }

    revision "2022-03-09" {
        description "Range replaced by length in RPCs";
        reference " 0.3.0.";
    }

    revision "2022-02-09" {
        description "Restructured module in accordance with OpenConfig style";
        reference " 0.2.0.";
    }

    revision "2022-02-08" {
        description "Initial Version";
        reference " 0.1.0.";
    }

    grouping erpsv2-physical-ring-config {
        description
            "Grouping for ERPSv2 physical ring configuration data";
        leaf ring-name  {
            type  string {
                length "1..255";
                pattern "[^?' =,>|]+";
            }
            description "G.8032 ring name. This attribue uniquely identifies a ring on the
                        network device.";
        } // END of ring-name definition.

        leaf bridge-id  {
            when " /ipi-network-instance:network-instances/ipi-network-instance:network-instance/ipi-network-instance:instance-type = 'l2ni' ";
            type  leafref {
                path  "/ipi-network-instance:network-instances/ipi-network-instance:network-instance/ipi-network-instance:instance-name";
            }
            mandatory true;
            description "Network Instance Name";
        } // END of bridge-id definition.

        leaf east-interface  {
            type  leafref {
                path  "/ipi-interface:interfaces/ipi-interface:interface/ipi-interface:name";
            }
            description "East port associated to the protection ring";
        } // END of east-interface definition.

        leaf west-interface  {
            when " ../east-interface ";
            type  leafref {
                path  "/ipi-interface:interfaces/ipi-interface:interface/ipi-interface:name";
            }
            description "West port associated to the protection ring";
        } // END of west-interface definition.

        leaf description  {
            type  cml-data-types:cml_line_t {
                length "1..255";
            }
            description "Textual description of the ring.";
        } // END of description definition.

    } // END of erpsv2-physical-ring-config definition.
    grouping erpsv2-physical-ring-top {
        description
            "Grouping for ERPSv2 physical Ring";
        container physical-rings {
            description
                "Container for ERPSv2 physical-rings";

            list physical-ring {
                key "ring-name";
                description
                    "List of ERPSv2 physical-ring";
                leaf ring-name  {
                    type  leafref {
                        path  "../config/ring-name";
                    }
                    description "G.8032 ring name. This attribue uniquely identifies a ring on the
                                network device.";
                } // END of ring-name definition.

                container config {
                    description
                        "Configuration data for erpsv2 physical ring";
                    uses erpsv2-physical-ring-config;
                } // END of config-container definition.
                container state {
                    config false;
                    description
                        "Operational state data for erpsv2 physical ring";
                    uses erpsv2-physical-ring-config;
                } // END of state-container definition.
            } // End of physical-ring-list
        } // END of physical-rings-container definition.
    } // END of erpsv2-physical-ring-top definition.
    grouping erpsv2-profile-config {
        description
            "Grouping for ERPSv2 profile configuration data";
        leaf profile-name  {
            type  string {
                length "1..32";
                pattern "[^?' =,>|]+";
            }
            description "G.8032 ring profile name";
        } // END of profile-name definition.

        leaf bridge-id  {
            when " /ipi-network-instance:network-instances/ipi-network-instance:network-instance/ipi-network-instance:instance-type = 'l2ni' ";
            type  leafref {
                path  "/ipi-network-instance:network-instances/ipi-network-instance:network-instance/ipi-network-instance:instance-name";
            }
            mandatory true;
            description "Network Instance Name";
        } // END of bridge-id definition.

        leaf wait-to-restore-timer  {
            type  uint8 {
                 range "1..12"  {
                    description "1..12: Supported range 1 - 12";
                 }
            }
            units "minutes";
            default "5";
            description "In revertive mode the 'wait to restore' (WTR) timer
                        is used to prevent frequent operation of the
                        protection switching due to intermittent signal
                        failure defects.
                        When recovering from a Signal fail, the delay timer
                        must be long enough to allow the recovering network to
                        become stable.
                        WTR timer is activated on RPL owner node. When WTR
                        timer is expired RPL owner node initiates the
                        reversion process by transmitting an R-APS (NR, RB)
                        message.";
        } // END of wait-to-restore-timer definition.

        leaf hold-off-timer  {
            type  uint16 {
                 range "0..10000"  {
                    description "0..10000: Supported range 0 - 10000";
                 }
            }
            units "milliseconds";
            default "0";
            description "The hold-off timer is used to coordinate the timing of
                        protection switches.
                        When a new defect or more severe defect occurs
                        (new SF), this event is not to be reported immediately
                        to protection switching if the provisioned hold-off
                        timer value is non-zero. Instead, the hold-off timer
                        is started. When the hold-off timer expires, the trail
                        that started the timer is checked as to whether a
                        defect still exists. If one does exist, that defect is
                        reported to protection switching.
                        Hold off timer values SHOULD be specified in multiple of
                        100.";
        } // END of hold-off-timer definition.

        leaf guard-timer  {
            type  uint16 {
                 range "10..2000"  {
                    description "10..2000: Supported range 10 - 2000";
                 }
            }
            units "milliseconds";
            default "500";
            description "The guard timer is used to prevent Ethernet ring nodes
                        from acting upon outdated R-APS messages and prevents
                        the possibility of forming a closed loop.
                        This timer period SHOULD be greater than the maximum
                        expected forwarding delay in which an R-APS message
                        traverses the entire ring.
                        The period of the guard timer MAY be configured by the
                        operator in 10 ms steps between 10 ms and 2 seconds.";
        } // END of guard-timer definition.

        leaf protection-mode  {
            type  ipi-erpsv2-types:erpsv2_protection_mode_t;
            default "revertive";
            description "This leaf defines G.8032 ring protection mode. A ring
                        may operate in revertive or non-revertive mode.
                        In revertive operation, after the condition(s) causing a
                        switch has cleared, the traffic channel is restored to
                        the working transport entity, i.e., blocked on the RPL.
                        In non-revertive operation, the traffic channel
                        continues to use the RPL, if it has not failed, after a
                        switch condition has cleared.";
        } // END of protection-mode definition.

    } // END of erpsv2-profile-config definition.
    grouping erpsv2-profile-state {
        description
            "Grouping for ERPSv2 profile operational state data";
        leaf wait-to-block-time  {
            type  uint32;
            units "milliseconds";
            description "The time period the RPL owner node waits efore reverting the
                        protection state to idle state when fault is recovered in the ring";
        } // END of wait-to-block-time definition.

    } // END of erpsv2-profile-state definition.
    grouping erpsv2-profiles-top {
        description
            "Grouping for ERPSv2 profile";
        container profiles {
            description
                "Container for erpsv2 profiles";

            list profile {
                key "profile-name";
                description
                    "List of erpsv2 profile";
                leaf profile-name  {
                    type  leafref {
                        path  "../config/profile-name";
                    }
                    description "G.8032 ring profile name";
                } // END of profile-name definition.

                container config {
                    description
                        "Configuration data for erpsv2 profile";
                    uses erpsv2-profile-config;
                } // END of config-container definition.
                container state {
                    config false;
                    description
                        "Operational state data for erpsv2 profile";
                    uses erpsv2-profile-config;
                    uses erpsv2-profile-state;
                } // END of state-container definition.
            } // End of profile-list
        } // END of profiles-container definition.
    } // END of erpsv2-profiles-top definition.
    grouping erpsv2-instance-config {
        description
            "Grouping for ERPSv2 instance configuration data";
        leaf name  {
            type  string {
                length "1..255";
                pattern "[^?' =,>|]+";
            }
            description "ERPS instance identifier";
        } // END of name definition.

        leaf bridge-id  {
            when " /ipi-network-instance:network-instances/ipi-network-instance:network-instance/ipi-network-instance:instance-type = 'l2ni' ";
            type  leafref {
                path  "/ipi-network-instance:network-instances/ipi-network-instance:network-instance/ipi-network-instance:instance-name";
            }
            mandatory true;
            description "Network Instance Name";
        } // END of bridge-id definition.

        leaf mapped-profile-name  {
            type  leafref {
                path  "/erpsv2/profiles/profile/profile-name";
            }
            description "G.8032 ring profile name. If this profile exists
                        in the profile configuration list, profile
                        parameters will be imported from it, default
                        values will be used otherwise.";
        } // END of mapped-profile-name definition.

        leaf ring-type  {
            type  ipi-erpsv2-types:erpsv2_ring_type_t;
            default "major-ring";
            description "Defines type of a ethernet ring. A ring can be configured as major
                        ring where ring nodes are connected in closed loop or as a sub-ring
                        when a ring may not have a complete closed loop";
        } // END of ring-type definition.

        leaf physical-ring-name  {
            type  leafref {
                path  "/erpsv2/physical-rings/physical-ring/ring-name";
            }
            description "This parameter specifies the physical ring instance to associated with
                        the ERPS instance";
        } // END of physical-ring-name definition.

        leaf raps-channel-vlan  {
            when " ../physical-ring-name ";
            type  uint16 {
                 range "2..4094"  {
                    description "2..4094: Supported range 2 - 4094";
                 }
            }
            description "Ring wide control vlan-id used by ERPS instance to send and recieve
                        the RAPS messages in the ring";
        } // END of raps-channel-vlan definition.

        leaf data-traffic-vlan  {
            when " ../raps-channel-vlan ";
            type  cml-data-types:cml_range_t;
            description "List of VLAN-IDs, protected by ring instance. For
                        example '2, 3-7, 9, 10-100'
                        VLAN-IDs MUST not overlap with VLAN-IDs of any other
                        instance of the same physical ring.";
        } // END of data-traffic-vlan definition.

        leaf level  {
            type  uint8 {
                 range "0..7"  {
                    description "0..7: Supported range 0 - 7";
                 }
            }
            description "Maintainance Endpoint Level (MEL) at which R-APS
                        PDU is transmitted.All nodes in the ring must be
                        configured with same APS level value.";
        } // END of level definition.

        leaf ring-id  {
            type  uint8 {
                 range "1..239"  {
                    description "1..239: Supported range 1 - 239";
                 }
            }
            description "G.8032 ring instance identifier (Ring ID).";
        } // END of ring-id definition.

        leaf enable-tcn-propagation  {
            when " ../ring-type='sub-ring' and ../physical-ring-name ";
            type  empty;
            description "Allows topology change notification (TCN) propagation to the ERPS ring
                        if it is enabled";
        } // END of enable-tcn-propagation definition.

        leaf-list tcn-to-instances  {
            when " ../enable-tcn-propagation and ../non-virtual-channel ";
            type  string {
                length "1..255";
                pattern "[^?' =,>|]+";
            }
            description "List of Instance that are to be notified when TCN occurs for this
                        instance if topology change notification (TCN) propagation is enabled";
        } // END of tcn-to-instances definition.

        leaf non-virtual-channel  {
            when " ../ring-type='sub-ring' and ../physical-ring-name ";
            type  empty;
            description "Creates a non-virtual channel";
        } // END of non-virtual-channel definition.

        leaf description  {
            type  cml-data-types:cml_line_t {
                length "1..255";
            }
            description "Textual description of the erps-instance.";
        } // END of description definition.

    } // END of erpsv2-instance-config definition.
    grouping erpsv2-instance-state {
        description
            "Grouping for erpsv2-instances-state operational state data";
        leaf current-state  {
            type  ipi-erpsv2-types:erpsv2_ring_state_t;
            description "The current state of the ERPS instance";
        } // END of current-state definition.

    } // END of erpsv2-instance-state definition.
    grouping erpsv2-instance-previous-state {
        description
            "Grouping for erp-instance notifcation state data";
        leaf previous-state  {
            type  ipi-erpsv2-types:erpsv2_ring_state_t;
            description "The previous state of the ERPS instance";
        } // END of previous-state definition.

    } // END of erpsv2-instance-previous-state definition.
    grouping erpsv2-instance-role-config {
        description
            "Grouping for ERPSv2 instance role configuration data";
        choice role-option {
            description
                "RPL role option";
            case owner {

                description
                    "Represents owner node in the ring.";

                leaf owner-port-id  {
                    type  ipi-erpsv2-types:erpsv2_port_id_t;
                    description "This identifies the ring port for which role is configured";
                } // END of owner-port-id definition.

            }
            case neighbor {

                description
                    "Represents neighbor node in the ring.";

                leaf neighbor-port-id  {
                    type  ipi-erpsv2-types:erpsv2_port_id_t;
                    description "This identifies the ring port for which role is configured";
                } // END of neighbor-port-id definition.

            }
            case next-neighbor {

                description
                    "Represents owner node in the ring.";

                leaf next-neighbor-port-id  {
                    type  ipi-erpsv2-types:erpsv2_port_id_t;
                    description "This identifies the ring port for which role is configured";
                } // END of next-neighbor-port-id definition.

            }
            case non-owner {

                description
                    "Represents normal node in the ring.";

                leaf non-owner  {
                    type  empty;
                    description "This identifies the ring port for which role is configured";
                } // END of non-owner definition.

            }
        } // END of role-option-choice definition.
    } // END of erpsv2-instance-role-config definition.
    grouping erpsv2-instance-role-top {
        description
            "Grouping for ERPSv2 instance role";
        container instance-role {
            description
                "Container for instance-role";
            container config {
                description
                    "Configuration data for erpsv2-instance-role";
                uses erpsv2-instance-role-config;
            } // END of config-container definition.
            container state {
                config false;
                description
                    "Operational state data for erpsv2-instance-role";
                uses erpsv2-instance-role-config;
            } // END of state-container definition.
        } // END of instance-role-container definition.
    } // END of erpsv2-instance-role-top definition.
    grouping erpsv2-virtual-channel-config {
        description
            "Grouping for ERPSv2 instance virtual channel configuration data";
        leaf channel-id  {
            type  uint16 {
                 range "2..4094"  {
                    description "2..4094: Supported range 2 - 4094";
                 }
            }
            mandatory true;
            description "Ring wide vlan-id used by ERPS instance to send and receive RAPS
                        message in the subring, by allowing the RAPS messages of the sub-ring
                        to flow through the major ring";
        } // END of channel-id definition.

        leaf attached-instance  {
            type  leafref {
                path  "/erpsv2/erp-instances/erp-instance/name";
            }
            mandatory true;
            description "This parameter specifies the ERPS instance on major ring which allows
                        the RAPS messages of Sub-ring, so RAPS message will be sent to other
                        nodes in the sub-ring";
        } // END of attached-instance definition.

    } // END of erpsv2-virtual-channel-config definition.
    grouping erpsv2-virtual-channel-top {
        description
            "Grouping for ERPSv2 instance virtual channel";
        container virtual-channel {
            when " ../config/ring-type='sub-ring' ";
            description
                "Container for virtual-channel";
            container config {
                presence "yes";
                description
                    "Configuration data for erpsv2-virtual-channel";
                uses erpsv2-virtual-channel-config;
            } // END of config-container definition.
            container state {
                config false;
                description
                    "Operational state data for erpsv2-virtual-channel";
                uses erpsv2-virtual-channel-config;
            } // END of state-container definition.
        } // END of virtual-channel-container definition.
    } // END of erpsv2-virtual-channel-top definition.
    grouping erpsv2-link-state {
        description
            "Grouping for ERPSv2 link operational state data";
        leaf link-name  {
            type  string {
                length "1..33";
                pattern "[^?' =,>|]+";
            }
            description "Name of West port associated with the ERPS instance";
        } // END of link-name definition.

        leaf link-state  {
            type  ipi-erpsv2-types:erpsv2_link_state_t;
            description "This parameter indicates the state of the west port associated with
                        the ERPS instance";
        } // END of link-state definition.

        leaf remote-node-id  {
            type  cml-data-types:cml_mac_addr_t {
                length "1..1965";
            }
            description "Node ID of the last R-APS message received over the ring port. During
                        initialization this value is set to 00:00:00:00:00:00 by ERP control
                        process.";
        } // END of remote-node-id definition.

        leaf remote-blocked-port-reference  {
            type  uint8 {
                 range "0..1"  {
                    description "0..1: Supported range 0 - 1";
                 }
            }
            description "Blocked port reference (BPR) of the last R-APS message received over
                        the ring port. During initialization this value is set to 0 by ERP
                        control process.";
        } // END of remote-blocked-port-reference definition.

    } // END of erpsv2-link-state definition.
    grouping erpsv2-east-link-top {
        description
            "Grouping for ERPSv2 east link";
        container east-link {
            description
                "Container for erpsv2 east link state";
            container state {
                config false;
                description
                    "Operational state data for erpsv2 east link";
                uses erpsv2-link-state;
            } // END of state-container definition.
        } // END of east-link-container definition.
    } // END of erpsv2-east-link-top definition.
    grouping erpsv2-west-link-top {
        description
            "Grouping for ERPSv2 west link";
        container west-link {
            description
                "Container for erpsv2 west link state";
            container state {
                config false;
                description
                    "Operational state data for erpsv2 west link";
                uses erpsv2-link-state;
            } // END of state-container definition.
        } // END of west-link-container definition.
    } // END of erpsv2-west-link-top definition.
    grouping erpsv2-raps-statistics-state {
        description
            "Grouping for ERPSv2 RAPS statistics operational state data";
        leaf tx-raps  {
            type  yang:counter32;
            description "Number of R-APS messages transmitted";
        } // END of tx-raps definition.

        leaf rx-raps  {
            type  yang:counter32;
            description "Number of R-APS messages received";
        } // END of rx-raps definition.

    } // END of erpsv2-raps-statistics-state definition.
    grouping erpsv2-raps-statistics-top {
        description
            "Grouping for ERPSv2 RAPS statistics";
        container raps-statistics {
            description
                "Container for raps-statistics";
            container state {
                config false;
                description
                    "Operational state data for raps-statistics";
                uses erpsv2-raps-statistics-state;
            } // END of state-container definition.
        } // END of raps-statistics-container definition.
    } // END of erpsv2-raps-statistics-top definition.
    grouping erpsv2-instance-top {
        description
            "Grouping for ERPSv2 instance";
        container erp-instances {
            description
                "Container for erpsv2 instances";

            list erp-instance {
                key "name";
                description
                    "List of erpsv2 instance";
                leaf name  {
                    type  leafref {
                        path  "../config/name";
                    }
                    description "ERPS instance identifier";
                } // END of name definition.

                container config {
                    description
                        "Configuration data for erpsv2 instance";
                    uses erpsv2-instance-config;
                } // END of config-container definition.
                container state {
                    config false;
                    description
                        "Operational state data for";
                    uses erpsv2-instance-config;
                    uses erpsv2-instance-state;
                    uses erpsv2-instance-previous-state;
                } // END of state-container definition.
                uses erpsv2-instance-role-top;
                uses erpsv2-virtual-channel-top;
                uses erpsv2-east-link-top;
                uses erpsv2-west-link-top;
                uses erpsv2-raps-statistics-top;
            } // End of erp-instance-list
        } // END of erp-instances-container definition.
    } // END of erpsv2-instance-top definition.
    grouping erpsv2-debug-config {
        description
            "G8032 ERPSv2 debug configuration attributes";
        leaf debug-options  {
            type  ipi-erpsv2-types:erpsv2_debug_t;
            description "Supported debug options for g8032";
        } // END of debug-options definition.

    } // END of erpsv2-debug-config definition.
    grouping erpsv2-debug-terminal-top {
        description
            "G8032 ERPSv2 debug state attributes";
        container terminal {
            config false;
            description
                "Container for g8032 debugging functions";
            uses erpsv2-debug-config;
        } // END of terminal-container definition.
    } // END of erpsv2-debug-terminal-top definition.
    grouping erpsv2-debug-top {
        description
            "Grouping for g8032 debug";
        container debug {
            description
                "Container for g8032 debugging functions";
            container config {
                description
                    "Configuration data for g8032 debug";
                uses erpsv2-debug-config;
            } // END of config-container definition.
            container state {
                config false;
                description
                    "Operational state data for g8032 debug";
                uses erpsv2-debug-config;
                uses erpsv2-debug-terminal-top;
            } // END of state-container definition.
        } // END of debug-container definition.
    } // END of erpsv2-debug-top definition.

    grouping  erpsv2-grouping {
    description
        "Container for ERPSv2 module";
    container erpsv2 {
        if-feature feature-list:HAVE_G8032V2;
        if-feature feature-list:HAVE_ONMD;
        description
            "Container for ERPSv2 module";
        uses erpsv2-physical-ring-top;
        uses erpsv2-profiles-top;
        uses erpsv2-instance-top;
        uses erpsv2-debug-top;
    } // END of erpsv2-container definition.
    } // END of erpsv2-grouping definition.

    uses erpsv2-grouping;

    rpc erpsv2-switch-erp-instance {
        if-feature feature-list:HAVE_G8032V2;
        if-feature feature-list:HAVE_ONMD;
        description "Perform administrative action on the ring (instance).";
        input  {
            leaf instance-name  {
                type string {
                    length "1..255";
                }
                mandatory true;
                description "ERPS instance identifier";
            }
            leaf bridge-id  {
                type string {
                    length "1..128";
                }
                mandatory true;
                description "Network Instance Name";
            }
            leaf operation  {
                type ipi-erpsv2-types:erpsv2_switch_operation_t;
                mandatory true;
                description "G.8032 administrative operation types.";
            }
            leaf port-id  {
                type ipi-erpsv2-types:erpsv2_port_id_t;
                mandatory true;
                description "Ring port to perform switch operation.";
            }
        }
    }

    rpc erpsv2-clear-ring-erp-instance {
        if-feature feature-list:HAVE_G8032V2;
        if-feature feature-list:HAVE_ONMD;
        description "Clear an existing Forced-Switch (FS) or Manual-Switch (MS) condition
                    on the ring port.";
        input  {
            leaf instance-name  {
                type string {
                    length "1..255";
                }
                mandatory true;
                description "ERPS instance identifier";
            }
            leaf bridge-id  {
                type string {
                    length "1..128";
                }
                mandatory true;
                description "Network Instance Name";
            }
        }
    }

    rpc erpsv2-clear-aps-statistics {
        if-feature feature-list:HAVE_G8032V2;
        if-feature feature-list:HAVE_ONMD;
        description "Clear APS statistics";
        input  {
            leaf instance-name  {
                type string {
                    length "1..255";
                }
                mandatory true;
                description "ERPS instance identifier";
            }
            leaf bridge-id  {
                type string {
                    length "1..128";
                }
                mandatory true;
                description "Network Instance Name";
            }
        }
    }

    rpc erpsv2-terminal-debug-on {
        if-feature feature-list:HAVE_G8032V2;
        if-feature feature-list:HAVE_ONMD;
        description "Enable g8032 debugging functions";
        input  {
            leaf debug-options  {
                type ipi-erpsv2-types:erpsv2_debug_t;
                mandatory true;
                description "Use this attribute to debug g8032 feature.";
            }
        }
    }

    rpc erpsv2-terminal-debug-off {
        if-feature feature-list:HAVE_G8032V2;
        if-feature feature-list:HAVE_ONMD;
        description "Disable g8032 debugging functions";
        input  {
            leaf debug-options  {
                type ipi-erpsv2-types:erpsv2_debug_t;
                mandatory true;
                description "Use this attribute to debug g8032 feature.";
            }
        }
    }

    notification erpsv2-instance-state-change-notification {
        if-feature feature-list:HAVE_G8032V2;
        if-feature feature-list:HAVE_ONMD;

        description "This notification indicates state change of the instance per the G.8032 state machine.";

        leaf severity {
            type cml-data-types:cml_notif_severity_t;
            description "Notification severity level (value: INFO)";
        }

        leaf eventClass {
            type cml-data-types:cml_notif_class_t;
            description "Notification event class (value: STATE)";
        }

        leaf name {
            type  string;
        description
            "ERPS instance identifier";
        }

        leaf bridge-id {
            type  string;
        description
            "Network Instance Name";
        }

        leaf current-state {
            type ipi-erpsv2-types:erpsv2_ring_state_t;
        description
            "The current state of the ERPS instance";
        }

        leaf previous-state {
            type ipi-erpsv2-types:erpsv2_ring_state_t;
        description
            "The previous state of the ERPS instance";
        }
    }

}
