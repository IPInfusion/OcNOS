/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-trill.yang
*
*/

submodule ipi-zebos-trill {

    belongs-to  ipi-zebos { prefix ipi-zebos; }

    import cml-data-types {
        prefix cml-data-types;
    }

    import feature-list {
        prefix feature-list;
    }

    organization
        "IP Infusion Inc.";

    contact
        "Address: 3965 Freedom Circle, Suite 200, Santa Clara, CA 95054
        Phone: +1 408-400-1900
        E-mail: support@ipinfusion.com
        Web: http://www.ipinfusion.com/";

    description
        "trill configuration";


    revision "2018-06-21" {
        description " Initial Version.";
        reference "";
    }



    grouping trill-grouping {
    description
        "trill";
        list trill {
            if-feature feature-list:HAVE_TRILLD;
            key "tag";
            description
                "trill";
            leaf tag  {
                type  cml-data-types:CML_STRING_T;
                description "";
            } // END of tag definition.

            leaf bridgeId  {
                type  cml-data-types:CML_STRING_T;
                description "";
            } // END of bridgeId definition.

            leaf instanceId  {
                type  cml-data-types:CML_UINT32_T;
                description "";
            } // END of instanceId definition.

            leaf systemId  {
                type  cml-data-types:CML_STRING_T;
                description "";
            } // END of systemId definition.

            leaf isType  {
                type  cml-data-types:CML_UINT8_T;
                description "";
            } // END of isType definition.

            leaf protoType  {
                type  cml-data-types:CML_UINT8_T;
                description "";
            } // END of protoType definition.

            leaf flags  {
                type  cml-data-types:CML_UINT8_T;
                description "";
            } // END of flags definition.

            leaf configflags  {
                type  cml-data-types:CML_ESADI_T;
                description "";
            } // END of configflags definition.

            leaf ignorLspErr  {
                type  cml-data-types:CML_UINT8_T;
                description "";
            } // END of ignorLspErr definition.

            leaf lspGenErr  {
                type  cml-data-types:CML_UINT8_T {
                     range "1..120";
                }
                description "";
            } // END of lspGenErr definition.

            leaf mcastpruning  {
                type  cml-data-types:CML_BOOL_T;
                description "";
            } // END of mcastpruning definition.

            leaf vlanpruning  {
                type  cml-data-types:CML_TRILL_T;
                description "";
            } // END of vlanpruning definition.

            leaf loadshareflag  {
                type  cml-data-types:CML_TRILL_T;
                description "";
            } // END of loadshareflag definition.

            leaf mtuProbe  {
                type  cml-data-types:CML_BOOL_T;
                description "";
            } // END of mtuProbe definition.

            leaf channelprotocol  {
                if-feature feature-list:HAVE_TRILL_OAM;
                type  cml-data-types:CML_BOOL_T;
                description "";
            } // END of channelprotocol definition.

            leaf oamprotocol  {
                if-feature feature-list:HAVE_TRILL_OAM;
                type  cml-data-types:CML_BOOL_T;
                description "";
            } // END of oamprotocol definition.

            leaf acceptNonAdj  {
                type  cml-data-types:CML_BOOL_T;
                description "";
            } // END of acceptNonAdj definition.

            leaf isunicast  {
                type  cml-data-types:CML_ISUNICAST_T;
                description "";
            } // END of isunicast definition.

            leaf maxAreaAddrs  {
                type  cml-data-types:CML_UINT8_T;
                description "";
            } // END of maxAreaAddrs definition.

            leaf lspRefreshInterval  {
                type  cml-data-types:CML_UINT16_T {
                     range "1..65535";
                }
                description "";
            } // END of lspRefreshInterval definition.

            leaf maxLspLifetime  {
                type  cml-data-types:CML_UINT16_T {
                     range "350..65535";
                }
                description "";
            } // END of maxLspLifetime definition.

            leaf forwardDelay  {
                type  cml-data-types:CML_UINT32_T;
                description "";
            } // END of forwardDelay definition.

            leaf confidenceLocalRecvd  {
                type  cml-data-types:CML_UINT8_T;
                description "";
            } // END of confidenceLocalRecvd definition.

            leaf confidenceRemoteRecvd  {
                type  cml-data-types:CML_UINT8_T;
                description "";
            } // END of confidenceRemoteRecvd definition.

            leaf confidenceStaticConfig  {
                type  cml-data-types:CML_UINT8_T;
                description "";
            } // END of confidenceStaticConfig definition.

            leaf interRbMtu  {
                type  cml-data-types:CML_UINT16_T;
                description "";
            } // END of interRbMtu definition.

            leaf dtreeConfig  {
                type  cml-data-types:CML_UINT16_T;
                description "";
            } // END of dtreeConfig definition.

            leaf numOfDtreesToCompute  {
                type  cml-data-types:CML_UINT16_T {
                     range "1..8";
                }
                description "";
            } // END of numOfDtreesToCompute definition.

            leaf maxDtrees  {
                type  cml-data-types:CML_UINT16_T;
                description "";
            } // END of maxDtrees definition.

            leaf numDtreeToUse  {
                type  cml-data-types:CML_UINT16_T {
                     range "0..8";
                }
                description "";
            } // END of numDtreeToUse definition.

            leaf numInstalledSelfNicknames  {
                type  cml-data-types:CML_UINT16_T;
                description "";
            } // END of numInstalledSelfNicknames definition.

            leaf dtreenickname  {
                type  cml-data-types:CML_STRING_T;
                description "";
            } // END of dtreenickname definition.

            leaf dtreestouse  {
                type  cml-data-types:CML_STRING_T;
                description "";
            } // END of dtreestouse definition.

            leaf campuswidemtu  {
                type  cml-data-types:CML_UINT32_T {
                     range "1470..65535";
                }
                default "1470";
                description "";
            } // END of campuswidemtu definition.

            leaf minimummtu  {
                type  cml-data-types:CML_UINT16_T;
                config false;
                description "";
            } // END of minimummtu definition.

            leaf mtuprobes  {
                type  cml-data-types:CML_UINT16_T {
                     range "1..255";
                }
                description "";
            } // END of mtuprobes definition.

            leaf fwddelay  {
                type  cml-data-types:CML_UINT16_T {
                     range "4..30";
                }
                description "";
            } // END of fwddelay definition.

            leaf confidenceType  {
                type  cml-data-types:CML_CONFIDENCETYPE_T;
                description "";
            } // END of confidenceType definition.

            leaf confidenceVal  {
                type  cml-data-types:CML_UINT16_T {
                     range "0..255";
                }
                description "";
            } // END of confidenceVal definition.

            leaf maxnickname  {
                type  cml-data-types:CML_UINT16_T {
                     range "1..256";
                }
                description "";
            } // END of maxnickname definition.

            leaf echoReqInterval  {
                if-feature feature-list:HAVE_TRILL_OAM;
                type  cml-data-types:CML_UINT32_T;
                description "";
            } // END of echoReqInterval definition.

            leaf echoreqtimeout  {
                if-feature feature-list:HAVE_TRILL_OAM;
                type  cml-data-types:CML_UINT16_T;
                description "";
            } // END of echoreqtimeout definition.

            leaf defaultdtree  {
                type  cml-data-types:CML_UINT16_T;
                description "";
            } // END of defaultdtree definition.

            leaf pingprobe  {
                if-feature feature-list:HAVE_TRILL_OAM;
                type  cml-data-types:CML_STRING_T;
                description "";
            } // END of pingprobe definition.


            list selfnickname {
                key "name";
                description
                    "List of nicknames Auto generated and user configured ";
                leaf nicknamepriority  {
                    type  cml-data-types:CML_UINT16_T {
                         range "128..255";
                    }
                    description "";
                } // END of nicknamepriority definition.

                leaf status  {
                    type  cml-data-types:CML_STRING_T;
                    config false;
                    description "";
                } // END of status definition.

                leaf systemidnick  {
                    type  cml-data-types:CML_STRING_T;
                    description "";
                } // END of systemidnick definition.

                leaf name  {
                    type  cml-data-types:CML_STRING_T;
                    description "";
                } // END of name definition.

                leaf rootppriority  {
                    type  cml-data-types:CML_UINT16_T {
                         range "0..65535";
                    }
                    description "";
                } // END of rootppriority definition.

                leaf installed  {
                    type  cml-data-types:CML_UINT16_T;
                    description "";
                } // END of installed definition.

            } // End of selfnickname-list
            container trillProto {
                description
                    "Information per protocol";
                leaf pindex  {
                    type  cml-data-types:CML_UINT8_T;
                    description "";
                } // END of pindex definition.


                list staticdtree {
                    key "dtreename";
                    description
                        "Table for tuple of dtree nickname - nexthop nickname - vlanid range";
                    leaf dtreename  {
                        type  cml-data-types:CML_STRING_T;
                        description "";
                    } // END of dtreename definition.

                    leaf nbrname  {
                        type  cml-data-types:CML_STRING_T;
                        description "";
                    } // END of nbrname definition.

                    leaf startVlan  {
                        type  cml-data-types:CML_UINT16_T {
                             range "1..4094";
                        }
                        description "";
                    } // END of startVlan definition.

                    leaf endVlan  {
                        type  cml-data-types:CML_UINT16_T {
                             range "1..4094";
                        }
                        description "";
                    } // END of endVlan definition.

                } // End of staticdtree-list

                list staticrpfentry {
                    key "rpfdtreename";
                    description
                        "Static RPF Table";
                    leaf rpfdtreename  {
                        type  cml-data-types:CML_STRING_T;
                        description "";
                    } // END of rpfdtreename definition.

                    leaf ingressname  {
                        type  cml-data-types:CML_STRING_T;
                        description "";
                    } // END of ingressname definition.

                    leaf ifName  {
                        type  cml-data-types:CML_STRING_T;
                        description "";
                    } // END of ifName definition.

                } // End of staticrpfentry-list

                list stmcastprune {
                    key "dtreenck";
                    description
                        "Static Multicast prune Table";
                    leaf dtreenck  {
                        type  cml-data-types:CML_STRING_T;
                        description "";
                    } // END of dtreenck definition.

                    leaf prunenbrname  {
                        type  cml-data-types:CML_STRING_T;
                        description "";
                    } // END of prunenbrname definition.

                    leaf vlanId  {
                        type  cml-data-types:CML_UINT16_T {
                             range "1..4094";
                        }
                        description "";
                    } // END of vlanId definition.

                    leaf macAddr  {
                        type  cml-data-types:CML_STRING_T;
                        description "";
                    } // END of macAddr definition.

                } // End of stmcastprune-list
                container urt {
                    description
                        "Unicast Route tables";
                    uses lsTable;
                } // END of urt-container definition.
                container dmactable {
                    description
                        "DMAC table for tuple of {dmac - vlan - egress nickname}";
                    uses lsTable;
                } // END of dmactable-container definition.
                container staticNhopnick {
                    description
                        "Table for tuple of {nexthop nickname - interface - nexthop mac address}";
                    uses lsTable;
                } // END of staticNhopnick-container definition.
            } // END of trillProto-container definition.
            container level {
                description
                    " Level context";
                leaf indexlevel  {
                    type  cml-data-types:CML_UINT8_T;
                    description "";
                } // END of indexlevel definition.

                leaf flagsLevel  {
                    type  cml-data-types:CML_UINT8_T;
                    description "";
                } // END of flagsLevel definition.

                leaf configsLevel  {
                    type  cml-data-types:CML_UINT8_T;
                    description "";
                } // END of configsLevel definition.

                leaf lspgeninterval  {
                    type  cml-data-types:CML_UINT8_T;
                    description "";
                } // END of lspgeninterval definition.

                leaf lspBufsize  {
                    type  cml-data-types:CML_UINT16_T;
                    description "";
                } // END of lspBufsize definition.

                leaf metricstyle  {
                    type  cml-data-types:CML_UINT16_T;
                    description "";
                } // END of metricstyle definition.

                leaf topologyType  {
                    type  cml-data-types:CML_UINT16_T;
                    description "";
                } // END of topologyType definition.

                leaf pruneflags  {
                    type  cml-data-types:CML_UINT8_T;
                    description "";
                } // END of pruneflags definition.

                leaf corruptedlsps  {
                    type  cml-data-types:CML_UINT32_T;
                    description "";
                } // END of corruptedlsps definition.

                leaf lspdboverloaded  {
                    type  cml-data-types:CML_UINT32_T;
                    description "";
                } // END of lspdboverloaded definition.

                leaf manaddrdroparea  {
                    type  cml-data-types:CML_UINT32_T;
                    description "";
                } // END of manaddrdroparea definition.

                leaf exceedmaxseqnums  {
                    type  cml-data-types:CML_UINT32_T;
                    description "";
                } // END of exceedmaxseqnums definition.

                leaf eqnumskips  {
                    type  cml-data-types:CML_UINT32_T;
                    description "";
                } // END of eqnumskips definition.

                leaf lsppurges  {
                    type  cml-data-types:CML_UINT32_T;
                    description "";
                } // END of lsppurges definition.

                leaf idlenmismatches  {
                    type  cml-data-types:CML_UINT32_T;
                    description "";
                } // END of idlenmismatches definition.

                leaf spfcalccount  {
                    type  cml-data-types:CML_UINT32_T;
                    description "";
                } // END of spfcalccount definition.

                container spfMinMaxDelay {
                    description
                        "SPF minimum maximum delay time";
                    leaf spfmindelay  {
                        type  cml-data-types:CML_UINT32_T {
                             range "1..2147483647";
                        }
                        description "";
                    } // END of spfmindelay definition.

                    leaf spfmaxdelay  {
                        type  cml-data-types:CML_UINT32_T {
                             range "1..2147483647";
                        }
                        description "";
                    } // END of spfmaxdelay definition.

                } // END of spfMinMaxDelay-container definition.
                container lspdb {
                    description
                        "LSPDB.";
                    uses lsTable;
                } // END of lspdb-container definition.
                container dtroutetable {
                    config false;
                    description
                        "Dtree route table";
                    leaf egname  {
                        type  cml-data-types:CML_UINT16_T;
                        description "";
                    } // END of egname definition.

                    leaf ingnickname  {
                        type  cml-data-types:CML_UINT16_T;
                        description "";
                    } // END of ingnickname definition.

                    leaf ifindex  {
                        type  cml-data-types:CML_UINT16_T;
                        description "";
                    } // END of ifindex definition.

                    leaf ifName  {
                        type  cml-data-types:CML_STRING_T;
                        description "";
                    } // END of ifName definition.

                    uses lsTable;
                } // END of dtroutetable-container definition.
                container proto {
                    description
                        "LSP update timestamp.";
                    leaf pindex  {
                        type  cml-data-types:CML_UINT8_T;
                        description "";
                    } // END of pindex definition.

                    leaf flagsproto  {
                        type  cml-data-types:CML_UINT8_T;
                        description "";
                    } // END of flagsproto definition.

                    leaf maxecmppath  {
                        type  cml-data-types:CML_UINT16_T {
                             range "1..100";
                        }
                        description "";
                    } // END of maxecmppath definition.

                    leaf origdtree  {
                        type  cml-data-types:CML_UINT8_T;
                        description "";
                    } // END of origdtree definition.

                } // END of proto-container definition.
                container tvspf {
                    description
                        "LSP update timestamp.";
                    leaf tvsec  {
                        type  cml-data-types:CML_STRING_T;
                        description "";
                    } // END of tvsec definition.

                    leaf tvusec  {
                        type  cml-data-types:CML_UINT32_T;
                        description "";
                    } // END of tvusec definition.

                } // END of tvspf-container definition.
                container tvspfcurr {
                    description
                        "Current SPF calculation";
                    leaf tvsec  {
                        type  cml-data-types:CML_STRING_T;
                        description "";
                    } // END of tvsec definition.

                    leaf tvusec  {
                        type  cml-data-types:CML_UINT32_T;
                        description "";
                    } // END of tvusec definition.

                } // END of tvspfcurr-container definition.
                container tvdtreecurr {
                    description
                        "Current Dtree calculation";
                    leaf tvsec  {
                        type  cml-data-types:CML_UINT32_T;
                        description "";
                    } // END of tvsec definition.

                    leaf tvusec  {
                        type  cml-data-types:CML_UINT32_T;
                        description "";
                    } // END of tvusec definition.

                } // END of tvdtreecurr-container definition.
                container tvpruncurr {
                    description
                        "Current pruning calculation.";
                    leaf tvsec  {
                        type  cml-data-types:CML_STRING_T;
                        description "";
                    } // END of tvsec definition.

                    leaf tvusec  {
                        type  cml-data-types:CML_UINT32_T;
                        description "";
                    } // END of tvusec definition.

                } // END of tvpruncurr-container definition.
                container dtreecalc {
                    description
                        "trill dtree calc";
                    leaf numdtreestocomputedtree  {
                        type  cml-data-types:CML_UINT16_T;
                        description "";
                    } // END of numdtreestocomputedtree definition.

                    leaf numdtreescomputeddtree  {
                        type  cml-data-types:CML_UINT16_T;
                        description "";
                    } // END of numdtreescomputeddtree definition.

                } // END of dtreecalc-container definition.
                container prunncalc {
                    description
                        "Multicast and VLAN prunning Thread";
                    leaf nextvectorindex  {
                        type  cml-data-types:CML_UINT16_T;
                        description "";
                    } // END of nextvectorindex definition.

                    container tvstartprunning {
                        description
                            "Prunning start time";
                        leaf tvsec  {
                            type  cml-data-types:CML_UINT32_T;
                            description "";
                        } // END of tvsec definition.

                        leaf tvusec  {
                            type  cml-data-types:CML_UINT32_T;
                            description "";
                        } // END of tvusec definition.

                    } // END of tvstartprunning-container definition.
                } // END of prunncalc-container definition.
            } // END of level-container definition.
            container nickdatabase {
                config false;
                description
                    "List of campus-wide nicknames  {struct trill_nickname}";
                leaf nicknamedbpriority  {
                    type  cml-data-types:CML_UINT16_T;
                    description "";
                } // END of nicknamedbpriority definition.

                leaf statusdb  {
                    type  cml-data-types:CML_UINT8_T;
                    description "";
                } // END of statusdb definition.

                leaf systemiddbnick  {
                    type  cml-data-types:CML_STRING_T;
                    description "";
                } // END of systemiddbnick definition.

                leaf dbname  {
                    type  cml-data-types:CML_STRING_T;
                    description "";
                } // END of dbname definition.

                leaf rootdbppriority  {
                    type  cml-data-types:CML_UINT16_T;
                    description "";
                } // END of rootdbppriority definition.

                uses lsTable;
            } // END of nickdatabase-container definition.
            container l2mcasttable {
                config false;
                description
                    "List of snooped multicast address  {struct trill_l2mcast}";
                leaf mcastVlanId  {
                    type  cml-data-types:CML_UINT16_T;
                    description "";
                } // END of mcastVlanId definition.

                leaf mcastMac  {
                    type  cml-data-types:CML_UINT32_T;
                    description "";
                } // END of mcastMac definition.

                uses lsTable;
            } // END of l2mcasttable-container definition.
            container aflosttable {
                description
                    "List of appointed forwarder lost status per vlan for self RB";
                uses lsTable;
            } // END of aflosttable-container definition.
            container chnlEchoReqTable {
                description
                    "Table to store info related to oam messages sent";
                uses lsTable;
            } // END of chnlEchoReqTable-container definition.
            container aflosttablelsp {
                description
                    "AF lost counter status for all LSPs, systemid + vlan(prefix)";
                uses lsTable;
            } // END of aflosttablelsp-container definition.
            container iftable {
                description
                    "Tables";
                uses lsTable;
            } // END of iftable-container definition.
            container nbrtable {
                description
                    "Global neighbor table";
                uses lsTable;
            } // END of nbrtable-container definition.
            container nexthopTable {
                description
                    "Global neighbor table";
                uses lsTable;
            } // END of nexthopTable-container definition.
            container tlvareaaddrs {
                description
                    "Area Addresses";
                uses trilltlv;
            } // END of tlvareaaddrs-container definition.
            container tlvprotos {
                description
                    "Protocol supported";
                uses trilltlv;
            } // END of tlvprotos-container definition.
            container tlvlspbuffsz {
                description
                    "MinimumLSPBufferSizeTLV.";
                uses trilltlv;
            } // END of tlvlspbuffsz-container definition.
            container stlvtreeid {
                description
                    " Tree ID Sub TLV";
                uses trilltlv;
            } // END of stlvtreeid-container definition.
            container stlvtreeuseid {
                description
                    "Tree use ID Sub TLV";
                uses trilltlv;
            } // END of stlvtreeuseid-container definition.
            container stlvchannel {
                description
                    "Channel Sub TLV";
                uses trilltlv;
            } // END of stlvchannel-container definition.
            container pvlantable {
                description
                    " Per vlan info table";
                uses lsTable;
            } // END of pvlantable-container definition.
            container trillsnmpneigh {
                description
                    "Trill neighbor table based on MAC, for SNMP";
                uses lsTable;
            } // END of trillsnmpneigh-container definition.
            container trillsnmpsnoopport {
                description
                    "Trill Snooping Port table for SNMP";
                uses lsTable;
            } // END of trillsnmpsnoopport-container definition.
            container prevsysid {
                description
                    "*Maintain previous sysID information";
                leaf lspid  {
                    type  cml-data-types:CML_STRING_T;
                    description "";
                } // END of lspid definition.

                leaf seqnumsys  {
                    type  cml-data-types:CML_UINT32_T;
                    description "";
                } // END of seqnumsys definition.

                leaf cksum  {
                    type  cml-data-types:CML_UINT16_T;
                    description "";
                } // END of cksum definition.

            } // END of prevsysid-container definition.
            container trillsnoopaddr {
                description
                    "Trill Snooping Address table for SNMP/CLI";
                uses lsTable;
            } // END of trillsnoopaddr-container definition.
            container esadi {
                description
                    "Pointer to esadi module";
                leaf esadiaggrselfafbitmap  {
                    type  cml-data-types:CML_UINT16_T;
                    description "";
                } // END of esadiaggrselfafbitmap definition.

                leaf esadienabledinstancesbitmap  {
                    type  cml-data-types:CML_UINT16_T;
                    description "";
                } // END of esadienabledinstancesbitmap definition.

                leaf lspgeninterval  {
                    type  cml-data-types:CML_UINT16_T;
                    description "";
                } // END of lspgeninterval definition.

                leaf esadiflags  {
                    type  cml-data-types:CML_UINT16_T;
                    description "";
                } // END of esadiflags definition.


                list esadiinstance {
                    key "startvidesadi";
                    description
                        "ls table for storing ESADI Instances for an RBridge running ESADI";
                    leaf bridgeId  {
                        type  cml-data-types:CML_UINT8_T;
                        description "";
                    } // END of bridgeId definition.

                    leaf startvidesadi  {
                        type  cml-data-types:CML_RANGE_T;
                        description "";
                    } // END of startvidesadi definition.

                    leaf endvidesadi  {
                        type  cml-data-types:CML_UINT16_T;
                        description "";
                    } // END of endvidesadi definition.

                    leaf flagsesadi  {
                        type  cml-data-types:CML_UINT8_T;
                        description "";
                    } // END of flagsesadi definition.

                    leaf lspin  {
                        type  cml-data-types:CML_UINT16_T;
                        config false;
                        description "";
                    } // END of lspin definition.

                    leaf lspout  {
                        type  cml-data-types:CML_UINT16_T;
                        config false;
                        description "";
                    } // END of lspout definition.

                    leaf lspinselfgenerated  {
                        type  cml-data-types:CML_UINT16_T;
                        config false;
                        description "";
                    } // END of lspinselfgenerated definition.

                    leaf csnpin  {
                        type  cml-data-types:CML_UINT16_T;
                        config false;
                        description "";
                    } // END of csnpin definition.

                    leaf csnpout  {
                        type  cml-data-types:CML_UINT16_T;
                        config false;
                        description "";
                    } // END of csnpout definition.

                    leaf psnpin  {
                        type  cml-data-types:CML_UINT16_T;
                        config false;
                        description "";
                    } // END of psnpin definition.

                    leaf psnpout  {
                        type  cml-data-types:CML_UINT16_T;
                        config false;
                        description "";
                    } // END of psnpout definition.

                    leaf unknownin  {
                        type  cml-data-types:CML_UINT16_T;
                        config false;
                        description "";
                    } // END of unknownin definition.

                    leaf corruptedlsps  {
                        type  cml-data-types:CML_UINT16_T;
                        config false;
                        description "";
                    } // END of corruptedlsps definition.

                    leaf drbchanges  {
                        type  cml-data-types:CML_UINT16_T;
                        config false;
                        description "";
                    } // END of drbchanges definition.

                    leaf exceedmaxseqnums  {
                        type  cml-data-types:CML_UINT16_T;
                        config false;
                        description "";
                    } // END of exceedmaxseqnums definition.

                    leaf lsppurges  {
                        type  cml-data-types:CML_UINT16_T;
                        config false;
                        description "";
                    } // END of lsppurges definition.

                    leaf idlenmismatches  {
                        type  cml-data-types:CML_UINT16_T;
                        config false;
                        description "";
                    } // END of idlenmismatches definition.

                    leaf maxareaaddrmismatches  {
                        type  cml-data-types:CML_UINT16_T;
                        config false;
                        description "";
                    } // END of maxareaaddrmismatches definition.

                    leaf lspchecksumerr  {
                        type  cml-data-types:CML_UINT16_T;
                        config false;
                        description "";
                    } // END of lspchecksumerr definition.

                    uses lsTable;
                } // End of esadiinstance-list
                container esadilspdb {
                    description
                        "ls table for storing ESADI LSPs for all ESADI Instances";
                    uses lsTable;
                } // END of esadilspdb-container definition.
                container esadiconfig {
                    description
                        "ls table to store esadi configuration";
                    leaf esadipriority  {
                        type  cml-data-types:CML_UINT16_T {
                             range "0..127";
                        }
                        description "";
                    } // END of esadipriority definition.

                    leaf vlanId  {
                        type  cml-data-types:CML_UINT16_T {
                             range "1..4094";
                        }
                        description "";
                    } // END of vlanId definition.

                    leaf esadicsnptimerinterval  {
                        type  cml-data-types:CML_UINT16_T {
                             range "1..65535";
                        }
                        description "";
                    } // END of esadicsnptimerinterval definition.

                    leaf lspgeninterval  {
                        type  cml-data-types:CML_UINT16_T {
                             range "33..120";
                        }
                        description "";
                    } // END of lspgeninterval definition.

                    leaf esadiconfidence  {
                        type  cml-data-types:CML_UINT16_T {
                             range "0..255";
                        }
                        description "";
                    } // END of esadiconfidence definition.

                    leaf esadil2learning  {
                        type  cml-data-types:CML_BOOL_T;
                        description "";
                    } // END of esadil2learning definition.

                    uses lsTable;
                } // END of esadiconfig-container definition.
            } // END of esadi-container definition.
            container fwddelaytmrinfolist {
                description
                    "Contains Forward delay timer information";
                uses lsTable;
            } // END of fwddelaytmrinfolist-container definition.
            container staticroute {
                description
                    "Contains Forward delay timer information";
                leaf routeflag  {
                    type  cml-data-types:CML_UINT16_T;
                    description "";
                } // END of routeflag definition.

                leaf egressname  {
                    type  cml-data-types:CML_STRING_T;
                    description "";
                } // END of egressname definition.

                leaf ncknextname  {
                    type  cml-data-types:CML_STRING_T;
                    description "";
                } // END of ncknextname definition.

                leaf hopcnt  {
                    type  cml-data-types:CML_UINT16_T {
                         range "1..255";
                    }
                    description "";
                } // END of hopcnt definition.

                leaf metric  {
                    type  cml-data-types:CML_UINT16_T;
                    description "";
                } // END of metric definition.

            } // END of staticroute-container definition.
            container nicknamenhinfo {
                description
                    "add neighbor nickname";
                leaf inuse  {
                    type  cml-data-types:CML_UINT8_T;
                    description "";
                } // END of inuse definition.

                leaf nhmac  {
                    type  cml-data-types:CML_STRING_T;
                    description "";
                } // END of nhmac definition.

                leaf ifName  {
                    type  cml-data-types:CML_STRING_T;
                    description "";
                } // END of ifName definition.

                leaf nhnick  {
                    type  cml-data-types:CML_STRING_T;
                    description "";
                } // END of nhnick definition.

                leaf ifindex  {
                    type  cml-data-types:CML_UINT16_T;
                    description "";
                } // END of ifindex definition.

            } // END of nicknamenhinfo-container definition.
            container dmacentry {
                description
                    "This struct can be reused for ESAID";
                leaf dmacflag  {
                    type  cml-data-types:CML_UINT8_T;
                    description "";
                } // END of dmacflag definition.

                leaf dmac  {
                    type  cml-data-types:CML_STRING_T;
                    description "";
                } // END of dmac definition.

                leaf vlanId  {
                    type  cml-data-types:CML_UINT16_T {
                         range "1..4094";
                    }
                    description "";
                } // END of vlanId definition.

                leaf egressnickname  {
                    type  cml-data-types:CML_STRING_T;
                    description "";
                } // END of egressnickname definition.

                leaf ifindex  {
                    type  cml-data-types:CML_UINT16_T;
                    description "";
                } // END of ifindex definition.

            } // END of dmacentry-container definition.
        } // End of trill-list
    } // END of trill-grouping definition.
    grouping lsTable {
        description
            "lsTable";
        leaf desc  {
            type  cml-data-types:CML_STRING_T;
            description "";
        } // END of desc definition.

        leaf prefixsize  {
            type  cml-data-types:CML_UINT8_T;
            description "";
        } // END of prefixsize definition.

        leaf slotsize  {
            type  cml-data-types:CML_UINT8_T;
            description "";
        } // END of slotsize definition.

        leaf count  {
            type  cml-data-types:CML_UINT32_T;
            description "";
        } // END of count definition.

    } // END of lsTable definition.
    grouping trilltlv {
        description
            "TLVs";
        leaf type  {
            type  cml-data-types:CML_UINT8_T;
            description "";
        } // END of type definition.

        leaf len  {
            type  cml-data-types:CML_UINT8_T;
            description "";
        } // END of len definition.

        leaf lenTmp  {
            type  cml-data-types:CML_UINT8_T;
            description "";
        } // END of lenTmp definition.

        leaf flags  {
            type  cml-data-types:CML_UINT8_T;
            description "";
        } // END of flags definition.

        leaf slot  {
            type  cml-data-types:CML_UINT8_T;
            description "";
        } // END of slot definition.

        leaf data  {
            type  cml-data-types:CML_STRING_T;
            description "";
        } // END of data definition.

        container lsp {
            description
                " Pointer to parent LSP.";
            leaf slot  {
                type  cml-data-types:CML_UINT8_T;
                description "";
            } // END of slot definition.

            leaf lock  {
                type  cml-data-types:CML_UINT32_T;
                description "";
            } // END of lock definition.

            leaf psnId  {
                type  cml-data-types:CML_UINT8_T;
                description "";
            } // END of psnId definition.

            leaf lspnum  {
                type  cml-data-types:CML_UINT8_T;
                description "";
            } // END of lspnum definition.

            leaf lspflags  {
                type  cml-data-types:CML_UINT16_T;
                description "";
            } // END of lspflags definition.

            leaf seqnum  {
                type  cml-data-types:CML_UINT32_T;
                description "";
            } // END of seqnum definition.

            leaf originatinglspbuffsz  {
                type  cml-data-types:CML_UINT16_T;
                description "";
            } // END of originatinglspbuffsz definition.

            leaf status  {
                type  cml-data-types:CML_UINT16_T;
                description "";
            } // END of status definition.

            leaf dstatus  {
                type  cml-data-types:CML_UINT16_T;
                description "";
            } // END of dstatus definition.

            leaf chFlags  {
                type  cml-data-types:CML_UINT16_T;
                description "";
            } // END of chFlags definition.

            container lsph {
                description
                    " Pointer to parent LSP.";
                leaf pduLength  {
                    type  cml-data-types:CML_UINT16_T;
                    description "";
                } // END of pduLength definition.

                leaf lifetime  {
                    type  cml-data-types:CML_UINT16_T;
                    description "";
                } // END of lifetime definition.

                leaf seqnum  {
                    type  cml-data-types:CML_UINT32_T;
                    description "";
                } // END of seqnum definition.

                leaf cksum  {
                    type  cml-data-types:CML_UINT16_T;
                    description "";
                } // END of cksum definition.

                leaf flags  {
                    type  cml-data-types:CML_UINT16_T;
                    description "";
                } // END of flags definition.

            } // END of lsph-container definition.
            container packet {
                description
                    "LSP in raw PDU format";
                leaf packetData  {
                    type  cml-data-types:CML_STRING_T;
                    description "";
                } // END of packetData definition.

                leaf putp  {
                    type  cml-data-types:CML_UINT32_T;
                    description "";
                } // END of putp definition.

                leaf getp  {
                    type  cml-data-types:CML_UINT32_T;
                    description "";
                } // END of getp definition.

                leaf endp  {
                    type  cml-data-types:CML_UINT32_T;
                    description "";
                } // END of endp definition.

                leaf size  {
                    type  cml-data-types:CML_UINT32_T;
                    description "";
                } // END of size definition.

            } // END of packet-container definition.
            container tvupdate {
                description
                    "LSP update timestamp.";
                leaf tvsec  {
                    type  cml-data-types:CML_STRING_T;
                    description "";
                } // END of tvsec definition.

                leaf tvusec  {
                    type  cml-data-types:CML_UINT32_T;
                    description "";
                } // END of tvusec definition.

            } // END of tvupdate-container definition.
            container srmFlag {
                description
                    "SRM flag";
                leaf srmSize  {
                    type  cml-data-types:CML_UINT32_T;
                    description "";
                } // END of srmSize definition.

                leaf srmBits  {
                    type  cml-data-types:CML_STRING_T;
                    description "";
                } // END of srmBits definition.

            } // END of srmFlag-container definition.
            container ssnFlag {
                description
                    "SSN flag";
                leaf ssnSize  {
                    type  cml-data-types:CML_UINT32_T;
                    description "";
                } // END of ssnSize definition.

                leaf ssnBits  {
                    type  cml-data-types:CML_STRING_T;
                    description "";
                } // END of ssnBits definition.

            } // END of ssnFlag-container definition.
            container dtinfo {
                description
                    "Dtree info";
                leaf numdtreestocompute  {
                    type  cml-data-types:CML_UINT16_T;
                    description "";
                } // END of numdtreestocompute definition.

                leaf numdtreesabletocompute  {
                    type  cml-data-types:CML_UINT16_T;
                    description "";
                } // END of numdtreesabletocompute definition.

                leaf numdtreestouse  {
                    type  cml-data-types:CML_UINT16_T;
                    description "";
                } // END of numdtreestouse definition.

            } // END of dtinfo-container definition.
        } // END of lsp-container definition.
    } // END of trilltlv definition.

    grouping  trillinterface-grouping {
    description
        "trillinterface";
    container trillinterface {
        if-feature feature-list:HAVE_TRILLD;
        description
            "trillinterface";
        leaf intfflags  {
            type  cml-data-types:CML_UINT8_T;
            description "";
        } // END of intfflags definition.

        leaf type  {
            type  cml-data-types:CML_STRING_T;
            config false;
            description "";
        } // END of type definition.

        leaf circuitid  {
            type  cml-data-types:CML_UINT8_T;
            config false;
            description "";
        } // END of circuitid definition.

        leaf portid  {
            type  cml-data-types:CML_UINT16_T;
            description "";
        } // END of portid definition.

        leaf circuittype  {
            type  cml-data-types:CML_STRING_T;
            config false;
            description "";
        } // END of circuittype definition.

        leaf neighbourCount  {
            type  cml-data-types:CML_UINT16_T;
            config false;
            description "";
        } // END of neighbourCount definition.

        leaf lock  {
            type  cml-data-types:CML_UINT32_T;
            description "";
        } // END of lock definition.

        leaf bridgeId  {
            type  cml-data-types:CML_STRING_T;
            description "";
        } // END of bridgeId definition.

        leaf probeseqno  {
            type  cml-data-types:CML_UINT32_T;
            description "";
        } // END of probeseqno definition.

        container trilliflevel {
            config false;
            description
                "Level for interface.";
            leaf indexlevel  {
                type  cml-data-types:CML_UINT32_T;
                description "";
            } // END of indexlevel definition.

            leaf flaglevel  {
                type  cml-data-types:CML_UINT32_T;
                description "";
            } // END of flaglevel definition.

            leaf statelevel  {
                type  cml-data-types:CML_UINT32_T;
                description "";
            } // END of statelevel definition.

            leaf ostatelevel  {
                type  cml-data-types:CML_UINT32_T;
                description "";
            } // END of ostatelevel definition.

            leaf drbportid  {
                type  cml-data-types:CML_UINT32_T;
                description "";
            } // END of drbportid definition.

            leaf drbmac  {
                type  cml-data-types:CML_STRING_T;
                description "";
            } // END of drbmac definition.

            leaf adjchanges  {
                type  cml-data-types:CML_UINT32_T;
                description "";
            } // END of adjchanges definition.

            leaf numadj  {
                type  cml-data-types:CML_UINT32_T;
                description "";
            } // END of numadj definition.

            leaf initfails  {
                type  cml-data-types:CML_UINT32_T;
                description "";
            } // END of initfails definition.

            leaf rejadjs  {
                type  cml-data-types:CML_UINT32_T;
                description "";
            } // END of rejadjs definition.

            leaf idlenmismatches  {
                type  cml-data-types:CML_UINT32_T;
                description "";
            } // END of idlenmismatches definition.

            leaf maxareaaddrmismatches  {
                type  cml-data-types:CML_UINT32_T;
                description "";
            } // END of maxareaaddrmismatches definition.

            leaf drbchanges  {
                type  cml-data-types:CML_UINT32_T;
                description "";
            } // END of drbchanges definition.

            leaf statechange  {
                type  cml-data-types:CML_UINT32_T;
                description "";
            } // END of statechange definition.

            leaf lanhelloin  {
                type  cml-data-types:CML_UINT32_T;
                description "";
            } // END of lanhelloin definition.

            leaf lanhelloout  {
                type  cml-data-types:CML_UINT32_T;
                description "";
            } // END of lanhelloout definition.

            leaf p2phelloin  {
                type  cml-data-types:CML_UINT32_T;
                description "";
            } // END of p2phelloin definition.

            leaf p2phelloout  {
                type  cml-data-types:CML_UINT32_T;
                description "";
            } // END of p2phelloout definition.

            leaf lspinlevel  {
                type  cml-data-types:CML_UINT32_T;
                description "";
            } // END of lspinlevel definition.

            leaf lspoutlevel  {
                type  cml-data-types:CML_UINT32_T;
                description "";
            } // END of lspoutlevel definition.

            leaf lspinselfgenerated  {
                type  cml-data-types:CML_UINT32_T;
                description "";
            } // END of lspinselfgenerated definition.

            leaf csnpinlevel  {
                type  cml-data-types:CML_UINT32_T;
                description "";
            } // END of csnpinlevel definition.

            leaf csnpoutlevel  {
                type  cml-data-types:CML_UINT32_T;
                description "";
            } // END of csnpoutlevel definition.

            leaf psnpinlevel  {
                type  cml-data-types:CML_UINT32_T;
                description "";
            } // END of psnpinlevel definition.

            leaf psnpoutlevel  {
                type  cml-data-types:CML_UINT32_T;
                description "";
            } // END of psnpoutlevel definition.

            leaf unknowninlevel  {
                type  cml-data-types:CML_UINT32_T;
                description "";
            } // END of unknowninlevel definition.

            leaf unknownoutlevel  {
                type  cml-data-types:CML_UINT32_T;
                description "";
            } // END of unknownoutlevel definition.

            leaf tcnoutlevel  {
                type  cml-data-types:CML_UINT32_T;
                description "";
            } // END of tcnoutlevel definition.

            leaf tcnackin  {
                type  cml-data-types:CML_UINT32_T;
                description "";
            } // END of tcnackin definition.

            leaf lspchecksumerr  {
                type  cml-data-types:CML_UINT32_T;
                description "";
            } // END of lspchecksumerr definition.

            leaf mtuprobein  {
                type  cml-data-types:CML_UINT32_T;
                description "";
            } // END of mtuprobein definition.

            leaf mtuprobeout  {
                type  cml-data-types:CML_UINT32_T;
                description "";
            } // END of mtuprobeout definition.

            leaf mtuackin  {
                type  cml-data-types:CML_UINT32_T;
                description "";
            } // END of mtuackin definition.

            leaf mtuackout  {
                type  cml-data-types:CML_UINT32_T;
                description "";
            } // END of mtuackout definition.

            leaf discarded  {
                type  cml-data-types:CML_UINT32_T;
                description "";
            } // END of discarded definition.

            leaf channeldiscarded  {
                type  cml-data-types:CML_UINT32_T;
                description "";
            } // END of channeldiscarded definition.

        } // END of trilliflevel-container definition.
        container trillifparams {
            description
                "Configuration parameters";
            leaf prototypeparam  {
                type  cml-data-types:CML_UINT8_T;
                description "";
            } // END of prototypeparam definition.

            leaf configparam  {
                type  cml-data-types:CML_UINT8_T;
                description "";
            } // END of configparam definition.

            leaf configtag  {
                type  cml-data-types:CML_STRING_T;
                description "";
            } // END of configtag definition.

            leaf configtype  {
                type  cml-data-types:CML_CONFIGTYPE_T;
                description "";
            } // END of configtype definition.

            leaf circuittype  {
                type  cml-data-types:CML_UINT8_T;
                description "";
            } // END of circuittype definition.

            leaf lspinterval  {
                type  cml-data-types:CML_UINT32_T {
                     range "1..4294967295";
                }
                description "";
            } // END of lspinterval definition.

            leaf retransmitinterval  {
                type  cml-data-types:CML_UINT32_T {
                     range "1..65535";
                }
                description "";
            } // END of retransmitinterval definition.

            leaf trillconfig  {
                type  cml-data-types:CML_UINT16_T;
                description "";
            } // END of trillconfig definition.

            leaf configBypasspsn  {
                type  cml-data-types:CML_UINT16_T;
                default "1";
                description "";
            } // END of configBypasspsn definition.

            leaf desireddesigvlan  {
                type  cml-data-types:CML_UINT16_T {
                     range "1..4094";
                }
                description "";
            } // END of desireddesigvlan definition.

            leaf inhibitiontime  {
                type  cml-data-types:CML_UINT16_T {
                     range "1..30";
                }
                description "";
            } // END of inhibitiontime definition.

            leaf maxneighborcount  {
                type  cml-data-types:CML_UINT16_T {
                     range "0..500";
                }
                description "";
            } // END of maxneighborcount definition.

            leaf stpwiringcloset  {
                type  cml-data-types:CML_STRING_T;
                description "";
            } // END of stpwiringcloset definition.

            leaf rootinhibitioninterval  {
                type  cml-data-types:CML_UINT8_T {
                     range "0..30";
                }
                description "";
            } // END of rootinhibitioninterval definition.

            leaf announcingvlanset  {
                type  cml-data-types:CML_RANGE_T;
                description "";
            } // END of announcingvlanset definition.

            leaf esenabledvlanset  {
                type  cml-data-types:CML_RANGE_T;
                description "";
            } // END of esenabledvlanset definition.

            leaf enabledvlan  {
                type  cml-data-types:CML_UINT32_T;
                description "";
            } // END of enabledvlan definition.

            leaf portflags  {
                type  cml-data-types:CML_UINT32_T;
                description "";
            } // END of portflags definition.

            leaf overHeadflags  {
                type  cml-data-types:CML_UINT8_T;
                default "1";
                description "";
            } // END of overHeadflags definition.

            leaf accessPort  {
                type  cml-data-types:CML_UINT8_T;
                default "1";
                description "";
            } // END of accessPort definition.

            leaf disablePort  {
                type  cml-data-types:CML_UINT8_T;
                default "1";
                description "";
            } // END of disablePort definition.

            leaf trunkPort  {
                type  cml-data-types:CML_UINT8_T;
                default "1";
                description "";
            } // END of trunkPort definition.

            leaf bpduEnable  {
                type  cml-data-types:CML_UINT8_T;
                default "1";
                description "";
            } // END of bpduEnable definition.

            leaf rootinhibitiontimer  {
                type  cml-data-types:CML_UINT8_T;
                description "";
            } // END of rootinhibitiontimer definition.

            container trilliflevelconf {
                description
                    "Configuration parameters";
                leaf confconfig  {
                    type  cml-data-types:CML_UINT16_T;
                    description "";
                } // END of confconfig definition.

                leaf minimalHellointrvl  {
                    type  cml-data-types:CML_UINT16_T;
                    default "1";
                    description "";
                } // END of minimalHellointrvl definition.

                leaf hellointerval  {
                    type  cml-data-types:CML_UINT32_T {
                         range "1..65535";
                    }
                    description "";
                } // END of hellointerval definition.

                leaf hellomultiplier  {
                    type  cml-data-types:CML_UINT16_T {
                         range "2..100";
                    }
                    description "";
                } // END of hellomultiplier definition.

                leaf csnpinterval  {
                    type  cml-data-types:CML_UINT32_T {
                         range "1..65535";
                    }
                    description "";
                } // END of csnpinterval definition.

                leaf priority  {
                    type  cml-data-types:CML_UINT8_T {
                         range "1..127";
                    }
                    description "";
                } // END of priority definition.

                leaf widemetric  {
                    type  cml-data-types:CML_UINT32_T {
                         range "1..16777214";
                    }
                    description "";
                } // END of widemetric definition.

            } // END of trilliflevelconf-container definition.
        } // END of trillifparams-container definition.
    } // END of trillinterface-container definition.
    } // END of trillinterface-container definition.

    grouping  debugTrill-grouping {
    description
        "debugTrill";
    container debugTrill {
        description
            "debugTrill";
        leaf debugAll  {
            type  cml-data-types:CML_UINT8_T;
            default "1";
            description "";
        } // END of debugAll definition.

        leaf ifsm  {
            type  cml-data-types:CML_UINT32_T;
            default "0";
            description "";
        } // END of ifsm definition.

        leaf nfsm  {
            type  cml-data-types:CML_UINT32_T;
            default "1";
            description "";
        } // END of nfsm definition.

        leaf pdu  {
            type  cml-data-types:CML_UINT32_T;
            default "4";
            description "";
        } // END of pdu definition.

        leaf lsp  {
            type  cml-data-types:CML_UINT32_T;
            default "5";
            description "";
        } // END of lsp definition.

        leaf spf  {
            type  cml-data-types:CML_UINT32_T;
            default "6";
            description "";
        } // END of spf definition.

        leaf events  {
            type  cml-data-types:CML_UINT32_T;
            default "7";
            description "";
        } // END of events definition.

        leaf nsm  {
            type  cml-data-types:CML_UINT32_T;
            default "8";
            description "";
        } // END of nsm definition.

        leaf oam  {
            type  cml-data-types:CML_UINT32_T;
            default "2";
            description "";
        } // END of oam definition.

        leaf esadi  {
            type  cml-data-types:CML_UINT32_T;
            default "3";
            description "";
        } // END of esadi definition.

        leaf l2mrib  {
            type  cml-data-types:CML_UINT32_T;
            default "9";
            description "";
        } // END of l2mrib definition.

    } // END of debugTrill-container definition.
    } // END of debugTrill-container definition.

    grouping  debugTrillExec-grouping {
    description
        "debugTrillExec";
    container debugTrillExec {
        description
            "debugTrillExec";
        leaf debugAllExec  {
            type  cml-data-types:CML_UINT8_T;
            default "1";
            description "";
        } // END of debugAllExec definition.

        leaf ifsmExec  {
            type  cml-data-types:CML_UINT32_T;
            default "0";
            description "";
        } // END of ifsmExec definition.

        leaf nfsmExec  {
            type  cml-data-types:CML_UINT32_T;
            default "1";
            description "";
        } // END of nfsmExec definition.

        leaf pduExec  {
            type  cml-data-types:CML_UINT32_T;
            default "4";
            description "";
        } // END of pduExec definition.

        leaf lspExec  {
            type  cml-data-types:CML_UINT32_T;
            default "5";
            description "";
        } // END of lspExec definition.

        leaf spfExec  {
            type  cml-data-types:CML_UINT32_T;
            default "6";
            description "";
        } // END of spfExec definition.

        leaf eventsExec  {
            type  cml-data-types:CML_UINT32_T;
            default "7";
            description "";
        } // END of eventsExec definition.

        leaf nsmExec  {
            type  cml-data-types:CML_UINT32_T;
            default "8";
            description "";
        } // END of nsmExec definition.

        leaf oamExec  {
            type  cml-data-types:CML_UINT32_T;
            default "2";
            description "";
        } // END of oamExec definition.

        leaf esadiExec  {
            type  cml-data-types:CML_UINT32_T;
            default "3";
            description "";
        } // END of esadiExec definition.

        leaf l2mribExec  {
            type  cml-data-types:CML_UINT32_T;
            default "9";
            description "";
        } // END of l2mribExec definition.

    } // END of debugTrillExec-container definition.
    } // END of debugTrillExec-container definition.


}
