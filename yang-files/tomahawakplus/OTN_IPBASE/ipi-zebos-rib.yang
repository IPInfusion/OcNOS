/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-rib.yang
*
*/

submodule ipi-zebos-rib {

    belongs-to  ipi-zebos { prefix ipi-zebos; }

    import cml-data-types {
        prefix cml-data-types;
    }

    import feature-list {
        prefix feature-list;
    }

    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "";


    revision "2018-06-21" {
        description " Initial Version.";
        reference "";
    }

    grouping ribRuntimeGrp {
        description
            "ribRuntimeGrp";
        leaf subType  {
            type  cml-data-types:CML_STRING_T;
            config false;
            description "Sub type of the route";
        } // END of subType definition.

        leaf distance  {
            type  cml-data-types:CML_UINT8_T;
            config false;
            description "Distance value for rib route";
        } // END of distance definition.

        leaf metric  {
            type  cml-data-types:CML_UINT8_T;
            config false;
            description "Metric value for rib route";
        } // END of metric definition.

        leaf blackHole  {
            type  cml-data-types:CML_STRING_T;
            config false;
            description "discarding incoming/outgoing packets without informing source";
        } // END of blackHole definition.

        leaf ribUptime  {
            type  cml-data-types:CML_STRING_T;
            config false;
            description "Uptime";
        } // END of ribUptime definition.

        leaf ribFlagSelected  {
            type  cml-data-types:CML_BOOL_T;
            config false;
            description "rib selected route";
        } // END of ribFlagSelected definition.

        leaf ribFlagStale  {
            type  cml-data-types:CML_BOOL_T;
            config false;
            description "rib stale entry info";
        } // END of ribFlagStale definition.


        list nextHopRunTime {
            key "gwAddrRuntime";
            config false;
            description
                "next-hop run-time attrs";
            leaf gwAddrRuntime  {
                type  cml-data-types:CML_STRING_T;
                description "Gateway address";
            } // END of gwAddrRuntime definition.

            leaf gwLastResort  {
                type  cml-data-types:CML_IPV4_ADDR_T;
                description "Gateway last resort";
            } // END of gwLastResort definition.

            leaf nexthopIfName  {
                type  cml-data-types:CML_STRING_T;
                description "Nexthop interface name";
            } // END of nexthopIfName definition.

            leaf nexthopIfIndex  {
                type  cml-data-types:CML_STRING_T;
                description "Nexthop interface index";
            } // END of nexthopIfIndex definition.

            leaf nexthopFlagActive  {
                type  cml-data-types:CML_BOOL_T;
                description "Nexthop flag active 0(Inactive) 1(Active)";
            } // END of nexthopFlagActive definition.

            leaf nexthopFibStatus  {
                type  cml-data-types:CML_BOOL_T;
                description "Nexthop fib status";
            } // END of nexthopFibStatus definition.

        } // End of nextHopRunTime-list
    } // END of ribRuntimeGrp definition.
    grouping ribVrfAfiGrp {
        description
            "ribVrfAfiGrp";
        leaf totalRoutes  {
            type  cml-data-types:CML_UINT32_T;
            config false;
            description "Total number of routes";
        } // END of totalRoutes definition.

        leaf totalPaths  {
            type  cml-data-types:CML_UINT32_T;
            config false;
            description "Total number of paths";
        } // END of totalPaths definition.

        leaf countFib  {
            type  cml-data-types:CML_UINT32_T;
            config false;
            description "Fib count";
        } // END of countFib definition.

        leaf ecmpRoutes  {
            type  cml-data-types:CML_UINT32_T;
            config false;
            description "Total number of ECMP routes";
        } // END of ecmpRoutes definition.

        leaf ecmpPaths  {
            type  cml-data-types:CML_UINT32_T;
            config false;
            description "Total number of ECMP paths";
        } // END of ecmpPaths definition.

        leaf ecmpPathCntr  {
            type  cml-data-types:CML_STRING_T;
            config false;
            description "Number of routes with the ECMP paths";
        } // END of ecmpPathCntr definition.


        list routeSource {
            key "routeType";
            config false;
            description
                "run-time route-type and route-count";
            leaf routeType  {
                type  cml-data-types:CML_STRING_T;
                description "Route type";
            } // END of routeType definition.

            leaf routeTypeCount  {
                type  cml-data-types:CML_UINT32_T;
                description "Router type count";
            } // END of routeTypeCount definition.

        } // End of routeSource-list
    } // END of ribVrfAfiGrp definition.
    grouping ribAttr {
        description
            "ribAttr";
        leaf distValue  {
            type  cml-data-types:CML_INT32_T {
                 range "1..255";
            }
            description "Distance value for the route";
        } // END of distValue definition.

        leaf tagVal  {
            type  cml-data-types:CML_UINT32_T {
                 range "0..4294967295";
            }
            default "0";
            description "tag value";
        } // END of tagVal definition.

        leaf description  {
            type  cml-data-types:CML_STRING_T;
            description "description of the static route";
        } // END of description definition.

    } // END of ribAttr definition.

    grouping  rib-grouping {
    description
        "RIB Master for system wide configurations";
    container rib {
        description
            "RIB Master for system wide configurations";
        leaf fibRetain  {
            if-feature feature-list:HAVE_L3;
            type  cml-data-types:CML_FIB_RETAIN_T;
            default "60";
            description "fib retain forever or specific time after RIB restarts";
        } // END of fibRetain definition.

        leaf multipathNum  {
            if-feature feature-list:HAVE_MULTIPATH;
            type  cml-data-types:CML_UINT8_T {
                 range "1..64";
            }
            description "value for maximum number of paths to be installed in FIB";
        } // END of multipathNum definition.

        leaf maxStaticRoutes  {
            type  cml-data-types:CML_UINT32_T {
                 range "1..4294967294";
            }
            default "4294967294";
            description "value for maximum number of static routes";
        } // END of maxStaticRoutes definition.

        leaf maxFibRoutes  {
            type  cml-data-types:CML_UINT32_T {
                 range "1..16384";
            }
            description "value for maximum fib routes to be included in kernel";
        } // END of maxFibRoutes definition.

        leaf debugTerm  {
            type  cml-data-types:CML_RIB_DEBUG_TYPE_T;
            description "Enable or Disable rib debugging";
        } // END of debugTerm definition.

        leaf debugConf  {
            type  cml-data-types:CML_RIB_DEBUG_TYPE_T;
            description "Enable or Disable rib debugging";
        } // END of debugConf definition.

        leaf debugIpExit  {
            type  cml-data-types:CML_RIB_DEBUG_ROUTING_TYPE_T;
            description "ipv4 debug value";
        } // END of debugIpExit definition.

        leaf debugIpv6Exit  {
            type  cml-data-types:CML_RIB_DEBUG_ROUTING_TYPE_T;
            description "ipv6 debug value";
        } // END of debugIpv6Exit definition.

        leaf debugIp  {
            type  cml-data-types:CML_RIB_DEBUG_ROUTING_TYPE_T;
            description "ipv4 debug type";
        } // END of debugIp definition.

        leaf debugIpv6  {
            type  cml-data-types:CML_RIB_DEBUG_ROUTING_TYPE_T;
            description "ipv6 debug type";
        } // END of debugIpv6 definition.


        list ribIpv4 {
            key "destPrefix";
            description
                "rib ipv4 config and run-time attributes";
            leaf destPrefix  {
                type  cml-data-types:CML_IPV4_PREFIX_T;
                description "IP destination prefix (e.g. 10.0.0.0/8)";
            } // END of destPrefix definition.


            list ribStaticGwAddr {
                key "gwAddr";
                description
                    "RIB ipv4 next-hop address";
                leaf gwAddr  {
                    type  cml-data-types:CML_IPV4_ADDR_T;
                    description "IP gateway address";
                } // END of gwAddr definition.

                container ribBfd {
                    description
                        "RIB bfd";
                    leaf ribStaticBfd  {
                        type  cml-data-types:CML_BOOL_T;
                        description "Fall-over detection for staic ipv4 prefix";
                    } // END of ribStaticBfd definition.

                    leaf ribStaticBfdDisable  {
                        type  cml-data-types:CML_BOOL_T;
                        description "Disabling fall-over detection for static ipv4 prefix";
                    } // END of ribStaticBfdDisable definition.

                } // END of ribBfd-container definition.
                uses ribAttr;
            } // End of ribStaticGwAddr-list

            list ribStaticIfName {
                key "gwIfName";
                description
                    "gateway interface name";
                leaf gwIfName  {
                    type  cml-data-types:CML_STRING_T;
                    description "IP gateway interface name or pseudo interface Null";
                } // END of gwIfName definition.

                uses ribAttr;
            } // End of ribStaticIfName-list

            list ribRuntime {
                key "type";
                config false;
                description
                    "RIB run-time attributes";
                leaf type  {
                    type  cml-data-types:CML_STRING_T;
                    description "rib route type";
                } // END of type definition.

                uses ribRuntimeGrp;
            } // End of ribRuntime-list
        } // End of ribIpv4-list

        list ribIpv4Vrf {
            if-feature feature-list:HAVE_VRF;
            key "vrfName";
            description
                "RIB IPv4 vrf";
            leaf vrfName  {
                type  cml-data-types:CML_STRING_T;
                description "vrf name";
            } // END of vrfName definition.


            list vrfDestPrefix {
                key "destVrfPrefix";
                description
                    "vrf Ipv4 destination prefix";
                leaf destVrfPrefix  {
                    type  cml-data-types:CML_IPV4_PREFIX_T;
                    description "IP destination prefix (e.g. 10.0.0.0/8)";
                } // END of destVrfPrefix definition.


                list vrfIfName {
                    key "gwVrfIfName";
                    description
                        "vrf gateway interface name";
                    leaf gwVrfIfName  {
                        type  cml-data-types:CML_STRING_T;
                        description "IP gateway interface name";
                    } // END of gwVrfIfName definition.

                    uses ribAttr;
                } // End of vrfIfName-list

                list vrfGwAddr {
                    key "vrfGwAddr";
                    description
                        "vrf Ipv4 nexthop address";
                    leaf vrfGwAddr  {
                        type  cml-data-types:CML_IPV4_ADDR_T;
                        description "IP gateway address";
                    } // END of vrfGwAddr definition.

                    leaf vrfStaticFallOverBfd  {
                        type  cml-data-types:CML_STATIC_BFD_ENABLE_DISABLE_T;
                        description "BFD for static ipv4 vrf";
                    } // END of vrfStaticFallOverBfd definition.


                    list vrfGwAddrIfName {
                        key "gwVrfIfNameAddr";
                        description
                            "vrf gateway interface name";
                        leaf gwVrfIfNameAddr  {
                            type  cml-data-types:CML_STRING_T;
                            description "IP gateway interface name";
                        } // END of gwVrfIfNameAddr definition.

                        leaf gwVrfGlobal  {
                            type  cml-data-types:CML_BOOL_T;
                            description "Global table lookup";
                        } // END of gwVrfGlobal definition.

                        uses ribAttr;
                    } // End of vrfGwAddrIfName-list
                } // End of vrfGwAddr-list

                list ribRuntime {
                    key "type";
                    config false;
                    description
                        "route type";
                    leaf type  {
                        type  cml-data-types:CML_STRING_T;
                        description "rib route type";
                    } // END of type definition.

                    uses ribRuntimeGrp;
                } // End of ribRuntime-list
            } // End of vrfDestPrefix-list
            container ribIpv4VrfAfi {
                config false;
                description
                    "RIB IPv4 vrf run-time";
                uses ribVrfAfiGrp;
            } // END of ribIpv4VrfAfi-container definition.
        } // End of ribIpv4Vrf-list

        list ribIpv6 {
            if-feature feature-list:HAVE_IPV6;
            key "ipv6DestPrefix";
            description
                "RIB IPv6 destination prefix";
            leaf ipv6DestPrefix  {
                type  cml-data-types:CML_IPV6_PREFIX_T;
                description "IPv6 destination prefix (e.g. 3ffe:506::/32)";
            } // END of ipv6DestPrefix definition.


            list ribIpv6GwAddr {
                key "ipv6GwAddr";
                description
                    "RIB IPv6 nexthop address";
                leaf ipv6GwAddr  {
                    type  cml-data-types:CML_IPV6_ADDR_T;
                    description "IPv6 gateway address";
                } // END of ipv6GwAddr definition.

                leaf ipv6DistVal  {
                    type  cml-data-types:CML_INT32_T {
                         range "1..255";
                    }
                    description "Distance value for ipv6 prefix";
                } // END of ipv6DistVal definition.

                leaf ribIpv6StaticBfd  {
                    type  cml-data-types:CML_BOOL_T;
                    description "Fall-over detection for static ipv6 prefix ";
                } // END of ribIpv6StaticBfd definition.

                leaf ribIpv6StaticBfdDisable  {
                    type  cml-data-types:CML_BOOL_T;
                    description "Disabling fall-over detection for static ipv6 prefix";
                } // END of ribIpv6StaticBfdDisable definition.

            } // End of ribIpv6GwAddr-list

            list ribIpv6GwIfName {
                key "ipv6GwIfName";
                description
                    "gateway interface name for ipv6 type RIB";
                leaf ipv6GwIfName  {
                    type  cml-data-types:CML_STRING_T;
                    description "IPv6 gateway interface name";
                } // END of ipv6GwIfName definition.

                leaf ipv6DistVal  {
                    type  cml-data-types:CML_INT32_T {
                         range "1..255";
                    }
                    description "Distance value for this prefix";
                } // END of ipv6DistVal definition.

            } // End of ribIpv6GwIfName-list

            list ribIpv6GwAddrIfName {
                key "ipv6GateWayAddr";
                description
                    "nexthop address for ipv6 type RIB";
                leaf ipv6GateWayAddr  {
                    type  cml-data-types:CML_IPV6_ADDR_T;
                    description "IPv6 gateway address";
                } // END of ipv6GateWayAddr definition.


                list ribIpv6GwIfName {
                    key "ipv6GateWayIfName";
                    description
                        "gateway interface name for ipv6 type RIB";
                    leaf ipv6GateWayIfName  {
                        type  cml-data-types:CML_STRING_T;
                        description "IPv6 gateway interface name";
                    } // END of ipv6GateWayIfName definition.

                    leaf distValgwAddr  {
                        type  cml-data-types:CML_INT32_T {
                             range "1..255";
                        }
                        description "Distance value for this prefix";
                    } // END of distValgwAddr definition.

                } // End of ribIpv6GwIfName-list
            } // End of ribIpv6GwAddrIfName-list

            list ribRuntime {
                key "type";
                config false;
                description
                    "route-type";
                leaf type  {
                    type  cml-data-types:CML_STRING_T;
                    description "rib route type";
                } // END of type definition.

                uses ribRuntimeGrp;
            } // End of ribRuntime-list
        } // End of ribIpv6-list

        list ribIpv6Vrf {
            if-feature feature-list:HAVE_VRF;
            key "vrfName";
            description
                "vrf name for ipv6 type RIB";
            leaf vrfName  {
                type  cml-data-types:CML_STRING_T;
                description "vrf name";
            } // END of vrfName definition.


            list vrfDestPrefix {
                if-feature feature-list:HAVE_IPV6;
                key "ipv6VrfDestPrefix";
                description
                    "destination prefix for vrf ipv6 type RIB";
                leaf ipv6VrfDestPrefix  {
                    type  cml-data-types:CML_IPV6_PREFIX_T;
                    description "IPV6 destination prefix (e.g. 3ffe:506::1/32)";
                } // END of ipv6VrfDestPrefix definition.


                list vrfIpv6GwAddr {
                    key "ipv6VrfGwAddr";
                    description
                        "next-hop for vrf ipv6 type RIB";
                    leaf ipv6VrfGwAddr  {
                        type  cml-data-types:CML_IPV6_ADDR_T;
                        description "IPv6 gateway address";
                    } // END of ipv6VrfGwAddr definition.

                    leaf vrfStaticFallOverBfdV6  {
                        type  cml-data-types:CML_STATIC_BFD_ENABLE_DISABLE_T;
                        description "BFD for static ipv6 vrf";
                    } // END of vrfStaticFallOverBfdV6 definition.


                    list vrfGwAddrIfName {
                        key "ipv6VrfgwIfName";
                        description
                            "gateway interface name for vrf ipv6 type RIB";
                        leaf ipv6VrfgwIfName  {
                            type  cml-data-types:CML_STRING_T;
                            description "IPV6 gateway interface name";
                        } // END of ipv6VrfgwIfName definition.

                    } // End of vrfGwAddrIfName-list
                } // End of vrfIpv6GwAddr-list

                list ribRuntime {
                    key "type";
                    config false;
                    description
                        "route-type";
                    leaf type  {
                        type  cml-data-types:CML_STRING_T;
                        description "rib route type";
                    } // END of type definition.

                    uses ribRuntimeGrp;
                } // End of ribRuntime-list
            } // End of vrfDestPrefix-list
            container ribIpv6VrfAfi {
                config false;
                description
                    "vrf run-time attr for ipv6 type RIB";
                uses ribVrfAfiGrp;
            } // END of ribIpv6VrfAfi-container definition.
        } // End of ribIpv6Vrf-list

        list ribMrouteVRF {
            if-feature feature-list:HAVE_VRF;
            key "vrfName";
            description
                "Mroute vrf";
            leaf vrfName  {
                type  cml-data-types:CML_STRING_T;
                description "vrf name";
            } // END of vrfName definition.


            list ribMroute {
                key "srcPrfix";
                description
                    "mroute Source prefix";
                leaf srcPrfix  {
                    type  cml-data-types:CML_IPV4_PREFIX_T;
                    description "Source prefix";
                } // END of srcPrfix definition.


                list mrouteProtoType {
                    key "mrouteIpv4Proto";
                    description
                        "mroute ipv4 proto type";
                    leaf mrouteIpv4Proto  {
                        type  cml-data-types:CML_MROUTE_ROUTETYPE_T;
                        description "ipv4 mroute prototype";
                    } // END of mrouteIpv4Proto definition.

                    leaf rpfRoute  {
                        type  cml-data-types:CML_IPV4_ADDR_T;
                        description "RPF neighbor address or route";
                    } // END of rpfRoute definition.

                    leaf adminDist  {
                        type  cml-data-types:CML_INT32_T {
                             range "1..255";
                        }
                        description "Administrative distance for mroute";
                    } // END of adminDist definition.

                } // End of mrouteProtoType-list
            } // End of ribMroute-list
        } // End of ribMrouteVRF-list

        list ribIpv6MrouteVRF {
            if-feature feature-list:HAVE_VRF;
            key "vrfName";
            description
                "ipv6 mroute vrf";
            leaf vrfName  {
                type  cml-data-types:CML_STRING_T;
                description "vrf name";
            } // END of vrfName definition.


            list ribMrouteIpv6 {
                if-feature feature-list:HAVE_IPV6;
                key "srcPrfixIpv6";
                description
                    "ipv6 mroute Source prefix";
                leaf srcPrfixIpv6  {
                    type  cml-data-types:CML_IPV6_PREFIX_T;
                    description "Source ipv6 prefix";
                } // END of srcPrfixIpv6 definition.


                list mrouteIpv6ProtoType {
                    key "mrouteIpv6Proto";
                    description
                        "ipv6 mroute proto type";
                    leaf mrouteIpv6Proto  {
                        type  cml-data-types:CML_MROUTE_IPV6_ROUTETYPE_T;
                        description "ipv6 mroute prototype";
                    } // END of mrouteIpv6Proto definition.

                    leaf gwIpv6Mroute  {
                        type  cml-data-types:CML_MROUTE_GW_ADDR_T;
                        description "RPF neighbor address or route";
                    } // END of gwIpv6Mroute definition.

                    leaf adminDist  {
                        type  cml-data-types:CML_INT32_T {
                             range "1..255";
                        }
                        description "Administrative distance for mroute";
                    } // END of adminDist definition.


                    list ipv6MrouteGwAddr {
                        key "mrouteIpv6gwAddr";
                        description
                            "ipv6 mroute nexthop address";
                        leaf mrouteIpv6gwAddr  {
                            type  cml-data-types:CML_IPV6_ADDR_T;
                            description "RPF neighbor address or route";
                        } // END of mrouteIpv6gwAddr definition.


                        list ipv6MrouteGwIfName {
                            key "mrouteIpv6gwIfName";
                            description
                                "ipv6 mroute gateway interface name";
                            leaf mrouteIpv6gwIfName  {
                                type  cml-data-types:CML_STRING_T;
                                description "RPF interface or pseudo interface Null";
                            } // END of mrouteIpv6gwIfName definition.

                            leaf adminDist  {
                                type  cml-data-types:CML_INT32_T {
                                     range "1..255";
                                }
                                description "Administrative distance for mroute";
                            } // END of adminDist definition.

                        } // End of ipv6MrouteGwIfName-list
                    } // End of ipv6MrouteGwAddr-list
                } // End of mrouteIpv6ProtoType-list
            } // End of ribMrouteIpv6-list
        } // End of ribIpv6MrouteVRF-list

        list ribVrf {
            key "vrfName";
            description
                "rib bfd vrf";
            leaf vrfName  {
                type  cml-data-types:CML_STRING_T;
                description "vrf name";
            } // END of vrfName definition.

            leaf ribVrfConfBfdIpv4  {
                type  cml-data-types:CML_BOOL_T;
                description "ipv4 static BFD on all interfaces";
            } // END of ribVrfConfBfdIpv4 definition.

            leaf ribVrfConfBfdIpv6  {
                type  cml-data-types:CML_BOOL_T;
                description "ipv6 static BFD on all interfaces";
            } // END of ribVrfConfBfdIpv6 definition.

        } // End of ribVrf-list
        container ribAfi {
            config false;
            description
                "RIB vrf run-time";
            uses ribVrfAfiGrp;
        } // END of ribAfi-container definition.
        container ribIpv6Afi {
            config false;
            description
                "rib vrf ipv6 run-time attr";
            uses ribVrfAfiGrp;
        } // END of ribIpv6Afi-container definition.
    } // END of rib-container definition.
    } // END of rib-container definition.

    grouping  ribInterface-grouping {
    description
        "RIB BFD interface related operations";
    container ribInterface {
        if-feature feature-list:HAVE_BFD;
        description
            "RIB BFD interface related operations";
        leaf staticBfd  {
            type  cml-data-types:CML_RIB_BFD_STATE;
            description "Bidirectional Forwarding Detection (BFD)";
        } // END of staticBfd definition.

        leaf ipv6StaticBfd  {
            if-feature feature-list:HAVE_IPV6;
            type  cml-data-types:CML_RIB_BFD_STATE;
            description "Ipv6 Bidirectional Forwarding Detection (BFD)";
        } // END of ipv6StaticBfd definition.

    } // END of ribInterface-container definition.
    } // END of ribInterface-container definition.


}
