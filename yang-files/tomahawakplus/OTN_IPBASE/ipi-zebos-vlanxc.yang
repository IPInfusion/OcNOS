/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-vlanxc.yang
*
*/

submodule ipi-zebos-vlanxc {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "VLAN XC Managed Object";


    revision "2019-04-08" {
        description " Initial Version.";
        reference "";
    }



    grouping evc-grouping {
    description
        "list evc's";
        list evc {
            key "xcName";
            description
                "list evc's";
            leaf xcName  {
                type  cml-data-types:CML_STRING_T {
                    length "1..256";
                }
                description "";
            } // END of xcName definition.

            leaf disable  {
                type  cml-data-types:CML_BOOL_T;
                default false;
                description "";
            } // END of disable definition.

            leaf outerVlanid  {
                type  cml-data-types:CML_RANGE_T;
                description "";
            } // END of outerVlanid definition.

            leaf innerVlanid  {
                type  cml-data-types:CML_RANGE_T;
                description "";
            } // END of innerVlanid definition.

            leaf ep1  {
                type  cml-data-types:CML_STRING_T;
                description "";
            } // END of ep1 definition.

            leaf ep2  {
                type  cml-data-types:CML_STRING_T;
                description "";
            } // END of ep2 definition.

        } // End of evc-list
    } // END of evc-grouping definition.


}
