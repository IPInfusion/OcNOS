/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos.yang
*
*/

module ipi-zebos {

    yang-version   1;

    namespace   "http://www.ipinfusion.com/CMLSchema/zebos";

    prefix "ipi-zebos";

    import cml-data-types {
        prefix cml-data-types;
    }

    import feature-list {
        prefix feature-list;
    }

    include ipi-zebos-vr;
    include ipi-zebos-vrf;
    include ipi-zebos-interface;
    include ipi-zebos-broadcom;
    include ipi-zebos-vlan;
    include ipi-zebos-vlanxc;
    include ipi-zebos-switchportinterface;
    include ipi-zebos-bridge;
    include ipi-zebos-mstp;
    include ipi-zebos-lacp;
    include ipi-zebos-lag;
    include ipi-zebos-lldpv2;
    include ipi-zebos-rib;
    include ipi-zebos-ospf;
    include ipi-zebos-ospfv3;
    include ipi-zebos-bgp;
    include ipi-zebos-oambfd;
    include ipi-zebos-vrrp;
    include ipi-zebos-plist;
    include ipi-zebos-isis;
    include ipi-zebos-keychain;
    include ipi-zebos-pim;
    include ipi-zebos-pim4;
    include ipi-zebos-vxlan;
    include ipi-zebos-tfo;
    include ipi-zebos-syslog;
    include ipi-zebos-snmp;
    include ipi-zebos-featuredhcp;
    include ipi-zebos-radius;
    include ipi-zebos-tacacs;
    include ipi-zebos-usermgmt;
    include ipi-zebos-ssh;
    include ipi-zebos-telnet;
    include ipi-zebos-ntp;
    include ipi-zebos-aaa;
    include ipi-zebos-dhcpr;
    include ipi-zebos-dns;
    include ipi-zebos-dhcpc;
    include ipi-zebos-sflow;
    include ipi-zebos-libsyslog;
    include ipi-zebos-license;
    include ipi-zebos-pserv;
    include ipi-zebos-mrib4;
    include ipi-zebos-igmp;
    include ipi-zebos-igmpsnooping;
    include ipi-zebos-routemap;
    include ipi-zebos-libsnmp;
    include ipi-zebos-mcec;
    include ipi-zebos-mlag;
    include ipi-zebos-hqos;
    include ipi-zebos-cmm;
    include ipi-zebos-auth;
    include ipi-zebos-rip;
    include ipi-zebos-acl;
    include ipi-zebos-aclinterface;
    include ipi-zebos-nsmsnmp;
    include ipi-zebos-dhcpsnooping;
    include ipi-zebos-ras;
    include ipi-zebos-rpf;
    include ipi-zebos-linktrack;
    include ipi-zebos-pmirror;
    include ipi-zebos-hsl;
    include ipi-zebos-authradius;
    include ipi-zebos-ripng;
    include ipi-zebos-trill;
    include ipi-zebos-ndd;
    include ipi-zebos-vlog;
    include ipi-zebos-imi;
    include ipi-zebos-rtadv;
    include ipi-zebos-imiLogging;
    include ipi-zebos-nat;
    include ipi-zebos-rbac;
    include ipi-zebos-vm;
    include ipi-zebos-sysupdate;
    include ipi-zebos-system;
    include ipi-zebos-customstats;
    include ipi-zebos-evpn;
    organization
        "IP Infusion Inc.";

    contact
        "Address: 3965 Freedom Circle, Suite 200, Santa Clara, CA 95054
        Phone: +1 408-400-1900
        E-mail: support@ipinfusion.com
        Web: http://www.ipinfusion.com/";

    description
        "ZebOS Managed Object";


    revision "2019-08-23" {
        description " Datemodel for system related commands.";
        reference "";
    }

    revision "2019-05-06" {
        description " Port Group Speed Support.";
        reference "";
    }

    revision "2019-04-08" {
        description " Adding support for VLAN Cross Connect.";
        reference "";
    }

    revision "2018-10-24" {
        description " Adding support for Guest-VM feature.";
        reference "";
    }

    revision "2018-09-18" {
        description " Initial Version.";
        reference "";
    }


    uses ifArbiter-grouping;
    uses cpuInterface-grouping;
    uses hwTCAMutilization-grouping;
    uses lacpMaster-grouping;
    uses lacpdebug-grouping;
    uses lldpDebug-grouping;
    uses oamMpls-grouping;
    uses tfo-grouping;
    uses hostpSyslog-grouping;
    uses snmpStatistics-grouping;
    uses debugSnmp-grouping;
    uses radiusDebug-grouping;
    uses debugTacacs-grouping;
    uses userDebug-grouping;
    uses debugSSHconfig-grouping;
    uses debugTELNETconfig-grouping;
    uses sourceNTP-grouping;
    uses debugNTP-grouping;
    uses AAAUserConfigs-grouping;
    uses console-grouping;
    uses debugAaa-grouping;
    uses dhcpRelay-grouping;
    uses debugDns-grouping;
    uses sflow-grouping;
    uses debugsflow-grouping;
    uses ACLsFlow-grouping;
    uses log-grouping;
    uses licenseServer-grouping;
    uses licenseInfo-grouping;
    uses pservd-grouping;
    uses cmmSoftwareProcessMgmt-grouping;
    uses igmpConfig-grouping;
    uses snmpTrap-grouping;
    uses debugAgentx-grouping;
    uses mcecDebug-grouping;
    uses mcecMaster-grouping;
    uses nsmMlag-grouping;
    uses cmmGlobals-grouping;
    uses cmmDdm-grouping;
    uses cmmCpuLoadThresh-grouping;
    uses cmmCpuCoreThresh-grouping;
    uses cmmAlarmVariable-grouping;
    uses debugdot1x-grouping;
    uses debugDhcpSnooping-grouping;
    uses logginghsl-grouping;
    uses logging-grouping;
    uses memInfo-grouping;
    uses loggingcli-grouping;
    uses imiNatTimeouts-grouping;
    uses installers-grouping;
    uses systemHostname-grouping;
    uses vr-grouping;
    uses evc-grouping;
    uses bfdSession-grouping;
    uses confModeDebug-grouping;
    uses execModeDebug-grouping;
    uses rsyslog-grouping;
    uses snmp-grouping;
    uses radius-grouping;
    uses tacacs-grouping;
    uses usermgmt-grouping;
    uses sshVrfInstance-grouping;
    uses telnetVrfInstance-grouping;
    uses ntp-grouping;
    uses aaa-grouping;
    uses aaaAuthOptions-grouping;
    uses dns-grouping;
    uses logginglevel-grouping;
    uses cmmSoftwareProcessObjects-grouping;
    uses mlagInterfaceConfig-grouping;
    uses cmmCoherentConfigTable-grouping;
    uses cmmCoherentStateTable-grouping;
    uses cmmStackUnitTable-grouping;
    uses nsmsnmp-grouping;
    uses dhcpSnooping-grouping;
    uses defaultbridgedhcpsnooping-grouping;
    uses dhcp_interface-grouping;
    uses interfaceTrack-grouping;
    uses imiNatAddressPool-grouping;
    uses imi_rule_acl-grouping;
    uses imiRuleLocaladdr-grouping;
    uses imiRuleAclDestIn-grouping;
    uses imiRuleLocaladdrDestIn-grouping;
    uses imiRuleAclSrcOut-grouping;
    uses imiRuleLocaladdrSrcOut-grouping;
    uses imiRuleAclOutDest-grouping;
    uses imiRuleLocaladdrOutDest-grouping;
    uses imiRuleLocaladdrStatic-grouping;

    rpc vrf-clear-default-router-id {
        if-feature feature-list:HAVE_L3;
    description "";
    reference "";
        input  {
            leaf vrId  {
                type cml-data-types:CML_UINT32_T;

                mandatory true;
                description "";
            }
        }
    }

    rpc vrf-clear-router-id-vrf {
        if-feature feature-list:HAVE_VRF;
    description "";
    reference "";
        input  {
            leaf vrId  {
                type cml-data-types:CML_UINT32_T;

                mandatory true;
                description "";
            }
            leaf vrfName  {
                type cml-data-types:CML_STRING_T;

                mandatory true;
                description "";
            }
        }
    }

    rpc interface-clear-interface-counter {
    description "";
    reference "";
        input  {
            leaf vrId  {
                type cml-data-types:CML_INT32_T;

                mandatory true;
                description "";
            }
            leaf ifName  {
                type cml-data-types:CML_STRING_T;

                mandatory true;
                description "";
            }
        }
    }

    rpc interface-clear-interface-cpu-counter {
        if-feature feature-list:HAVE_BROADCOM;
    description "";
    reference "";
        input  {
            leaf vrId  {
                type cml-data-types:CML_INT32_T;

                mandatory true;
                description "";
            }
        }
    }

    rpc interface-clear-interface-fec {
    description "";
    reference "";
        input  {
            leaf vrId  {
                type cml-data-types:CML_INT32_T;

                mandatory true;
                description "";
            }
            leaf ifName  {
                type cml-data-types:CML_STRING_T;

                mandatory true;
                description "";
            }
        }
    }

    rpc interface-clear-interface-error-disable {
    description "";
    reference "";
        input  {
            leaf vrId  {
                type cml-data-types:CML_INT32_T;

                mandatory true;
                description "";
            }
            leaf ifName  {
                type cml-data-types:CML_STRING_T;

                mandatory true;
                description "";
            }
        }
    }

    rpc interface-nsm-snmp-restart {
        if-feature feature-list:HAVE_SNMP;
    description "";
    reference "";
    }

    rpc vlan-clearvlanAccessList {
    description "";
    reference "";
        input  {
            leaf vrId  {
                type cml-data-types:CML_UINT32_T;

                mandatory true;
                description "";
            }
            leaf accessMapName  {
                type cml-data-types:CML_STRING_T;

                mandatory true;
                description "";
            }
        }
    }

    rpc bridge-clearFbbMacTable {
    description "";
    reference "";
        input  {
            leaf macType  {
                type cml-data-types:CML_MACTYPE_T;

                mandatory true;
                description "";
            }
            leaf bridgeId  {
                type cml-data-types:CML_STRING_T;

                mandatory true;
                description "";
            }
        }
    }

    rpc bridge-clearFbbMacAddr {
    description "";
    reference "";
        input  {
            leaf macType  {
                type cml-data-types:CML_MACTYPE_T;

                mandatory true;
                description "";
            }
            leaf macAddr  {
                type cml-data-types:CML_STRING_T;

                mandatory true;
                description "";
            }
            leaf bridgeId  {
                type cml-data-types:CML_STRING_T;

                mandatory true;
                description "";
            }
        }
    }

    rpc bridge-clearFbbMacPort {
    description "";
    reference "";
        input  {
            leaf macType  {
                type cml-data-types:CML_MACTYPE_T;

                mandatory true;
                description "";
            }
            leaf ifName  {
                type cml-data-types:CML_STRING_T;

                mandatory true;
                description "";
            }
            leaf bridgeId  {
                type cml-data-types:CML_STRING_T;

                mandatory true;
                description "";
            }
        }
    }

    rpc bridge-clearFbbVlanPort {
    description "";
    reference "";
        input  {
            leaf macType  {
                type cml-data-types:CML_MACTYPE_T;

                mandatory true;
                description "";
            }
            leaf vlanId  {
                type cml-data-types:CML_UINT32_T {
                    range "2..4094";
                }

                mandatory true;
                description "";
            }
            leaf bridgeId  {
                type cml-data-types:CML_STRING_T;

                mandatory true;
                description "";
            }
        }
    }

    rpc bridge-clearvxlan {
    description "";
    reference "";
        input  {
            leaf vrId  {
                type cml-data-types:CML_UINT32_T;

                mandatory true;
                description "";
            }
            leaf vxlan  {
                type cml-data-types:CML_BOOL_T;

                mandatory true;
                description "";
            }
        }
    }

    rpc bridge-clearvxlanmac {
    description "";
    reference "";
        input  {
            leaf vrId  {
                type cml-data-types:CML_UINT32_T;

                mandatory true;
                description "";
            }
            leaf vxlan  {
                type cml-data-types:CML_BOOL_T;

                mandatory true;
                description "";
            }
            leaf macCMLSEPaddr  {
                type cml-data-types:CML_STRING_T;

                mandatory true;
                description "";
            }
            leaf vnid  {
                type cml-data-types:CML_UINT32_T;

                mandatory true;
                description "";
            }
        }
    }

    rpc bridge-clearbridge {
    description "";
    reference "";
        input  {
            leaf vrId  {
                type cml-data-types:CML_UINT32_T;

                mandatory true;
                description "";
            }
            leaf bridgeId  {
                type cml-data-types:CML_STRING_T;

                mandatory true;
                description "";
            }
        }
    }

    rpc bridge-clearDynamicMacAddr {
    description "";
    reference "";
        input  {
            leaf vrId  {
                type cml-data-types:CML_UINT32_T;

                mandatory true;
                description "";
            }
            leaf macAddr  {
                type cml-data-types:CML_STRING_T;

                mandatory true;
                description "";
            }
            leaf bridgeId  {
                type cml-data-types:CML_STRING_T;

                mandatory true;
                description "";
            }
        }
    }

    rpc bridge-clearDynamicMacPort {
    description "";
    reference "";
        input  {
            leaf vrId  {
                type cml-data-types:CML_UINT32_T;

                mandatory true;
                description "";
            }
            leaf ifName  {
                type cml-data-types:CML_STRING_T;

                mandatory true;
                description "";
            }
            leaf bridgeId  {
                type cml-data-types:CML_STRING_T;

                mandatory true;
                description "";
            }
        }
    }

    rpc bridge-clearDynamicMacPortMstpInst {
    description "";
    reference "";
        input  {
            leaf vrId  {
                type cml-data-types:CML_UINT32_T;

                mandatory true;
                description "";
            }
            leaf ifName  {
                type cml-data-types:CML_STRING_T;

                mandatory true;
                description "";
            }
            leaf instanceId  {
                type cml-data-types:CML_UINT32_T;

                mandatory true;
                description "";
            }
            leaf bridgeId  {
                type cml-data-types:CML_STRING_T;

                mandatory true;
                description "";
            }
        }
    }

    rpc bridge-clearDynamicMacVlan {
    description "";
    reference "";
        input  {
            leaf vrId  {
                type cml-data-types:CML_UINT32_T;

                mandatory true;
                description "";
            }
            leaf vlanId  {
                type cml-data-types:CML_INT32_T {
                    range "2..4094";
                }

                mandatory true;
                description "";
            }
            leaf bridgeId  {
                type cml-data-types:CML_STRING_T;

                mandatory true;
                description "";
            }
        }
    }

    rpc bridge-clearnsmipc {
        if-feature feature-list:HAVE_ASYNC;
    description "";
    reference "";
        input  {
            leaf vrId  {
                type cml-data-types:CML_UINT32_T;

                mandatory true;
                description "";
            }
        }
    }

    rpc bridge-clearallowed-ethertypestatistics {
    description "";
    reference "";
        input  {
            leaf vrId  {
                type cml-data-types:CML_UINT32_T;

                mandatory true;
                description "";
            }
        }
    }

    rpc bridge-clearallowed-ethertypestatisticsIFNAME {
    description "";
    reference "";
        input  {
            leaf vrId  {
                type cml-data-types:CML_UINT32_T;

                mandatory true;
                description "";
            }
            leaf ifName  {
                type cml-data-types:CML_STRING_T;

                mandatory true;
                description "";
            }
        }
    }

    rpc bridge-clear-rbridge-trill-vlan-vId {
        if-feature feature-list:HAVE_TRILLD;
    description "";
    reference "";
        input  {
            leaf vrId  {
                type cml-data-types:CML_UINT32_T;

                mandatory true;
                description "";
            }
            leaf vId  {
                type cml-data-types:CML_INT32_T;

                mandatory true;
                description "";
            }
            leaf bridgeId  {
                type cml-data-types:CML_STRING_T;

                mandatory true;
                description "";
            }
        }
    }

    rpc bridge-clear-rbridge-trill-egress-nickname {
        if-feature feature-list:HAVE_TRILLD;
    description "";
    reference "";
        input  {
            leaf vrId  {
                type cml-data-types:CML_UINT32_T;

                mandatory true;
                description "";
            }
            leaf egressNickname  {
                type cml-data-types:CML_STRING_T;

                mandatory true;
                description "";
            }
            leaf bridgeId  {
                type cml-data-types:CML_STRING_T;

                mandatory true;
                description "";
            }
        }
    }

    rpc bridge-clear-rbridge-trill-all {
        if-feature feature-list:HAVE_TRILLD;
    description "";
    reference "";
        input  {
            leaf vrId  {
                type cml-data-types:CML_UINT32_T;

                mandatory true;
                description "";
            }
            leaf bridgeId  {
                type cml-data-types:CML_STRING_T;

                mandatory true;
                description "";
            }
        }
    }

    rpc mstp-clearDetectedProtocols {
    description "";
    reference "";
        input  {
            leaf vrId  {
                type cml-data-types:CML_UINT32_T;

                mandatory true;
                description "";
            }
            leaf bridgeId  {
                type cml-data-types:CML_STRING_T;

                mandatory true;
                description "";
            }
        }
    }

    rpc mstp-clearDetectedProtocolsinterface {
    description "";
    reference "";
        input  {
            leaf vrId  {
                type cml-data-types:CML_UINT32_T;

                mandatory true;
                description "";
            }
            leaf interface  {
                type cml-data-types:CML_STRING_T;

                mandatory true;
                description "";
            }
        }
    }

    rpc mstp-clear-spanning-tree-statistics-instance-bridge {
        if-feature feature-list:HAVE_MSTPD;
        if-feature feature-list:HAVE_PROVIDER_BRIDGE;
        if-feature feature-list:HAVE_B_BEB;
    description "";
    reference "";
        input  {
            leaf vrId  {
                type cml-data-types:CML_UINT32_T;

                mandatory true;
                description "";
            }
            leaf bridgeId  {
                type cml-data-types:CML_STRING_T;

                mandatory true;
                description "";
            }
            leaf instanceTypeId  {
                type cml-data-types:CML_MSTP_INSTANCE_TYPE_T;

                mandatory true;
                description "";
            }
        }
    }

    rpc mstp-clear-spanning-tree-statistics-interface-vlan-bridge {
        if-feature feature-list:HAVE_MSTPD;
        if-feature feature-list:HAVE_PROVIDER_BRIDGE;
        if-feature feature-list:HAVE_B_BEB;
    description "";
    reference "";
        input  {
            leaf vrId  {
                type cml-data-types:CML_UINT32_T;

                mandatory true;
                description "";
            }
            leaf bridgeId  {
                type cml-data-types:CML_STRING_T;

                mandatory true;
                description "";
            }
            leaf ifName  {
                type cml-data-types:CML_STRING_T;

                mandatory true;
                description "";
            }
            leaf vlanStatId  {
                type cml-data-types:CML_UINT16_T {
                    range "2..4094";
                }

                mandatory true;
                description "";
            }
        }
    }

    rpc mstp-clear-spanning-tree-statistics-interface-bridge {
    description "";
    reference "";
        input  {
            leaf vrId  {
                type cml-data-types:CML_UINT32_T;

                mandatory true;
                description "";
            }
            leaf bridgeId  {
                type cml-data-types:CML_STRING_T;

                mandatory true;
                description "";
            }
            leaf ifName  {
                type cml-data-types:CML_STRING_T;

                mandatory true;
                description "";
            }
        }
    }

    rpc mstp-clearspanning-treestatisticsbridgebridgeId {
    description "";
    reference "";
        input  {
            leaf vrId  {
                type cml-data-types:CML_UINT32_T;

                mandatory true;
                description "";
            }
            leaf bridgeId  {
                type cml-data-types:CML_STRING_T;

                mandatory true;
                description "";
            }
        }
    }

    rpc mstp-clearspanning-treestatisticsvlanvlanIdbridgebridgeId {
    description "";
    reference "";
        input  {
            leaf vrId  {
                type cml-data-types:CML_UINT32_T;

                mandatory true;
                description "";
            }
            leaf bridgeId  {
                type cml-data-types:CML_STRING_T;

                mandatory true;
                description "";
            }
            leaf vlanStatId  {
                type cml-data-types:CML_UINT16_T {
                    range "2..4094";
                }

                mandatory true;
                description "";
            }
        }
    }

    rpc mstp-clear-spanning-tree-statistics-interface-instance {
    description "";
    reference "";
        input  {
            leaf vrId  {
                type cml-data-types:CML_UINT32_T;

                mandatory true;
                description "";
            }
            leaf bridgeId  {
                type cml-data-types:CML_STRING_T;

                mandatory true;
                description "";
            }
            leaf ifName  {
                type cml-data-types:CML_STRING_T;

                mandatory true;
                description "";
            }
            leaf instanceTypeId  {
                type cml-data-types:CML_MSTP_INSTANCE_TYPE_T;

                mandatory true;
                description "";
            }
        }
    }

    rpc mstp-mstp-snmp-restart {
        if-feature feature-list:HAVE_SNMP;
    description "";
    reference "";
    }

    rpc lag-lacp-snmp-restart {
        if-feature feature-list:HAVE_SNMP;
    description "";
    reference "";
    }

    rpc lag-clear-all-lacp-counters {
    description "";
    reference "";
    }

    rpc lag-clear-lacp-counters {
    description "";
    reference "";
        input  {
            leaf portPriority  {
                type cml-data-types:CML_UINT16_T {
                    range "1..65535";
                }

                mandatory true;
                description "";
            }
        }
    }

    rpc lldpv2-clear-lldp-counter {
    description "";
    reference "";
        input  {
            leaf vrId  {
                type cml-data-types:CML_INT32_T;

                mandatory true;
                description "";
            }
        }
    }

    rpc lldpv2-lldp-snmp-restart {
        if-feature feature-list:HAVE_SNMP;
    description "";
    reference "";
        input  {
            leaf vrId  {
                type cml-data-types:CML_INT32_T;

                mandatory true;
                description "";
            }
        }
    }

    rpc rib-snmpRestart {
        if-feature feature-list:HAVE_SNMP;
    description "";
    reference "";
    }

    rpc rib-clearIpRouteKernel {
    description "";
    reference "";
        input  {
            leaf vrId  {
                type cml-data-types:CML_UINT32_T;

                mandatory true;
                description "";
            }
        }
    }

    rpc rib-clearIpKernelRoute {
    description "";
    reference "";
        input  {
            leaf vrId  {
                type cml-data-types:CML_UINT32_T;

                mandatory true;
                description "";
            }
        }
    }

    rpc rib-clearIpv6RouteKernel {
        if-feature feature-list:HAVE_IPV6;
    description "";
    reference "";
        input  {
            leaf vrId  {
                type cml-data-types:CML_UINT32_T;

                mandatory true;
                description "";
            }
        }
    }

    rpc rib-clearIpRouteAll {
    description "";
    reference "";
        input  {
            leaf vrId  {
                type cml-data-types:CML_UINT32_T;

                mandatory true;
                description "Virtual router id";
            }
            leaf starPrint  {
                type cml-data-types:CML_STRING_T;

                mandatory true;
                description "all route";
            }
        }
    }

    rpc rib-clearIpRoutePrefix {
    description "";
    reference "";
        input  {
            leaf vrId  {
                type cml-data-types:CML_UINT32_T;

                mandatory true;
                description "Virtual router id";
            }
            leaf prefixAddr  {
                type cml-data-types:CML_IPV4_PREFIX_T;

                mandatory true;
                description "Prefix to be cleared(e.g. 10.0.0.0/8)";
            }
        }
    }

    rpc rib-clearIpv4RouteAll {
    description "";
    reference "";
        input  {
            leaf vrId  {
                type cml-data-types:CML_UINT32_T;

                mandatory true;
                description "Virtual router id";
            }
            leaf starPrint  {
                type cml-data-types:CML_STRING_T;

                mandatory true;
                description "clearing all ipv4 routes";
            }
        }
    }

    rpc rib-clearIpv4RoutePrefix {
    description "";
    reference "";
        input  {
            leaf vrId  {
                type cml-data-types:CML_UINT32_T;

                mandatory true;
                description "Virtual router id";
            }
            leaf prefixAddr  {
                type cml-data-types:CML_IPV4_PREFIX_T;

                mandatory true;
                description "Prefix to be cleared(e.g. 3ffe:506::/32)";
            }
        }
    }

    rpc rib-clearIpv6RouteAll {
        if-feature feature-list:HAVE_IPV6;
    description "";
    reference "";
        input  {
            leaf vrId  {
                type cml-data-types:CML_UINT32_T;

                mandatory true;
                description "Virtual router id";
            }
            leaf starPrint  {
                type cml-data-types:CML_STRING_T;

                mandatory true;
                description "clearing all ipv6 routes";
            }
        }
    }

    rpc rib-clearIpv6RoutePrefix {
    description "";
    reference "";
        input  {
            leaf vrId  {
                type cml-data-types:CML_UINT32_T;

                mandatory true;
                description "Virtual router id";
            }
            leaf prefixIpv6Addr  {
                type cml-data-types:CML_IPV6_PREFIX_T;

                mandatory true;
                description "";
            }
        }
    }

    rpc rib-clearIpVrfRouteAll {
        if-feature feature-list:HAVE_VRF;
    description "";
    reference "";
        input  {
            leaf vrId  {
                type cml-data-types:CML_UINT32_T;

                mandatory true;
                description "Virtual router id";
            }
            leaf vrfName  {
                type cml-data-types:CML_STRING_T;

                mandatory true;
                description "vrf name";
            }
            leaf starPrint  {
                type cml-data-types:CML_STRING_T;

                mandatory true;
                description "clear all ipv4 routes";
            }
        }
    }

    rpc rib-clearIpVrfRoutePrefix {
        if-feature feature-list:HAVE_VRF;
    description "";
    reference "";
        input  {
            leaf vrId  {
                type cml-data-types:CML_UINT32_T;

                mandatory true;
                description "Virtual router id";
            }
            leaf vrfName  {
                type cml-data-types:CML_STRING_T;

                mandatory true;
                description "vrf name";
            }
            leaf prefixAddr  {
                type cml-data-types:CML_IPV4_PREFIX_T;

                mandatory true;
                description "Prefix to be cleared(e.g. 10.0.0.0/8)";
            }
        }
    }

    rpc rib-clearIpv4VrfRouteAll {
        if-feature feature-list:HAVE_VRF;
    description "";
    reference "";
        input  {
            leaf vrId  {
                type cml-data-types:CML_UINT32_T;

                mandatory true;
                description "Virtual router id";
            }
            leaf vrfName  {
                type cml-data-types:CML_STRING_T;

                mandatory true;
                description "vrf name";
            }
            leaf starPrint  {
                type cml-data-types:CML_STRING_T;

                mandatory true;
                description "clear all ipv4 routes";
            }
        }
    }

    rpc rib-clearIpv4VrfRoutePrefix {
        if-feature feature-list:HAVE_VRF;
    description "";
    reference "";
        input  {
            leaf vrId  {
                type cml-data-types:CML_UINT32_T;

                mandatory true;
                description "Virtual router id";
            }
            leaf vrfName  {
                type cml-data-types:CML_STRING_T;

                mandatory true;
                description "vrf name";
            }
            leaf prefixAddr  {
                type cml-data-types:CML_IPV4_PREFIX_T;

                mandatory true;
                description "Prefix to be cleared(e.g. 10.0.0.0/8)";
            }
        }
    }

    rpc rib-clearIpv6VrdRouteAll {
        if-feature feature-list:HAVE_VRF;
        if-feature feature-list:HAVE_IPV6;
    description "";
    reference "";
        input  {
            leaf vrId  {
                type cml-data-types:CML_UINT32_T;

                mandatory true;
                description "Virtual router id";
            }
            leaf vrfName  {
                type cml-data-types:CML_STRING_T;

                mandatory true;
                description "vrf name";
            }
            leaf starPrint  {
                type cml-data-types:CML_STRING_T;

                mandatory true;
                description "clear all ipv6 routes";
            }
        }
    }

    rpc rib-clearIpv6RoutePrefixVrf {
    description "";
    reference "";
        input  {
            leaf vrId  {
                type cml-data-types:CML_UINT32_T;

                mandatory true;
                description "Virtual router id";
            }
            leaf vrfName  {
                type cml-data-types:CML_STRING_T;

                mandatory true;
                description "Virtual router id";
            }
            leaf prefixIpv6Addr  {
                type cml-data-types:CML_IPV6_PREFIX_T;

                mandatory true;
                description "Prefix to be cleared(e.g. 3ffe:506::/32)";
            }
        }
    }

    rpc ospf-restart-ospf-graceful {
        if-feature feature-list:HAVE_RESTART;
    description "";
    reference "";
        input  {
            leaf vrId  {
                type cml-data-types:CML_UINT32_T;

                mandatory true;
                description "";
            }
            leaf restartGracePeriod  {
                type cml-data-types:CML_UINT32_T {
                    range "2..1800";
                }

                mandatory true;
                description "Grace period in seconds";
            }
        }
    }

    rpc ospf-restart-ospf-hitless {
        if-feature feature-list:HAVE_RESTART;
    description "";
    reference "";
        input  {
            leaf vrId  {
                type cml-data-types:CML_UINT32_T;

                mandatory true;
                description "";
            }
            leaf hitlessGracePeriod  {
                type cml-data-types:CML_UINT32_T {
                    range "2..1800";
                }

                mandatory true;
                description "";
            }
        }
    }

    rpc ospf-ospf-snmp-restart {
        if-feature feature-list:HAVE_SNMP;
    description "";
    reference "";
    }

    rpc ospf-clear-ospf-process {
    description "";
    reference "";
        input  {
            leaf vrId  {
                type cml-data-types:CML_UINT32_T;

                mandatory true;
                description "";
            }
        }
    }

    rpc ospf-clear-ospf-process-id {
    description "";
    reference "";
        input  {
            leaf vrId  {
                type cml-data-types:CML_UINT32_T;

                mandatory true;
                description "";
            }
            leaf procId  {
                type cml-data-types:CML_UINT32_T {
                    range "0..65535";
                }

                mandatory true;
                description "";
            }
        }
    }

    rpc ospfv3-ospf6-clear {
    description "";
    reference "";
        input  {
            leaf vrId  {
                type cml-data-types:CML_UINT32_T;

                mandatory true;
                description "Virtual Router ID numeric";
            }
            leaf ospfProcess  {
                type cml-data-types:CML_STRING_T;

                mandatory true;
                description "";
            }
        }
    }

    rpc ospfv3-ospf6-restart-hitless {
    description "";
    reference "";
        input  {
            leaf vrId  {
                type cml-data-types:CML_UINT32_T;

                mandatory true;
                description "";
            }
            leaf gracePeriod  {
                type cml-data-types:CML_UINT32_T {
                    range "2..1800";
                }

                mandatory true;
                description "";
            }
        }
    }

    rpc ospfv3-ospf6-restart {
    description "";
    reference "";
        input  {
            leaf vrId  {
                type cml-data-types:CML_UINT32_T;

                mandatory true;
                description "";
            }
            leaf gracePeriod  {
                type cml-data-types:CML_UINT32_T {
                    range "2..1800";
                }

                mandatory true;
                description "";
            }
        }
    }

    rpc ospfv3-ospf6-snmp-restart {
        if-feature feature-list:HAVE_SNMP;
    description "";
    reference "";
    }

    rpc bgp-restartBgp {
        if-feature feature-list:HAVE_RESTART;
    description "";
    reference "";
    }

    rpc bgp-clearBgpStatistics {
    description "";
    reference "";
    }

    rpc bgp-clearIpBgpAll {
    description "";
    reference "";
        input  {
            leaf view  {
                type cml-data-types:CML_STRING_T;

                mandatory true;
                description "bgp view name (default=NULL)";
            }
            leaf afi  {
                type cml-data-types:CML_AFI_TYPE_T;

                mandatory true;
                description "BGP 'afi' Types";
            }
            leaf safi  {
                type cml-data-types:CML_SAFI_TYPE_T;

                mandatory true;
                description "BGP 'safi' Types";
            }
            leaf clearType  {
                type cml-data-types:CML_CLEAR_TYPE_T;

                mandatory true;
                description "BGP 'clear' Types";
            }
            leaf clearSoft  {
                type cml-data-types:CML_CLEAR_SOFT_T;

                mandatory true;
                description "clear flag for peer soft, route flap dampening and table map";
            }
            leaf arg  {
                type cml-data-types:CML_HOSTNAME_T;

                mandatory true;
                description "input arguments (peer Address,prefix address, peer-group name, bgp As)";
            }
            leaf vrId  {
                type cml-data-types:CML_UINT32_T;

                mandatory true;
                description "";
            }
        }
    }

    rpc bgp-clearIpBgpAllPeerVrf {
    description "";
    reference "";
        input  {
            leaf vrfName  {
                type cml-data-types:CML_STRING_T;

                mandatory true;
                description "vrf name";
            }
            leaf afi  {
                type cml-data-types:CML_AFI_TYPE_T;

                mandatory true;
                description "BGP 'afi' Types";
            }
            leaf safi  {
                type cml-data-types:CML_SAFI_TYPE_T;

                mandatory true;
                description "BGP 'safi' Types";
            }
            leaf clearType  {
                type cml-data-types:CML_CLEAR_TYPE_T;

                mandatory true;
                description "BGP 'clear' Types";
            }
            leaf clearSoft  {
                type cml-data-types:CML_CLEAR_SOFT_T;

                mandatory true;
                description "clear flag for peer soft, route flap dampening and table map";
            }
            leaf arg  {
                type cml-data-types:CML_IP_PREFIX_ADDR_T;

                mandatory true;
                description "input arguments (peer Address,prefix address, peer-group name, bgp As)";
            }
            leaf vrId  {
                type cml-data-types:CML_UINT32_T;

                mandatory true;
                description "";
            }
        }
    }

    rpc bgp-clearIpBgpAllVrf {
    description "";
    reference "";
        input  {
            leaf vrfName  {
                type cml-data-types:CML_STRING_T;

                mandatory true;
                description "vrf name";
            }
            leaf afi  {
                type cml-data-types:CML_AFI_TYPE_T;

                mandatory true;
                description "BGP 'afi' Types";
            }
            leaf safi  {
                type cml-data-types:CML_SAFI_TYPE_T;

                mandatory true;
                description "BGP 'safi' Types";
            }
            leaf clearType  {
                type cml-data-types:CML_CLEAR_TYPE_T;

                mandatory true;
                description "BGP 'clear' Types";
            }
            leaf clearSoft  {
                type cml-data-types:CML_CLEAR_SOFT_T;

                mandatory true;
                description "clear flag for peer soft, route flap dampening and table map";
            }
            leaf arg  {
                type cml-data-types:CML_IP_PREFIX_ADDR_T;

                mandatory true;
                description "input arguments (peer Address,prefix address, peer-group name, bgp As)";
            }
            leaf vrId  {
                type cml-data-types:CML_UINT32_T;

                mandatory true;
                description "";
            }
        }
    }

    rpc oambfd-bfd-snmp-restart {
        if-feature feature-list:HAVE_SNMP;
    description "";
    reference "";
    }

    rpc vrrp-snmp-restart-vrrp {
        if-feature feature-list:HAVE_SNMP;
    description "";
    reference "";
    }

    rpc vrrp-clear-vrrp-statistics {
    description "";
    reference "";
        input  {
            leaf vrId  {
                type cml-data-types:CML_UINT32_T;

                mandatory true;
                description "";
            }
        }
    }

    rpc vrrp-clear-vrrp-ipv4-statistics {
    description "";
    reference "";
        input  {
            leaf vrId  {
                type cml-data-types:CML_UINT32_T;

                mandatory true;
                description "";
            }
        }
    }

    rpc vrrp-clear-vrrp-ipv6-statistics {
    description "";
    reference "";
        input  {
            leaf vrId  {
                type cml-data-types:CML_UINT32_T;

                mandatory true;
                description "";
            }
        }
    }

    rpc vrrp-clear-vrrp-session-ipv4-statistics {
    description "";
    reference "";
        input  {
            leaf vrId  {
                type cml-data-types:CML_UINT32_T;

                mandatory true;
                description "";
            }
            leaf vrrpid  {
                type cml-data-types:CML_INT32_T {
                    range "1..255";
                }

                mandatory true;
                description "";
            }
            leaf ifName  {
                type cml-data-types:CML_STRING_T;

                mandatory true;
                description "";
            }
        }
    }

    rpc vrrp-clear-vrrp-session-ipv6-statistics {
    description "";
    reference "";
        input  {
            leaf vrId  {
                type cml-data-types:CML_UINT32_T;

                mandatory true;
                description "";
            }
            leaf vrrp6id  {
                type cml-data-types:CML_INT32_T {
                    range "1..255";
                }

                mandatory true;
                description "";
            }
            leaf ifName  {
                type cml-data-types:CML_STRING_T;

                mandatory true;
                description "";
            }
        }
    }

    rpc plist-clear-ip-prefix {
    description "";
    reference "";
        input  {
            leaf vrId  {
                type cml-data-types:CML_UINT32_T;

                mandatory true;
                description "";
            }
        }
    }

    rpc plist-clear-ip-prefix-by-name {
    description "";
    reference "";
        input  {
            leaf vrId  {
                type cml-data-types:CML_UINT32_T;

                mandatory true;
                description "";
            }
            leaf name  {
                type cml-data-types:CML_STRING_T;

                mandatory true;
                description "";
            }
        }
    }

    rpc plist-clear-ip-prefix-by-prefix {
    description "";
    reference "";
        input  {
            leaf vrId  {
                type cml-data-types:CML_UINT32_T;

                mandatory true;
                description "";
            }
            leaf name  {
                type cml-data-types:CML_STRING_T;

                mandatory true;
                description "";
            }
            leaf prefix  {
                type cml-data-types:CML_IPV4_ADDR_PREFIX_T;

                mandatory true;
                description "";
            }
        }
    }

    rpc plist-clear-ipv6-prefix {
    description "";
    reference "";
        input  {
            leaf vrId  {
                type cml-data-types:CML_UINT32_T;

                mandatory true;
                description "";
            }
        }
    }

    rpc plist-clear-ipv6-prefix-by-name {
    description "";
    reference "";
        input  {
            leaf vrId  {
                type cml-data-types:CML_UINT32_T;

                mandatory true;
                description "";
            }
            leaf name  {
                type cml-data-types:CML_STRING_T;

                mandatory true;
                description "";
            }
        }
    }

    rpc plist-clear-ipv6-prefix-by-prefix {
    description "";
    reference "";
        input  {
            leaf vrId  {
                type cml-data-types:CML_UINT32_T;

                mandatory true;
                description "";
            }
            leaf name  {
                type cml-data-types:CML_STRING_T;

                mandatory true;
                description "";
            }
            leaf prefix  {
                type cml-data-types:CML_IPV6_PREFIX_T;

                mandatory true;
                description "";
            }
        }
    }

    rpc isis-isis-restart {
        if-feature feature-list:HAVE_RESTART;
    description "";
    reference "";
        input  {
            leaf vrId  {
                type cml-data-types:CML_UINT32_T;

                mandatory true;
                description "";
            }
            leaf graceCMLSEPperiod  {
                type cml-data-types:CML_UINT16_T {
                    range "1..65535";
                }

                mandatory true;
                description "";
            }
        }
    }

    rpc isis-clear-is-neighbors {
    description "";
    reference "";
        input  {
            leaf vrId  {
                type cml-data-types:CML_UINT32_T;

                mandatory true;
                description "";
            }
            leaf SystemID  {
                type cml-data-types:CML_STRING_T;

                mandatory true;
                description "";
            }
        }
    }

    rpc isis-clear-neighbors {
    description "";
    reference "";
        input  {
            leaf vrId  {
                type cml-data-types:CML_UINT32_T;

                mandatory true;
                description "";
            }
        }
    }

    rpc isis-clear-ip-route {
    description "";
    reference "";
        input  {
            leaf vrId  {
                type cml-data-types:CML_UINT32_T;

                mandatory true;
                description "";
            }
            leaf isisInstanceTag  {
                type cml-data-types:CML_STRING_T;

                mandatory true;
                description "";
            }
            leaf ipv4route  {
                type cml-data-types:CML_ISIS_ROUTE_T;

                mandatory true;
                description "";
            }
        }
    }

    rpc isis-clear-ipv6-route {
    description "";
    reference "";
        input  {
            leaf vrId  {
                type cml-data-types:CML_UINT32_T;

                mandatory true;
                description "";
            }
            leaf isisInstanceTag  {
                type cml-data-types:CML_STRING_T;

                mandatory true;
                description "";
            }
            leaf ipv6route  {
                type cml-data-types:CML_ISIS_ROUTE_T;

                mandatory true;
                description "";
            }
        }
    }

    rpc isis-isis-proc-clear {
    description "";
    reference "";
        input  {
            leaf vrId  {
                type cml-data-types:CML_UINT32_T;

                mandatory true;
                description "";
            }
            leaf isisInstanceTag  {
                type cml-data-types:CML_STRING_T;

                mandatory true;
                description "";
            }
        }
    }

    rpc isis-isis-clear-counters {
    description "";
    reference "";
        input  {
            leaf vrId  {
                type cml-data-types:CML_UINT32_T;

                mandatory true;
                description "";
            }
        }
    }

    rpc isis-clear-interface-counters {
    description "";
    reference "";
        input  {
            leaf vrId  {
                type cml-data-types:CML_UINT32_T;

                mandatory true;
                description "";
            }
            leaf ifName  {
                type cml-data-types:CML_STRING_T;

                mandatory true;
                description "";
            }
        }
    }

    rpc isis-clear-adjacency-all {
    description "";
    reference "";
        input  {
            leaf vrId  {
                type cml-data-types:CML_UINT32_T;

                mandatory true;
                description "";
            }
            leaf adjall  {
                type cml-data-types:CML_BOOL_T;

                mandatory true;
                description "";
            }
            leaf adjvrfname  {
                type cml-data-types:CML_STRING_T;

                mandatory true;
                description "";
            }
        }
    }

    rpc isis-clear-adjacency-word-all {
    description "";
    reference "";
        input  {
            leaf vrId  {
                type cml-data-types:CML_UINT32_T;

                mandatory true;
                description "";
            }
            leaf tagname  {
                type cml-data-types:CML_STRING_T;

                mandatory true;
                description "";
            }
            leaf adjall  {
                type cml-data-types:CML_BOOL_T;

                mandatory true;
                description "";
            }
            leaf adjvrfname  {
                type cml-data-types:CML_STRING_T;

                mandatory true;
                description "";
            }
        }
    }

    rpc isis-clear-adjacency-word-ifname {
    description "";
    reference "";
        input  {
            leaf vrId  {
                type cml-data-types:CML_UINT32_T;

                mandatory true;
                description "";
            }
            leaf tagname  {
                type cml-data-types:CML_STRING_T;

                mandatory true;
                description "";
            }
            leaf tagifname  {
                type cml-data-types:CML_STRING_T;

                mandatory true;
                description "";
            }
            leaf adjvrfname  {
                type cml-data-types:CML_STRING_T;

                mandatory true;
                description "";
            }
        }
    }

    rpc isis-clear-adjacency-ifname {
    description "";
    reference "";
        input  {
            leaf vrId  {
                type cml-data-types:CML_UINT32_T;

                mandatory true;
                description "";
            }
            leaf adjifname  {
                type cml-data-types:CML_STRING_T;

                mandatory true;
                description "";
            }
            leaf adjvrfname  {
                type cml-data-types:CML_STRING_T;

                mandatory true;
                description "";
            }
        }
    }

    rpc isis-clear-adjacency-word-systemid {
    description "";
    reference "";
        input  {
            leaf vrId  {
                type cml-data-types:CML_UINT32_T;

                mandatory true;
                description "";
            }
            leaf tagname  {
                type cml-data-types:CML_STRING_T;

                mandatory true;
                description "";
            }
            leaf tagsystemid  {
                type cml-data-types:CML_ISIS_SYSTEMID_T;

                mandatory true;
                description "";
            }
            leaf tagvrfname  {
                type cml-data-types:CML_STRING_T;

                mandatory true;
                description "";
            }
        }
    }

    rpc isis-clear-adjacency-systemid {
    description "";
    reference "";
        input  {
            leaf vrId  {
                type cml-data-types:CML_UINT32_T;

                mandatory true;
                description "";
            }
            leaf adjsystemid  {
                type cml-data-types:CML_ISIS_SYSTEMID_T;

                mandatory true;
                description "";
            }
            leaf adjvrfname  {
                type cml-data-types:CML_STRING_T;

                mandatory true;
                description "";
            }
        }
    }

    rpc isis-snmp-restart-isis {
        if-feature feature-list:HAVE_SNMP;
    description "";
    reference "";
    }

    rpc pim-snmp-restart-pim {
        if-feature feature-list:HAVE_SNMP;
    description "";
    reference "";
    }

    rpc pim4-clear-ip-mroute {
    description "";
    reference "";
        input  {
            leaf vrId  {
                type cml-data-types:CML_UINT32_T;

                mandatory true;
                description "";
            }
            leaf vrfName  {
                type cml-data-types:CML_STRING_T;

                mandatory true;
                description "";
            }
            leaf allFlag  {
                type cml-data-types:CML_BOOL_T;

                mandatory true;
                description "";
            }
            leaf pimmode  {
                type cml-data-types:CML_PIM_MODE_TYPE_T;

                mandatory true;
                description "";
            }
        }
    }

    rpc pim4-clear-ip-mroute-xg {
    description "";
    reference "";
        input  {
            leaf vrId  {
                type cml-data-types:CML_UINT32_T;

                mandatory true;
                description "";
            }
            leaf vrfName  {
                type cml-data-types:CML_STRING_T;

                mandatory true;
                description "";
            }
            leaf mrouteXg  {
                type cml-data-types:CML_IPV4_ADDR_T;

                mandatory true;
                description "";
            }
        }
    }

    rpc pim4-clear-ip-mroute-sg {
    description "";
    reference "";
        input  {
            leaf vrId  {
                type cml-data-types:CML_UINT32_T;

                mandatory true;
                description "";
            }
            leaf vrfName  {
                type cml-data-types:CML_STRING_T;

                mandatory true;
                description "";
            }
            leaf mrouteGaddr  {
                type cml-data-types:CML_IPV4_ADDR_T;

                mandatory true;
                description "";
            }
            leaf mrouteSaddr  {
                type cml-data-types:CML_IPV4_ADDR_T;

                mandatory true;
                description "";
            }
            leaf pimgsmode  {
                type cml-data-types:CML_PIM_MODE_TYPE_T;

                mandatory true;
                description "";
            }
        }
    }

    rpc pim4-clear-ip-pim {
        if-feature feature-list:HAVE_PIM_SM;
    description "";
    reference "";
        input  {
            leaf vrId  {
                type cml-data-types:CML_UINT32_T;

                mandatory true;
                description "";
            }
            leaf vrfName  {
                type cml-data-types:CML_STRING_T;

                mandatory true;
                description "";
            }
            leaf allRp  {
                type cml-data-types:CML_BOOL_T;

                mandatory true;
                description "";
            }
        }
    }

    rpc vxlan-clear-nvo-id-vxlan-tunnels {
        if-feature feature-list:HAVE_VXLAN;
    description "";
    reference "";
        input  {
            leaf vrId  {
                type cml-data-types:CML_INT32_T;

                mandatory true;
                description "";
            }
        }
    }

    rpc vxlan-clear-nvo-id-access-port {
        if-feature feature-list:HAVE_VXLAN;
    description "";
    reference "";
        input  {
            leaf vrId  {
                type cml-data-types:CML_INT32_T;

                mandatory true;
                description "";
            }
            leaf ifName  {
                type cml-data-types:CML_STRING_T;

                mandatory true;
                description "";
            }
        }
    }

    rpc vxlan-clear-nvo-id-acess-port-vlan {
        if-feature feature-list:HAVE_VXLAN;
    description "";
    reference "";
        input  {
            leaf vrId  {
                type cml-data-types:CML_INT32_T;

                mandatory true;
                description "";
            }
            leaf ifName  {
                type cml-data-types:CML_STRING_T;

                mandatory true;
                description "";
            }
            leaf vlanId  {
                type cml-data-types:CML_UINT32_T;

                mandatory true;
                description "";
            }
            leaf innerVlanId  {
                type cml-data-types:CML_UINT32_T {
                    range "2..4094";
                }

                mandatory true;
                description "";
            }
        }
    }

    rpc vxlan-clear-nvo-id-access-all {
        if-feature feature-list:HAVE_VXLAN;
    description "";
    reference "";
        input  {
            leaf vrId  {
                type cml-data-types:CML_INT32_T;

                mandatory true;
                description "";
            }
            leaf clearAllCounter  {
                type cml-data-types:CML_BOOL_T;

                mandatory true;
                description "";
            }
            leaf vnId  {
                type cml-data-types:CML_INT32_T {
                    range "1..16777215";
                }

                mandatory true;
                description "";
            }
        }
    }

    rpc vxlan-clear-nvo-id-network-all {
        if-feature feature-list:HAVE_VXLAN;
    description "";
    reference "";
        input  {
            leaf vrId  {
                type cml-data-types:CML_INT32_T;

                mandatory true;
                description "";
            }
            leaf clearNetworkAllCounter  {
                type cml-data-types:CML_BOOL_T;

                mandatory true;
                description "";
            }
        }
    }

    rpc vxlan-clear-nvo-id-network-port {
        if-feature feature-list:HAVE_VXLAN;
    description "";
    reference "";
        input  {
            leaf vrId  {
                type cml-data-types:CML_INT32_T;

                mandatory true;
                description "";
            }
            leaf destIpv4  {
                type cml-data-types:CML_STRING_T;

                mandatory true;
                description "";
            }
        }
    }

    rpc vxlan-clear-nvo-vxlan-mac-stale-entries {
        if-feature feature-list:HAVE_VXLAN;
    description "";
    reference "";
        input  {
            leaf vrId  {
                type cml-data-types:CML_INT32_T;

                mandatory true;
                description "";
            }
            leaf vnId  {
                type cml-data-types:CML_INT32_T {
                    range "1..16777215";
                }

                mandatory true;
                description "";
            }
        }
    }

    rpc tfo-cleartfocounter {
        if-feature feature-list:HAVE_TFO;
    description "";
    reference "";
    }

    rpc tfo-cleartfocounterfog {
        if-feature feature-list:HAVE_TFO;
    description "";
    reference "";
        input  {
            leaf fognum  {
                type cml-data-types:CML_UINT32_T {
                    range "1..64";
                }

                mandatory true;
                description "";
            }
        }
    }

    rpc snmp-clear-snmp-hostconfig {
    description "";
    reference "";
    }

    rpc radius-clear-radius-server-counters {
    description "";
    reference "";
        input  {
            leaf vrfName  {
                type cml-data-types:CML_STRING_T;

                mandatory true;
                description "";
            }
        }
    }

    rpc radius-clear-radius-server-name-counters {
    description "";
    reference "";
        input  {
            leaf hostname  {
                type cml-data-types:CML_HOSTPNAME_T;

                mandatory true;
                description "";
            }
            leaf vrfName  {
                type cml-data-types:CML_STRING_T;

                mandatory true;
                description "";
            }
        }
    }

    rpc tacacs-clear-tacacs-server-counters {
    description "";
    reference "";
        input  {
            leaf vrfName  {
                type cml-data-types:CML_STRING_T;

                mandatory true;
                description "";
            }
        }
    }

    rpc tacacs-clear-tacacs-server-name-counters {
    description "";
    reference "";
        input  {
            leaf hostname  {
                type cml-data-types:CML_HOSTPNAME_T;

                mandatory true;
                description "";
            }
            leaf vrfName  {
                type cml-data-types:CML_STRING_T;

                mandatory true;
                description "";
            }
        }
    }

    rpc usermgmt-user {
        if-feature feature-list:HAVE_USER_MGMT;
    description "";
    reference "";
        input  {
            leaf user  {
                type cml-data-types:CML_STRING_T;

                mandatory true;
                description "";
            }
        }
    }

    rpc ssh-lengthRSA {
        if-feature feature-list:HAVE_SSH_SERVER;
    description "";
    reference "";
        input  {
            leaf usernameRSA  {
                type cml-data-types:CML_STRING_T;

                mandatory true;
                description "";
            }
            leaf keyRSA  {
                type cml-data-types:CML_BOOL_T;

                mandatory true;
                description "";
            }
            leaf lengthRSA  {
                type cml-data-types:CML_UINT32_T {
                    range "768..4096";
                }

                mandatory true;
                description "";
            }
            leaf forceRSA  {
                type cml-data-types:CML_BOOL_T;

                mandatory true;
                description "";
            }
        }
    }

    rpc ssh-keyDSA {
        if-feature feature-list:HAVE_SSH_SERVER;
    description "";
    reference "";
        input  {
            leaf usernameDSA  {
                type cml-data-types:CML_STRING_T;

                mandatory true;
                description "";
            }
            leaf keyDSA  {
                type cml-data-types:CML_BOOL_T;

                mandatory true;
                description "";
            }
            leaf forceDSA  {
                type cml-data-types:CML_BOOL_T;

                mandatory true;
                description "";
            }
        }
    }

    rpc ssh-keyGenRSA {
        if-feature feature-list:HAVE_SSH_SERVER;
    description "";
    reference "";
        input  {
            leaf keyGenRSA  {
                type cml-data-types:CML_BOOL_T;

                mandatory true;
                description "";
            }
            leaf keyGenlengthRSA  {
                type cml-data-types:CML_UINT32_T {
                    range "768..4096";
                }

                mandatory true;
                description "";
            }
            leaf keyGenforceRSA  {
                type cml-data-types:CML_BOOL_T;

                mandatory true;
                description "";
            }
            leaf vrfName  {
                type cml-data-types:CML_STRING_T;

                mandatory true;
                description "";
            }
        }
    }

    rpc ssh-keyDelRSA {
        if-feature feature-list:HAVE_SSH_SERVER;
    description "";
    reference "";
        input  {
            leaf keyDelRSA  {
                type cml-data-types:CML_BOOL_T;

                mandatory true;
                description "";
            }
            leaf vrfName  {
                type cml-data-types:CML_STRING_T;

                mandatory true;
                description "";
            }
        }
    }

    rpc ssh-keyGenDSA {
        if-feature feature-list:HAVE_SSH_SERVER;
    description "";
    reference "";
        input  {
            leaf keyGenDSA  {
                type cml-data-types:CML_BOOL_T;

                mandatory true;
                description "";
            }
            leaf keyGenforceDSA  {
                type cml-data-types:CML_BOOL_T;

                mandatory true;
                description "";
            }
            leaf vrfName  {
                type cml-data-types:CML_STRING_T;

                mandatory true;
                description "";
            }
        }
    }

    rpc ssh-keyDelDSA {
        if-feature feature-list:HAVE_SSH_SERVER;
    description "";
    reference "";
        input  {
            leaf keyDelDSA  {
                type cml-data-types:CML_BOOL_T;

                mandatory true;
                description "";
            }
            leaf vrfName  {
                type cml-data-types:CML_STRING_T;

                mandatory true;
                description "";
            }
        }
    }

    rpc ssh-keyDelSSHkeys {
        if-feature feature-list:HAVE_SSH_SERVER;
    description "";
    reference "";
        input  {
            leaf keyDelSSHkeys  {
                type cml-data-types:CML_BOOL_T;

                mandatory true;
                description "";
            }
            leaf vrfName  {
                type cml-data-types:CML_STRING_T;

                mandatory true;
                description "";
            }
        }
    }

    rpc ssh-clearSSHhosts {
        if-feature feature-list:HAVE_SSH_SERVER;
    description "";
    reference "";
        input  {
            leaf clearSSHhosts  {
                type cml-data-types:CML_BOOL_T;

                mandatory true;
                description "";
            }
        }
    }

    rpc ntp-sync-retry {
        if-feature feature-list:HAVE_HOSTP_NTP;
    description "";
    reference "";
        input  {
            leaf vrfName  {
                type cml-data-types:CML_STRING_T;

                mandatory true;
                description "";
            }
        }
    }

    rpc ntp-clear {
        if-feature feature-list:HAVE_HOSTP_NTP;
    description "";
    reference "";
        input  {
            leaf statistics  {
                type cml-data-types:CML_CLEAR_NTP_STATISTICS_T;

                mandatory true;
                description "";
            }
        }
    }

    rpc aaa-lockout {
        if-feature feature-list:HAVE_HOSTPD;
        if-feature feature-list:HAVE_AAA;
    description "";
    reference "";
        input  {
            leaf username  {
                type cml-data-types:CML_STRING_T {
                    length "2..15";
                }

                mandatory true;
                description "";
            }
        }
    }

    rpc sflow-clearaccess-listlog-cache {
        if-feature feature-list:HAVE_ACL;
    description "";
    reference "";
    }

    rpc sflow-clearsflowstatistics {
    description "";
    reference "";
        input  {
            leaf interface  {
                type cml-data-types:CML_STRING_T;

                mandatory true;
                description "";
            }
        }
    }

    rpc libsyslog-cleardebuglogfile {
    description "";
    reference "";
    }

    rpc libsyslog-clearlogginglogfile {
    description "";
    reference "";
    }

    rpc license-get {
        if-feature feature-list:HAVE_FLEXLM;
    description "";
    reference "";
        input  {
            leaf sourceCMLSEPinterface  {
                type cml-data-types:CML_STRING_T;

                mandatory true;
                description "";
            }
            leaf url  {
                type cml-data-types:CML_STRING_T;

                mandatory true;
                description "";
            }
        }
    }

    rpc license-refresh {
        if-feature feature-list:HAVE_FLEXLM;
    description "";
    reference "";
        input  {
            leaf licenseCMLSEPfile  {
                type cml-data-types:CML_STRING_T;

                mandatory true;
                description "";
            }
        }
    }

    rpc license-get-pool {
    description "";
    reference "";
        input  {
            leaf serverUrl  {
                type cml-data-types:CML_STRING_T;

                mandatory true;
                description "";
            }
            leaf vrfName  {
                type cml-data-types:CML_STRING_T;

                mandatory true;
                description "";
            }
        }
    }

    rpc license-release {
    description "";
    reference "";
    }

    rpc pserv-clearCores {
        if-feature feature-list:HAVE_PSERVD;
        if-feature feature-list:HAVE_ZEBOS_CORE_ANALYSER;
    description "";
    reference "";
        input  {
            leaf clearCore  {
                type cml-data-types:CML_STRING_T;

                mandatory true;
                description "";
            }
        }
    }

    rpc mrib4-snmp-restart-mrib {
        if-feature feature-list:HAVE_SNMP;
    description "";
    reference "";
    }

    rpc mrib4-mrib-bulking-start {
        if-feature feature-list:HAVE_ASYNC;
    description "";
    reference "";
    }

    rpc mrib4-mrib-bulking-stop {
        if-feature feature-list:HAVE_ASYNC;
    description "";
    reference "";
    }

    rpc mrib4-mrib-bulking-flush {
        if-feature feature-list:HAVE_ASYNC;
    description "";
    reference "";
    }

    rpc mrib4-clear-mrib-vrf-all {
    description "";
    reference "";
        input  {
            leaf vrId  {
                type cml-data-types:CML_UINT32_T;

                mandatory true;
                description "";
            }
            leaf vrfName  {
                type cml-data-types:CML_STRING_T;

                mandatory true;
                description "";
            }
            leaf allroute  {
                type cml-data-types:CML_BOOL_T;

                mandatory true;
                description "";
            }
        }
    }

    rpc mrib4-clear-mrib-grp {
    description "";
    reference "";
        input  {
            leaf vrId  {
                type cml-data-types:CML_UINT32_T;

                mandatory true;
                description "";
            }
            leaf vrfName  {
                type cml-data-types:CML_STRING_T;

                mandatory true;
                description "";
            }
            leaf grpAddr  {
                type cml-data-types:CML_IPV4_ADDR_T;

                mandatory true;
                description "";
            }
        }
    }

    rpc mrib4-clear-mrib-vrf-src-grp {
    description "";
    reference "";
        input  {
            leaf vrId  {
                type cml-data-types:CML_UINT32_T;

                mandatory true;
                description "";
            }
            leaf vrfName  {
                type cml-data-types:CML_STRING_T;

                mandatory true;
                description "";
            }
            leaf srcAddr  {
                type cml-data-types:CML_IPV4_ADDR_T;

                mandatory true;
                description "";
            }
            leaf grpAddr  {
                type cml-data-types:CML_IPV4_ADDR_T;

                mandatory true;
                description "";
            }
        }
    }

    rpc mrib4-clear-mrib-stats-all {
    description "";
    reference "";
        input  {
            leaf vrId  {
                type cml-data-types:CML_UINT32_T;

                mandatory true;
                description "";
            }
            leaf vrfName  {
                type cml-data-types:CML_STRING_T;

                mandatory true;
                description "";
            }
            leaf allroute  {
                type cml-data-types:CML_BOOL_T;

                mandatory true;
                description "";
            }
        }
    }

    rpc mrib4-clear-mrib-vrf-grp-stats {
    description "";
    reference "";
        input  {
            leaf vrId  {
                type cml-data-types:CML_UINT32_T;

                mandatory true;
                description "";
            }
            leaf vrfName  {
                type cml-data-types:CML_STRING_T;

                mandatory true;
                description "";
            }
            leaf grpAddr  {
                type cml-data-types:CML_IPV4_ADDR_T;

                mandatory true;
                description "";
            }
        }
    }

    rpc mrib4-clear-mrib-vrf-src-grp-stats {
    description "";
    reference "";
        input  {
            leaf vrId  {
                type cml-data-types:CML_UINT32_T;

                mandatory true;
                description "";
            }
            leaf vrfName  {
                type cml-data-types:CML_STRING_T;

                mandatory true;
                description "";
            }
            leaf srcAddr  {
                type cml-data-types:CML_IPV4_ADDR_T;

                mandatory true;
                description "";
            }
            leaf grpAddr  {
                type cml-data-types:CML_IPV4_ADDR_T;

                mandatory true;
                description "";
            }
        }
    }

    rpc igmp-mrib4-igmp-group-clear {
    description "";
    reference "";
        input  {
            leaf vrfName  {
                type cml-data-types:CML_STRING_T;

                mandatory true;
                description "";
            }
            leaf groupAddr  {
                type cml-data-types:CML_IPV4_ADDR_T;

                mandatory true;
                description "";
            }
            leaf ifName  {
                type cml-data-types:CML_STRING_T;

                mandatory true;
                description "";
            }
        }
    }

    rpc igmp-mrib4-igmp-interface-clear {
    description "";
    reference "";
        input  {
            leaf vrfName  {
                type cml-data-types:CML_STRING_T;

                mandatory true;
                description "";
            }
            leaf ifName  {
                type cml-data-types:CML_STRING_T;

                mandatory true;
                description "";
            }
        }
    }

    rpc igmp-mrib4-igmp-vrfName-clear {
    description "";
    reference "";
        input  {
            leaf vrfName  {
                type cml-data-types:CML_STRING_T;

                mandatory true;
                description "";
            }
        }
    }

    rpc igmp-mrib4-igmp-all-group-clear {
    description "";
    reference "";
        input  {
            leaf vrfName  {
                type cml-data-types:CML_STRING_T;

                mandatory true;
                description "";
            }
            leaf groupAddr  {
                type cml-data-types:CML_IPV4_ADDR_T;

                mandatory true;
                description "";
            }
        }
    }

    rpc igmp-mrib4-igmp-group-clear-all {
    description "";
    reference "";
        input  {
            leaf vrfName  {
                type cml-data-types:CML_STRING_T;

                mandatory true;
                description "";
            }
            leaf clearAll  {
                type cml-data-types:CML_EMPTY_T;

                mandatory true;
                description "";
            }
        }
    }

    rpc igmpsnooping-igmpsnooping-clear-interface-group {
    description "";
    reference "";
        input  {
            leaf groupAddr  {
                type cml-data-types:CML_IPV4_ADDR_T;

                mandatory true;
                description "";
            }
            leaf ifName  {
                type cml-data-types:CML_STRING_T;

                mandatory true;
                description "";
            }
        }
    }

    rpc igmpsnooping-igmpsnooping-clear-interface {
    description "";
    reference "";
        input  {
            leaf ifName  {
                type cml-data-types:CML_STRING_T;

                mandatory true;
                description "";
            }
        }
    }

    rpc igmpsnooping-igmpsnooping-clear-all {
    description "";
    reference "";
    }

    rpc igmpsnooping-igmpsnooping-clear {
    description "";
    reference "";
    }

    rpc igmpsnooping-igmpsnooping-clear-group {
    description "";
    reference "";
        input  {
            leaf groupAddr  {
                type cml-data-types:CML_IPV4_ADDR_T;

                mandatory true;
                description "";
            }
        }
    }

    rpc mcec-clear-mcec-statistics {
    description "";
    reference "";
    }

    rpc hqos-clearQos {
    description "";
    reference "";
        input  {
            leaf vrId  {
                type cml-data-types:CML_UINT32_T;

                mandatory true;
                description "";
            }
            leaf ifName  {
                type cml-data-types:CML_STRING_T;

                mandatory true;
                description "";
            }
        }
    }

    rpc hqos-cleartaildrop {
    description "";
    reference "";
        input  {
            leaf vrId  {
                type cml-data-types:CML_UINT32_T;

                mandatory true;
                description "";
            }
            leaf ifName  {
                type cml-data-types:CML_STRING_T;

                mandatory true;
                description "";
            }
        }
    }

    rpc hqos-clearCosqState {
    description "";
    reference "";
        input  {
            leaf vrId  {
                type cml-data-types:CML_UINT32_T;

                mandatory true;
                description "";
            }
            leaf ifName  {
                type cml-data-types:CML_STRING_T;

                mandatory true;
                description "";
            }
            leaf cosQid  {
                type cml-data-types:CML_QOS_DATA_T;

                mandatory true;
                description "";
            }
        }
    }

    rpc hqos-clearStatics {
    description "";
    reference "";
        input  {
            leaf vrId  {
                type cml-data-types:CML_UINT32_T;

                mandatory true;
                description "";
            }
            leaf ifName  {
                type cml-data-types:CML_STRING_T;

                mandatory true;
                description "";
            }
            leaf cosStatValue  {
                type cml-data-types:CML_CLEAR_STAT_QOS_T;

                mandatory true;
                description "";
            }
        }
    }

    rpc cmm-clear-ddm-transceiver-alarm-all {
    description "";
    reference "";
    }

    rpc cmm-clear-ddm-transceiver-alarm {
    description "";
    reference "";
        input  {
            leaf vrId  {
                type cml-data-types:CML_UINT32_T;

                mandatory true;
                description "";
            }
            leaf ifName  {
                type cml-data-types:CML_STRING_T;

                mandatory true;
                description "";
            }
        }
    }

    rpc auth-snmp-restart {
        if-feature feature-list:HAVE_SNMP;
    description "";
    reference "";
    }

    rpc rip-clear-ip-rip-route {
    description "";
    reference "";
        input  {
            leaf vrId  {
                type cml-data-types:CML_UINT32_T;

                mandatory true;
                description "";
            }
            leaf routeCMLSEPtype  {
                type cml-data-types:CML_RIP_ROUTE_T;

                mandatory true;
                description "";
            }
        }
    }

    rpc rip-clear-ip-rip-route-prefix {
    description "";
    reference "";
        input  {
            leaf vrId  {
                type cml-data-types:CML_UINT32_T;

                mandatory true;
                description "";
            }
            leaf routeCMLSEPtypeCMLSEPpre  {
                type cml-data-types:CML_IPV4_ADDR_PREFIX_T;

                mandatory true;
                description "";
            }
        }
    }

    rpc rip-clear-ip-rip-stat-interf {
    description "";
    reference "";
        input  {
            leaf vrId  {
                type cml-data-types:CML_UINT32_T;

                mandatory true;
                description "";
            }
            leaf ifName  {
                type cml-data-types:CML_STRING_T;

                mandatory true;
                description "";
            }
        }
    }

    rpc rip-snmp-restart-rip {
        if-feature feature-list:HAVE_SNMP;
    description "";
    reference "";
    }

    rpc aclinterface-clear-access-list-counters {
    description "";
    reference "";
        input  {
            leaf vrId  {
                type cml-data-types:CML_UINT32_T;

                mandatory true;
                description "";
            }
        }
    }

    rpc aclinterface-clear-access-list-name-counters {
    description "";
    reference "";
        input  {
            leaf vrId  {
                type cml-data-types:CML_UINT32_T;

                mandatory true;
                description "";
            }
            leaf aclName  {
                type cml-data-types:CML_STRING_T;

                mandatory true;
                description "";
            }
        }
    }

    rpc aclinterface-clear-ip-access-list-counters {
    description "";
    reference "";
        input  {
            leaf vrId  {
                type cml-data-types:CML_UINT32_T;

                mandatory true;
                description "";
            }
        }
    }

    rpc aclinterface-clear-ip-access-list-name-counters {
    description "";
    reference "";
        input  {
            leaf vrId  {
                type cml-data-types:CML_UINT32_T;

                mandatory true;
                description "";
            }
            leaf aclName  {
                type cml-data-types:CML_STRING_T;

                mandatory true;
                description "";
            }
        }
    }

    rpc aclinterface-clear-ipv6-access-list-counters {
    description "";
    reference "";
        input  {
            leaf vrId  {
                type cml-data-types:CML_UINT32_T;

                mandatory true;
                description "";
            }
        }
    }

    rpc aclinterface-clear-ipv6-access-list-name-counters {
    description "";
    reference "";
        input  {
            leaf vrId  {
                type cml-data-types:CML_UINT32_T;

                mandatory true;
                description "";
            }
            leaf aclName  {
                type cml-data-types:CML_STRING_T;

                mandatory true;
                description "";
            }
        }
    }

    rpc aclinterface-clear-mac-access-list-counters {
    description "";
    reference "";
        input  {
            leaf vrId  {
                type cml-data-types:CML_UINT32_T;

                mandatory true;
                description "";
            }
        }
    }

    rpc aclinterface-clear-mac-access-list-name-counters {
    description "";
    reference "";
        input  {
            leaf vrId  {
                type cml-data-types:CML_UINT32_T;

                mandatory true;
                description "";
            }
            leaf aclName  {
                type cml-data-types:CML_STRING_T;

                mandatory true;
                description "";
            }
        }
    }

    rpc aclinterface-clear-arp-access-list-counters {
        if-feature feature-list:HAVE_CUSTOM2_ACL;
    description "";
    reference "";
        input  {
            leaf vrId  {
                type cml-data-types:CML_UINT32_T;

                mandatory true;
                description "";
            }
        }
    }

    rpc aclinterface-clear-arp-access-list-name-counters {
        if-feature feature-list:HAVE_CUSTOM2_ACL;
    description "";
    reference "";
        input  {
            leaf vrId  {
                type cml-data-types:CML_UINT32_T;

                mandatory true;
                description "";
            }
            leaf aclName  {
                type cml-data-types:CML_STRING_T;

                mandatory true;
                description "";
            }
        }
    }

    rpc dhcpsnooping-ipdhcpsnoopingdatabase {
    description "";
    reference "";
        input  {
            leaf bridgeId  {
                type cml-data-types:CML_STRING_T {
                    length "1..32";
                }

                mandatory true;
                description "";
            }
        }
    }

    rpc dhcpsnooping-renewipdhcpsnoopingdatabase {
    description "";
    reference "";
        input  {
            leaf bridgeId  {
                type cml-data-types:CML_STRING_T {
                    length "1..32";
                }

                mandatory true;
                description "";
            }
        }
    }

    rpc dhcpsnooping-ipdhcpsnoopingsourcedatabase {
    description "";
    reference "";
        input  {
            leaf bridgeId  {
                type cml-data-types:CML_STRING_T {
                    length "1..32";
                }

                mandatory true;
                description "";
            }
        }
    }

    rpc dhcpsnooping-ipdhcpsnoopingrenewsourcedatabase {
    description "";
    reference "";
        input  {
            leaf bridgeId  {
                type cml-data-types:CML_STRING_T {
                    length "1..32";
                }

                mandatory true;
                description "";
            }
        }
    }

    rpc dhcpsnooping-clearipdhcpsnoopingdatabase {
    description "";
    reference "";
        input  {
            leaf bridgeId  {
                type cml-data-types:CML_STRING_T {
                    length "1..32";
                }

                mandatory true;
                description "";
            }
        }
    }

    rpc ras-clear-hsl-ipc-stat-values {
    description "";
    reference "";
        input  {
            leaf startCMLSEPvalue  {
                type cml-data-types:CML_UINT16_T;

                mandatory true;
                description "";
            }
            leaf endCMLSEPvalue  {
                type cml-data-types:CML_UINT16_T;

                mandatory true;
                description "";
            }
        }
    }

    rpc ras-clear-hsl-ipc-stat {
    description "";
    reference "";
    }

    rpc ras-clear-hsl-mlag-mac-sync {
        if-feature feature-list:HAVE_MLAG;
    description "";
    reference "";
    }

    rpc ripng-clear-ipv6-rip-route {
    description "";
    reference "";
        input  {
            leaf vrId  {
                type cml-data-types:CML_UINT32_T;

                mandatory true;
                description "";
            }
            leaf routeCMLSEPtype  {
                type cml-data-types:CML_RIPNG_ROUTE_T;

                mandatory true;
                description "";
            }
        }
    }

    rpc ripng-clear-ipv6-rip-route-prefix {
    description "";
    reference "";
        input  {
            leaf vrId  {
                type cml-data-types:CML_UINT32_T;

                mandatory true;
                description "";
            }
            leaf routeCMLSEPtypeCMLSEPpre  {
                type cml-data-types:CML_IPV6_PREFIX_T;

                mandatory true;
                description "";
            }
        }
    }

    rpc trill-cleartrillprocess {
    description "";
    reference "";
        input  {
            leaf vrId  {
                type cml-data-types:CML_UINT32_T;

                mandatory true;
                description "";
            }
            leaf trillId  {
                type cml-data-types:CML_STRING_T;

                mandatory true;
                description "";
            }
        }
    }

    rpc trill-cleartrillcounter {
    description "";
    reference "";
        input  {
            leaf vrId  {
                type cml-data-types:CML_UINT32_T;

                mandatory true;
                description "";
            }
        }
    }

    rpc trill-cleartrillIfcounter {
    description "";
    reference "";
        input  {
            leaf vrId  {
                type cml-data-types:CML_UINT32_T;

                mandatory true;
                description "";
            }
            leaf ifName  {
                type cml-data-types:CML_STRING_T;

                mandatory true;
                description "";
            }
        }
    }

    rpc trill-snmp-restart-trill {
        if-feature feature-list:HAVE_SNMP;
    description "";
    reference "";
    }

    rpc ndd-cleararp {
    description "";
    reference "";
        input  {
            leaf vrId  {
                type cml-data-types:CML_UINT32_T;

                mandatory true;
                description "";
            }
            leaf ipAddr  {
                type cml-data-types:CML_IPV4_ADDR_T;

                mandatory true;
                description "";
            }
            leaf vrfName  {
                type cml-data-types:CML_VRF_NAME_T;

                mandatory true;
                description "";
            }
        }
    }

    rpc ndd-cleararpIfname {
    description "";
    reference "";
        input  {
            leaf vrId  {
                type cml-data-types:CML_UINT32_T;

                mandatory true;
                description "";
            }
            leaf ifName  {
                type cml-data-types:CML_STRING_T;

                mandatory true;
                description "";
            }
            leaf vrfName  {
                type cml-data-types:CML_VRF_NAME_T;

                mandatory true;
                description "";
            }
        }
    }

    rpc ndd-clearipv6neigbour {
    description "";
    reference "";
        input  {
            leaf vrId  {
                type cml-data-types:CML_UINT32_T;

                mandatory true;
                description "";
            }
            leaf ipv6Addr  {
                type cml-data-types:CML_IPV6_ADDR_T;

                mandatory true;
                description "";
            }
            leaf vrfName  {
                type cml-data-types:CML_VRF_NAME_T;

                mandatory true;
                description "";
            }
        }
    }

    rpc ndd-clearipv6neigbourifname {
    description "";
    reference "";
        input  {
            leaf vrId  {
                type cml-data-types:CML_UINT32_T;

                mandatory true;
                description "";
            }
            leaf ifName  {
                type cml-data-types:CML_STRING_T;

                mandatory true;
                description "";
            }
            leaf vrfName  {
                type cml-data-types:CML_VRF_NAME_T;

                mandatory true;
                description "";
            }
        }
    }

    rpc imi-clearUser {
        if-feature feature-list:HAVE_IMI;
    description "";
    reference "";
        input  {
            leaf vrId  {
                type cml-data-types:CML_UINT32_T;

                mandatory true;
                description "";
            }
            leaf clearUser  {
                type cml-data-types:CML_STRING_T {
                    length "1..28";
                }

                mandatory true;
                description "";
            }
        }
    }

    rpc imi-clearLine {
        if-feature feature-list:HAVE_IMI;
    description "";
    reference "";
        input  {
            leaf vrId  {
                type cml-data-types:CML_UINT32_T;

                mandatory true;
                description "";
            }
            leaf clearLine  {
                type cml-data-types:CML_STRING_T {
                    length "1..64";
                }

                mandatory true;
                description "";
            }
        }
    }

    rpc nat-clear {
    description "";
    reference "";
    }

    rpc vm-stopvm {
        if-feature feature-list:HAVE_GUEST_VM;
    description "";
    reference "";
        input  {
            leaf vrId  {
                type cml-data-types:CML_UINT32_T;

                mandatory true;
                description "";
            }
            leaf stopvm  {
                type cml-data-types:CML_BOOL_T;

                mandatory true;
                description "Stop running VM";
            }
            leaf vmName  {
                type cml-data-types:CML_STRING_T {
                    length "1..16";
                }

                mandatory true;
                description "Name of the VM";
            }
        }
    }

    rpc vm-reloadvm {
        if-feature feature-list:HAVE_GUEST_VM;
    description "";
    reference "";
        input  {
            leaf vrId  {
                type cml-data-types:CML_UINT32_T;

                mandatory true;
                description "";
            }
            leaf vmTemplateName  {
                type cml-data-types:CML_STRING_T {
                    length "1..16";
                }

                mandatory true;
                description "Name of the VM template";
            }
            leaf reloadvm  {
                type cml-data-types:CML_BOOL_T;

                mandatory true;
                description "Reload the VM";
            }
            leaf vmName  {
                type cml-data-types:CML_STRING_T {
                    length "1..16";
                }

                mandatory true;
                description "Name of the VM";
            }
        }
    }

    rpc sysupdate-install {
    description "";
    reference "";
        input  {
            leaf installerName  {
                type cml-data-types:CML_STRING_T;

                mandatory true;
                description "";
            }
        }
    }

    rpc sysupdate-get {
    description "";
    reference "";
        input  {
            leaf sourceInterface  {
                type cml-data-types:CML_STRING_T;

                mandatory true;
                description "";
            }
            leaf url  {
                type cml-data-types:CML_STRING_T;

                mandatory true;
                description "";
            }
        }
    }

    rpc sysupdate-remove {
    description "";
    reference "";
        input  {
            leaf imageName  {
                type cml-data-types:CML_STRING_T;

                mandatory true;
                description "";
            }
        }
    }

    rpc sysupdate-cancel-download {
    description "";
    reference "";
    }

    notification force_unlock {

        description "Notify force unlck from netconf.";

        // severity "INFO";
        // eventClass "MESSAGE";
        leaf message {
            type string;
            description " alarm message notification";
        }
    }

    notification config_sync_completion_status {

        description "Notify netconf about config sync being completed.";

        // severity "INFO";
        // eventClass "MESSAGE";
        leaf message {
            type string;
            description " alarm message notification";
        }
    }

    notification system_shutdown_or_reload {

        description "Notify netconf about system shutdown or reload.";

        // severity "CRITICAL";
        // eventClass "MESSAGE";
        leaf message {
            type string;
            description " alarm message notification";
        }
    }

    notification interface-Errdis-Notif {

        description "The interfaceErrdisNotif is generated when an interface is error-disabled(errDisReason will have non-zero value) and when it recovers from errdisabled state (errDisReason will have '0'). Severity level is CRITICAL for interface going down and MINOR for interface moving to UP state when it recovers from errdisabled state..";

        // eventClass "STATE";
        leaf ifIndex {
            type cml-data-types:CML_INT32_T;
            description "A unique value, greater than zero, for each interface.It is recommended that values are assigned contiguously starting from 1.The value for each interface sub-layer must remain constant at least from one re-initialization of the entity's network management system to the next re-initialization.";
        }

        leaf vrId {
            type cml-data-types:CML_UINT32_T;
            description "Virtual router id";
        }

        leaf errDisReason {
            type cml-data-types:CML_NSM_ERRDISABLE_STATE_T;
            description "This object specifies the event that caused the interface to be error-disabled. If interface is error-disabled because of lag-mismatch, value of this object is 1. If interface is error-disabled because of stp-bpdu-guard, value of this object is 2. If interface is error-disabled because of link-flap, value of this object is 4.";
        }
    }

    notification agg-Min-Link {

        description "The aggMinLink is generated when a total Active (link-UP) LAG member link count becomes less than the configured min-link count. Severity level is CRITICAL for interface going down and INFO for interface moving to UP state..";

        // eventClass "STATE";
        leaf ifIndex {
            type cml-data-types:CML_INT32_T;
            description "A unique value, greater than zero, for each interface.It is recommended that values are assigned contiguously starting from 1.The value for each interface sub-layer must remain constant at least from one re-initialization of the entity's network management system to the next re-initialization.";
        }

        leaf vrId {
            type cml-data-types:CML_UINT32_T;
            description "Virtual router id";
        }

        leaf aggDownMinLink {
            type cml-data-types:CML_BOOL_T;
            description "aggDownMinLink Flag is set then Interface moved to Down state Min Links else move to Up state Min Links";
        }
    }

    notification interface-link-state-change-notification {

        description "A linkDown specifies that one of the communication links is about to enter the down state from some other state (but not from the notPresent state).  This other state is indicated by the included value of ifOperStatus. A linkUp trap signifies that one of communication links left the down state and transitioned into some other state (but not into the notPresent state).  This other state is indicated by the included value of ifOperStatus. Severity level is CRITICAL for link state Down and MINOR for link state Up..";

        // eventClass "STATE";
        leaf ifName {
            type cml-data-types:CML_STRING_T;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type cml-data-types:CML_UINT32_T;
            description "Virtual router id";
        }

        leaf ifOperStatus {
            type  CML_INTERFACE_OPER_STATUS_T;
            description "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components.";
        }
    }

    notification warning-TCAM-Util-Notif {

        description "The warningTCAMUtilNotif is generated         when number of entries in TCAM group crosses the warning threshold limit..";

        // severity "WARNING";
        // eventClass "STATE";
        leaf groupId {
            type cml-data-types:CML_UINT32_T;
            description "A unique number corresponding to each TCAM group.";
        }

        leaf groupName {
            type cml-data-types:CML_STRING_T;
            description "TCAM group name.";
        }

        leaf usedPercent {
            type cml-data-types:CML_INT32_T;
            description "Percentage of entries used in the TCAM group.
              Value of -1 means the field is not applicable.";
        }

        leaf freeEntries {
            type cml-data-types:CML_INT32_T;
            description "Count of free entries in the TCAM group.
              Value of -1 means the field is not applicable.";
        }
    }

    notification critical-TCAM-Util-Notif {

        description "The criticalTCAMUtilNotif is generated         when number of entries in TCAM group crosses the critical threshold limit..";

        // severity "CRITICAL";
        // eventClass "STATE";
        leaf groupId {
            type cml-data-types:CML_UINT32_T;
            description "A unique number corresponding to each TCAM group.";
        }

        leaf groupName {
            type cml-data-types:CML_STRING_T;
            description "TCAM group name.";
        }

        leaf usedPercent {
            type cml-data-types:CML_INT32_T;
            description "Percentage of entries used in the TCAM group.
              Value of -1 means the field is not applicable.";
        }

        leaf freeEntries {
            type cml-data-types:CML_INT32_T;
            description "Count of free entries in the TCAM group.
              Value of -1 means the field is not applicable.";
        }
    }

    notification topologyChange {

        description "A topologyChange trap is sent by a bridge when any of its configured ports transitions from the Learning state to the Forwarding state, or from the Forwarding state to the Blocking state..";

        // severity "INFO";
        // eventClass "MESSAGE";
        leaf message {
            type string;
            description " alarm message notification";
        }
    }

    notification newRoot {

        description "The newRoot trap indicates that the sending agent has become the new root of the Spanning Tree..";

        // severity "INFO";
        // eventClass "MESSAGE";
        leaf message {
            type string;
            description " alarm message notification";
        }
    }

    notification bgp-peer-state {

        description "bgp Peer State..";

        // severity "INFO";
        // eventClass "STATE";
        leaf peerAddr {
            type cml-data-types:CML_HOSTNAME_T;
            description "The peer address or Tag or Interface Name";
        }

        leaf bgpAs {
            type cml-data-types:CML_UINT32_T;
            description "AS number";
        }

        leaf vrId {
            type cml-data-types:CML_UINT32_T;
            description "Virtual router id";
        }

        leaf vrfName {
            type cml-data-types:CML_STRING_T;
            description "vrf name";
        }

        leaf bgpPeerState {
            type cml-data-types:CML_BGP_PEER_STATUS_T;
            description "Bgp peer session state. If there is change in state of the session , notification will be published only if the current state or the previous state is in establised state ";
        }

        leaf peerAs {
            type cml-data-types:CML_BGP_AS_T;
            description "Remote AS number";
        }
    }

    notification bgp-maximum-prefix {

        description "Maximum prefix learned exceeded the limit for neighbor..";

        // severity "CRITICAL";
        // eventClass "STATE";
        leaf peerAddr {
            type cml-data-types:CML_HOSTNAME_T;
            description "The peer address or Tag or Interface Name";
        }

        leaf bgpAs {
            type cml-data-types:CML_UINT32_T;
            description "AS number";
        }

        leaf vrId {
            type cml-data-types:CML_UINT32_T;
            description "Virtual router id";
        }

        leaf vrfName {
            type cml-data-types:CML_STRING_T;
            description "vrf name";
        }

        leaf maxPrefixes {
            type cml-data-types:CML_UINT32_T;
            description "Maximum number of prefixes";
        }
    }

    notification vxlan-tunnel-status-change-notification {

        description "The nvoTunnelStatus trap is generated when there is any status change in Tunnel Severity level is INFO for tunnel status going to Unresolved/Deleted status and MINOR for Resolved status..";

        // eventClass "STATE";
        leaf destIp {
            type cml-data-types:CML_IPV4_ADDR_T;
            description "Tunnel destination IP";
        }

        leaf vrId {
            type cml-data-types:CML_UINT32_T;
            description "Virtual router id";
        }

        leaf tunnelStatus {
            type cml-data-types:CML_TUNNEL_STATUS_T;
            description "Status of tunnel";
        }
    }

    notification sflowReceiverTimeoutAlarmMsg {

        description "Notify alarm message.";

        // severity "MINOR";
        // eventClass "MESSAGE";
        leaf message {
            type string;
            description " alarm message notification";
        }
    }

    notification license_message {

        description "license messages to all northbound.";

        // eventClass "STATE";
        leaf licenseMsg {
            type cml-data-types:CML_STRING_T;
            description "license log message for all clients";
        }
    }

    notification license_status {

        description "license success or failure.";

        // eventClass "STATE";
        leaf licenseStatus {
            type cml-data-types:CML_STRING_T;
            description "license log message for all clients";
        }
    }

    notification license_remaining_days {

        description "license remaining days.";

        // eventClass "STATE";
        leaf remainingDays {
            type cml-data-types:CML_INT32_T;
            description "remaining days to license expiry or remaining lease";
        }
    }

    notification cmmSysPsDownNotification {

        description "The cmmSysPsDownNotification  event is generated when a protocol module down/hung/crashes.";

        // severity "CRITICAL";
        // eventClass "STATE";
        leaf cmmSoftwareProcessID {
            type cml-data-types:CML_UINT32_T;
            description "Each protocol module is uniquely identified with a number, also called as protocol module id";
        }

        leaf cmmSoftwareProcessName {
            type cml-data-types:CML_STRING_T;
            description "Protocol module name";
        }

        leaf cmmSoftwareProcessStartTime {
            type cml-data-types:CML_DATE_TIME_T;
            description "The starting time of a protocol module, given in date and time.";
        }

        leaf cmmSoftwareProcessLastRestartReason {
            type cml-data-types:CML_LINE_T;
            description "Reason for process to shutdown provided it was running.This value will be the signal description";
        }
    }

    notification cmmSysPsRestartNotification {

        description "The cmmSysPsRestartNotification  event is generated when a protocol module recovered from down/hung/crashes.";

        // severity "MINOR";
        // eventClass "STATE";
        leaf cmmSoftwareProcessID {
            type cml-data-types:CML_UINT32_T;
            description "Each protocol module is uniquely identified with a number, also called as protocol module id";
        }

        leaf cmmSoftwareProcessName {
            type cml-data-types:CML_STRING_T;
            description "Protocol module name";
        }

        leaf cmmSoftwareProcessStartTime {
            type cml-data-types:CML_DATE_TIME_T;
            description "The starting time of a protocol module, given in date and time.";
        }
    }

    notification cmmCpuLoad15MinCritical {

        description "notification to send information for 15min critical threshold and CPU Utilisation.";

        // severity "CRITICAL";
        // eventClass "STATE";
        leaf cmmStackUnitIndex {
            type cml-data-types:CML_INT32_T;
            description "The unique index for this entry.Refer to the object cmmStackUnitIndexNext.";
        }

        leaf cmmStackUnitCpuLoad15Min {
            type cml-data-types:CML_FLOAT_T;
            description "CPU Load in percentage for last 15 minutes. '-1000.01' indicates unavailable.";
        }

        leaf cmmStackCpuLoad15minCriticalThreshold {
            type cml-data-types:CML_FLOAT_T;
            description "The CPU Critical Threshold percentage value for 15 min load. '-1000.01' indicates unavailable.";
        }
    }

    notification cmmCpuLoad5MinCritical {

        description "notification to send information for 5min critical threshold and CPU Utilisation.";

        // severity "CRITICAL";
        // eventClass "STATE";
        leaf cmmStackUnitIndex {
            type cml-data-types:CML_INT32_T;
            description "The unique index for this entry.Refer to the object cmmStackUnitIndexNext.";
        }

        leaf cmmStackUnitCpuLoad5Min {
            type cml-data-types:CML_FLOAT_T;
            description "CPU Load in percentage for last 5 minutes. '-1000.01' indicates unavailable.";
        }

        leaf cmmStackCpuLoad5minCriticalThreshold {
            type cml-data-types:CML_FLOAT_T;
            description "The CPU Critical Threshold percentage value for 5 min load. '-1000.01' indicates unavailable.";
        }
    }

    notification cmmCpuLoad1MinAlert {

        description "notification to send information for 1min alert threshold and CPU Utilisation.";

        // severity "CRITICAL";
        // eventClass "STATE";
        leaf cmmStackUnitIndex {
            type cml-data-types:CML_INT32_T;
            description "The unique index for this entry.Refer to the object cmmStackUnitIndexNext.";
        }

        leaf cmmStackUnitCpuLoad1Min {
            type cml-data-types:CML_FLOAT_T;
            description "CPU Load in percentage for last 1 minute. '-1000.01' indicates unavailable.";
        }

        leaf cmmStackCpuLoad1minAlertThreshold {
            type cml-data-types:CML_FLOAT_T;
            description "The CPU Alert Threshold percentage value for 1 min load. '-1000.01' indicates unavailable.";
        }
    }

    notification cmmCpuLoad1MinCritical {

        description "notification to send information for 1min critical threshold and CPU Utilisation.";

        // severity "CRITICAL";
        // eventClass "STATE";
        leaf cmmStackUnitIndex {
            type cml-data-types:CML_INT32_T;
            description "The unique index for this entry.Refer to the object cmmStackUnitIndexNext.";
        }

        leaf cmmStackUnitCpuLoad1Min {
            type cml-data-types:CML_FLOAT_T;
            description "CPU Load in percentage for last 1 minute. '-1000.01' indicates unavailable.";
        }

        leaf cmmStackCpuLoad1minCriticalThreshold {
            type cml-data-types:CML_FLOAT_T;
            description "The CPU Critical Threshold percentage value for 1 min load. '-1000.01' indicates unavailable.";
        }
    }

    notification cmmCpuLoad1MinAlertRecovery {

        description "notification to send information for CPU usage recovered from Alert Condition.";

        // severity "MINOR";
        // eventClass "STATE";
        leaf cmmStackUnitIndex {
            type cml-data-types:CML_INT32_T;
            description "The unique index for this entry.Refer to the object cmmStackUnitIndexNext.";
        }

        leaf cmmStackUnitCpuLoad1Min {
            type cml-data-types:CML_FLOAT_T;
            description "CPU Load in percentage for last 1 minute. '-1000.01' indicates unavailable.";
        }

        leaf cmmStackCpuLoad1minAlertThreshold {
            type cml-data-types:CML_FLOAT_T;
            description "The CPU Alert Threshold percentage value for 1 min load. '-1000.01' indicates unavailable.";
        }
    }

    notification cmmCpuLoad15MinCriticalRecovery {

        description "notification to send information for CPU usage recovered from 15 min Critical Condition.";

        // severity "MINOR";
        // eventClass "STATE";
        leaf cmmStackUnitIndex {
            type cml-data-types:CML_INT32_T;
            description "The unique index for this entry.Refer to the object cmmStackUnitIndexNext.";
        }

        leaf cmmStackUnitCpuLoad15Min {
            type cml-data-types:CML_FLOAT_T;
            description "CPU Load in percentage for last 15 minutes. '-1000.01' indicates unavailable.";
        }

        leaf cmmStackCpuLoad15minCriticalThreshold {
            type cml-data-types:CML_FLOAT_T;
            description "The CPU Critical Threshold percentage value for 15 min load. '-1000.01' indicates unavailable.";
        }
    }

    notification cmmCpuLoad5MinCriticalRecovery {

        description "notification to send information for CPU usage recovered from 5 min Critical Condition.";

        // severity "MINOR";
        // eventClass "STATE";
        leaf cmmStackUnitIndex {
            type cml-data-types:CML_INT32_T;
            description "The unique index for this entry.Refer to the object cmmStackUnitIndexNext.";
        }

        leaf cmmStackUnitCpuLoad5Min {
            type cml-data-types:CML_FLOAT_T;
            description "CPU Load in percentage for last 5 minutes. '-1000.01' indicates unavailable.";
        }

        leaf cmmStackCpuLoad5minCriticalThreshold {
            type cml-data-types:CML_FLOAT_T;
            description "The CPU Critical Threshold percentage value for 5 min load. '-1000.01' indicates unavailable.";
        }
    }

    notification cmmCpuLoad1MinCriticalRecovery {

        description "notification to send information for CPU usage recovered from 1 min Critical Condition.";

        // severity "MINOR";
        // eventClass "STATE";
        leaf cmmStackUnitIndex {
            type cml-data-types:CML_INT32_T;
            description "The unique index for this entry.Refer to the object cmmStackUnitIndexNext.";
        }

        leaf cmmStackUnitCpuLoad1Min {
            type cml-data-types:CML_FLOAT_T;
            description "CPU Load in percentage for last 1 minute. '-1000.01' indicates unavailable.";
        }

        leaf cmmStackCpuLoad1minCriticalThreshold {
            type cml-data-types:CML_FLOAT_T;
            description "The CPU Critical Threshold percentage value for 1 min load. '-1000.01' indicates unavailable.";
        }
    }

    notification cmmCpuCoreUtilHighAlert {

        description "notification to send information for CPU utilization in alert condition..";

        // severity "CRITICAL";
        // eventClass "STATE";
        leaf cmmStackUnitIndex {
            type cml-data-types:CML_INT32_T;
            description "The unique index for this entry.Refer to the object cmmStackUnitIndexNext.";
        }

        leaf cmmStackUnitCpuUtilization {
            type cml-data-types:CML_FLOAT_T;
            description "Total cpu usage in percentage. '-1000.01' indicates unavailable.";
        }

        leaf cmmStackUnitCpuUtilAlertThreshold {
            type cml-data-types:CML_FLOAT_T;
            description "The CPU utilization Alert Threshold %. '-1000.01' indicates unavailable.";
        }
    }

    notification cmmCpuCoreUtilHighCritical {

        description "notification to send information for CPU utilization in Critical condition..";

        // severity "CRITICAL";
        // eventClass "STATE";
        leaf cmmStackUnitIndex {
            type cml-data-types:CML_INT32_T;
            description "The unique index for this entry.Refer to the object cmmStackUnitIndexNext.";
        }

        leaf cmmStackUnitCpuUtilization {
            type cml-data-types:CML_FLOAT_T;
            description "Total cpu usage in percentage. '-1000.01' indicates unavailable.";
        }

        leaf cmmStackUnitCpuUtilCriticalThreshold {
            type cml-data-types:CML_FLOAT_T;
            description "The CPU utilization Critical Threshold %. '-1000.01' indicates unavailable.";
        }
    }

    notification cmmCpuCoreUtilHighAlertRecovery {

        description "notification to send information for CPU utilization after alert recovery..";

        // severity "MINOR";
        // eventClass "STATE";
        leaf cmmStackUnitIndex {
            type cml-data-types:CML_INT32_T;
            description "The unique index for this entry.Refer to the object cmmStackUnitIndexNext.";
        }

        leaf cmmStackUnitCpuUtilization {
            type cml-data-types:CML_FLOAT_T;
            description "Total cpu usage in percentage. '-1000.01' indicates unavailable.";
        }
    }

    notification cmmCpuCoreUtilHighCriticalRecovery {

        description "notification to send information for CPU utilization after Critical recovery..";

        // severity "MINOR";
        // eventClass "STATE";
        leaf cmmStackUnitIndex {
            type cml-data-types:CML_INT32_T;
            description "The unique index for this entry.Refer to the object cmmStackUnitIndexNext.";
        }

        leaf cmmStackUnitCpuUtilization {
            type cml-data-types:CML_FLOAT_T;
            description "Total cpu usage in percentage. '-1000.01' indicates unavailable.";
        }
    }

    notification cmmRamUsageRisingAlert {

        description " notification to send when RAM usage exceeds Alert Threshold.";

        // severity "CRITICAL";
        // eventClass "STATE";
        leaf cmmStackUnitIndex {
            type cml-data-types:CML_INT32_T;
            description "The unique index for this entry.Refer to the object cmmStackUnitIndexNext.";
        }

        leaf cmmSysRamUsedMem {
            type cml-data-types:CML_INT32_T;
            description "CPU RAM's Used memory available for utilisation in MBytes. '-100001' indicates unavailable.";
        }

        leaf cmmSysRamAlertThreshold {
            type cml-data-types:CML_INT32_T;
            description "RAM usage threshold % for Alert level. '-100001' indicates unavailable.";
        }
    }

    notification cmmRamUsageRisingCritical {

        description " notification to send when RAM usage exceeds Critical Threshold.";

        // severity "CRITICAL";
        // eventClass "STATE";
        leaf cmmStackUnitIndex {
            type cml-data-types:CML_INT32_T;
            description "The unique index for this entry.Refer to the object cmmStackUnitIndexNext.";
        }

        leaf cmmSysRamUsedMem {
            type cml-data-types:CML_INT32_T;
            description "CPU RAM's Used memory available for utilisation in MBytes. '-100001' indicates unavailable.";
        }

        leaf cmmSysRamCriticalThreshold {
            type cml-data-types:CML_INT32_T;
            description "RAM usage threshold % for Critical level. '-100001' indicates unavailable.";
        }
    }

    notification cmmRamUsageAlertRecovery {

        description " notification to send when RAM usage recovers from Alert condition.";

        // severity "MINOR";
        // eventClass "STATE";
        leaf cmmStackUnitIndex {
            type cml-data-types:CML_INT32_T;
            description "The unique index for this entry.Refer to the object cmmStackUnitIndexNext.";
        }

        leaf cmmSysRamUsedMem {
            type cml-data-types:CML_INT32_T;
            description "CPU RAM's Used memory available for utilisation in MBytes. '-100001' indicates unavailable.";
        }

        leaf cmmSysRamAlertThreshold {
            type cml-data-types:CML_INT32_T;
            description "RAM usage threshold % for Alert level. '-100001' indicates unavailable.";
        }
    }

    notification cmmRamUsageCriticalRecovery {

        description " notification to send when RAM usage recovers from Critical condition.";

        // severity "MINOR";
        // eventClass "STATE";
        leaf cmmStackUnitIndex {
            type cml-data-types:CML_INT32_T;
            description "The unique index for this entry.Refer to the object cmmStackUnitIndexNext.";
        }

        leaf cmmSysRamUsedMem {
            type cml-data-types:CML_INT32_T;
            description "CPU RAM's Used memory available for utilisation in MBytes. '-100001' indicates unavailable.";
        }

        leaf cmmSysRamCriticalThreshold {
            type cml-data-types:CML_INT32_T;
            description "RAM usage threshold % for Critical level. '-100001' indicates unavailable.";
        }
    }

    notification cmmHardDiskUsageRisingAlert {

        description "notification to send when Hard Disk usage exceeds alert threshold..";

        // severity "CRITICAL";
        // eventClass "STATE";
        leaf cmmStackUnitIndex {
            type cml-data-types:CML_INT32_T;
            description "The unique index for this entry.Refer to the object cmmStackUnitIndexNext.";
        }

        leaf cmmSysHarddiskUsedMem {
            type cml-data-types:CML_INT32_T;
            description "Used memory of the Hard disk. '-100001' indicates unavailable.";
        }

        leaf cmmSysHarddiskUsageAlertThreshold {
            type cml-data-types:CML_INT32_T;
            description "Harddisk usage threshold %  for Alert Level. '-100001' indicates unavailable.";
        }

        leaf cmmSysMountPoint {
            type cml-data-types:CML_STRING_T;
            description "Path of the mounted filesystem";
        }
    }

    notification cmmHardDiskUsageRisingCritical {

        description "notification to send when Hard Disk usage exceeds critical threshold..";

        // severity "CRITICAL";
        // eventClass "STATE";
        leaf cmmStackUnitIndex {
            type cml-data-types:CML_INT32_T;
            description "The unique index for this entry.Refer to the object cmmStackUnitIndexNext.";
        }

        leaf cmmSysHarddiskUsedMem {
            type cml-data-types:CML_INT32_T;
            description "Used memory of the Hard disk. '-100001' indicates unavailable.";
        }

        leaf cmmSysHarddiskUsageCriticalThreshold {
            type cml-data-types:CML_INT32_T;
            description "Harddisk usage threshold %  for Critical Level. '-100001' indicates unavailable.";
        }

        leaf cmmSysMountPoint {
            type cml-data-types:CML_STRING_T;
            description "Path of the mounted filesystem";
        }
    }

    notification cmmHardDiskUsageAlertRecovery {

        description "notification to send when Hard Disk usage recovers under alert threshold..";

        // severity "MINOR";
        // eventClass "STATE";
        leaf cmmStackUnitIndex {
            type cml-data-types:CML_INT32_T;
            description "The unique index for this entry.Refer to the object cmmStackUnitIndexNext.";
        }

        leaf cmmSysHarddiskUsedMem {
            type cml-data-types:CML_INT32_T;
            description "Used memory of the Hard disk. '-100001' indicates unavailable.";
        }

        leaf cmmSysHarddiskUsageAlertThreshold {
            type cml-data-types:CML_INT32_T;
            description "Harddisk usage threshold %  for Alert Level. '-100001' indicates unavailable.";
        }

        leaf cmmSysMountPoint {
            type cml-data-types:CML_STRING_T;
            description "Path of the mounted filesystem";
        }
    }

    notification cmmHardDiskUsageCriticalRecovery {

        description "notification to send when Hard Disk usage recovers under critical threshold..";

        // severity "MINOR";
        // eventClass "STATE";
        leaf cmmStackUnitIndex {
            type cml-data-types:CML_INT32_T;
            description "The unique index for this entry.Refer to the object cmmStackUnitIndexNext.";
        }

        leaf cmmSysHarddiskUsedMem {
            type cml-data-types:CML_INT32_T;
            description "Used memory of the Hard disk. '-100001' indicates unavailable.";
        }

        leaf cmmSysHarddiskUsageCriticalThreshold {
            type cml-data-types:CML_INT32_T;
            description "Harddisk usage threshold %  for Critical Level. '-100001' indicates unavailable.";
        }

        leaf cmmSysMountPoint {
            type cml-data-types:CML_STRING_T;
            description "Path of the mounted filesystem";
        }
    }

    notification cmmSysHardDiskRemainLifeRisingCritical {

        description "notification to send when Hard Disk Remain life reached below the critical threshold..";

        // eventClass "STATE";
        leaf cmmStackUnitIndex {
            type cml-data-types:CML_INT32_T;
            description "The unique index for this entry.Refer to the object cmmStackUnitIndexNext.";
        }

        leaf cmmSysHardDiskRemainLife {
            type cml-data-types:CML_INT32_T;
            description "Harddisk Remain life % Values '-100001' indicates unavailable.";
        }

        leaf cmmSysHardDiskRemainLifeAlertThreshold {
            type cml-data-types:CML_INT32_T;
            description "Harddisk Remain Life threshold % values for Alert Level. '-100001' indicates unavailable.";
        }
    }

    notification cmmSysHardDiskRemainLifeRisingAlert {

        description "notification to send when Hard Disk Remain life reached below the Alert threshold..";

        // eventClass "STATE";
        leaf cmmStackUnitIndex {
            type cml-data-types:CML_INT32_T;
            description "The unique index for this entry.Refer to the object cmmStackUnitIndexNext.";
        }

        leaf cmmSysHardDiskRemainLife {
            type cml-data-types:CML_INT32_T;
            description "Harddisk Remain life % Values '-100001' indicates unavailable.";
        }

        leaf cmmSysHardDiskRemainLifeAlertThreshold {
            type cml-data-types:CML_INT32_T;
            description "Harddisk Remain Life threshold % values for Alert Level. '-100001' indicates unavailable.";
        }
    }

    notification cmmSysHardDiskAvailableReservedSpaceCritical {

        description "notification to send when Hard Disk Available Reserved Space reached critical threshold level..";

        // eventClass "STATE";
        leaf cmmStackUnitIndex {
            type cml-data-types:CML_INT32_T;
            description "The unique index for this entry.Refer to the object cmmStackUnitIndexNext.";
        }

        leaf cmmSysHardDiskAvailableReservedSpace {
            type cml-data-types:CML_INT32_T;
            description "Harddisk Available Reserved Space % values'-100001' indicates unavailable.";
        }

        leaf cmmSysHardDiskAvailableReservedSpaceCriticalThreshold {
            type cml-data-types:CML_INT32_T;
            description "Harddisk Available Reserved Space threshold % values for critical Level'-100001' indicates unavailable.";
        }
    }

    notification cmmSysHardDiskAvailableReservedSpaceAlert {

        description "notification to send when Hard Disk Available Reserved Space reached Alert threshold level..";

        // eventClass "STATE";
        leaf cmmStackUnitIndex {
            type cml-data-types:CML_INT32_T;
            description "The unique index for this entry.Refer to the object cmmStackUnitIndexNext.";
        }

        leaf cmmSysHardDiskAvailableReservedSpace {
            type cml-data-types:CML_INT32_T;
            description "Harddisk Available Reserved Space % values'-100001' indicates unavailable.";
        }

        leaf cmmSysHardDiskAvailableReservedSpaceAlertThreshold {
            type cml-data-types:CML_INT32_T;
            description "Harddisk Available Reserved Space threshold % values for Alert Level'-100001' indicates unavailable.";
        }
    }

    notification cmmSysHardDiskReallocSectorsCountCritical {

        description "notification to send when Hard Disk Reallocated sector count increments by 10..";

        // eventClass "STATE";
        leaf cmmStackUnitIndex {
            type cml-data-types:CML_INT32_T;
            description "The unique index for this entry.Refer to the object cmmStackUnitIndexNext.";
        }

        leaf cmmSysHardDiskReallocSectorsCount {
            type cml-data-types:CML_INT32_T;
            description "Harddisk Reallocated Sectors Count values '-100001' indicates unavailable.";
        }
    }

    notification cmmSysHardDiskUncorrectableSectorCountAlert {

        description "notification to send when Hard Disk Uncorrectable sector count increments by 1..";

        // eventClass "STATE";
        leaf cmmStackUnitIndex {
            type cml-data-types:CML_INT32_T;
            description "The unique index for this entry.Refer to the object cmmStackUnitIndexNext.";
        }

        leaf cmmSysHardDiskUncorrectSectorCount {
            type cml-data-types:CML_INT32_T;
            description "Harddisk Uncorrectable Sectors Count '-100001' indicates unavailable.";
        }
    }

    notification cmmTemperatureLowEmergency {

        description "notification sent when Temperature will be below lower threshold for sensor.";

        // severity "CRITICAL";
        // eventClass "STATE";
        leaf cmmSysTemperatureSensorIndex {
            type cml-data-types:CML_INT8_T;
            description "Value represents Temperature Sensor Index";
        }

        leaf cmmStackUnitIndex {
            type cml-data-types:CML_INT32_T;
            description "The unique index for this entry.Refer to the object cmmStackUnitIndexNext.";
        }

        leaf cmmSysTemperatureValue {
            type cml-data-types:CML_FLOAT_T;
            description "Value represents Temperature Sensor value. '-1000.01' indicates unavailable.";
        }

        leaf cmmSysTempEmergencyThresholdMin {
            type cml-data-types:CML_FLOAT_T;
            description "Value represents Temperature Sensor Min Emergency threshold. '-1000.01' indicates unavailable.";
        }

        leaf cmmSysTempEmergencyThresholdMax {
            type cml-data-types:CML_FLOAT_T;
            description "Value represents Temperature Sensor Max Emergency threshold. '-1000.01' indicates unavailable.";
        }

        leaf cmmSysTemperatureSensorName {
            type cml-data-types:CML_LINE_T;
            description "Temperature Sensor Name. Blank indicates unavailable.";
        }
    }

    notification cmmTemperatureHighEmergency {

        description "notification sent when Temperature will be above threshold for sensor.";

        // severity "CRITICAL";
        // eventClass "STATE";
        leaf cmmSysTemperatureSensorIndex {
            type cml-data-types:CML_INT8_T;
            description "Value represents Temperature Sensor Index";
        }

        leaf cmmStackUnitIndex {
            type cml-data-types:CML_INT32_T;
            description "The unique index for this entry.Refer to the object cmmStackUnitIndexNext.";
        }

        leaf cmmSysTemperatureValue {
            type cml-data-types:CML_FLOAT_T;
            description "Value represents Temperature Sensor value. '-1000.01' indicates unavailable.";
        }

        leaf cmmSysTempEmergencyThresholdMin {
            type cml-data-types:CML_FLOAT_T;
            description "Value represents Temperature Sensor Min Emergency threshold. '-1000.01' indicates unavailable.";
        }

        leaf cmmSysTempEmergencyThresholdMax {
            type cml-data-types:CML_FLOAT_T;
            description "Value represents Temperature Sensor Max Emergency threshold. '-1000.01' indicates unavailable.";
        }

        leaf cmmSysTemperatureSensorName {
            type cml-data-types:CML_LINE_T;
            description "Temperature Sensor Name. Blank indicates unavailable.";
        }
    }

    notification cmmTemperatureLowAlert {

        description "notification sent when Temperature is nearing low emergency condition for sensor.";

        // severity "CRITICAL";
        // eventClass "STATE";
        leaf cmmSysTemperatureSensorIndex {
            type cml-data-types:CML_INT8_T;
            description "Value represents Temperature Sensor Index";
        }

        leaf cmmStackUnitIndex {
            type cml-data-types:CML_INT32_T;
            description "The unique index for this entry.Refer to the object cmmStackUnitIndexNext.";
        }

        leaf cmmSysTemperatureValue {
            type cml-data-types:CML_FLOAT_T;
            description "Value represents Temperature Sensor value. '-1000.01' indicates unavailable.";
        }

        leaf cmmSysTempAlertThresholdMin {
            type cml-data-types:CML_FLOAT_T;
            description "Value represents Temperature Sensor Min Alert threshold. '-1000.01' indicates unavailable.";
        }

        leaf cmmSysTempAlertThresholdMax {
            type cml-data-types:CML_FLOAT_T;
            description "Value represents Temperature Sensor Max Alert threshold. '-1000.01' indicates unavailable.";
        }

        leaf cmmSysTemperatureSensorName {
            type cml-data-types:CML_LINE_T;
            description "Temperature Sensor Name. Blank indicates unavailable.";
        }
    }

    notification cmmTemperatureHighAlert {

        description "notification sent when Temperature is nearing high emergency condition for sensor.";

        // severity "CRITICAL";
        // eventClass "STATE";
        leaf cmmSysTemperatureSensorIndex {
            type cml-data-types:CML_INT8_T;
            description "Value represents Temperature Sensor Index";
        }

        leaf cmmStackUnitIndex {
            type cml-data-types:CML_INT32_T;
            description "The unique index for this entry.Refer to the object cmmStackUnitIndexNext.";
        }

        leaf cmmSysTemperatureValue {
            type cml-data-types:CML_FLOAT_T;
            description "Value represents Temperature Sensor value. '-1000.01' indicates unavailable.";
        }

        leaf cmmSysTempAlertThresholdMin {
            type cml-data-types:CML_FLOAT_T;
            description "Value represents Temperature Sensor Min Alert threshold. '-1000.01' indicates unavailable.";
        }

        leaf cmmSysTempAlertThresholdMax {
            type cml-data-types:CML_FLOAT_T;
            description "Value represents Temperature Sensor Max Alert threshold. '-1000.01' indicates unavailable.";
        }

        leaf cmmSysTemperatureSensorName {
            type cml-data-types:CML_LINE_T;
            description "Temperature Sensor Name. Blank indicates unavailable.";
        }
    }

    notification cmmTemperatureLowCritical {

        description "notification sent when Temperature has reached low critical condition for sensor.";

        // severity "CRITICAL";
        // eventClass "STATE";
        leaf cmmSysTemperatureSensorIndex {
            type cml-data-types:CML_INT8_T;
            description "Value represents Temperature Sensor Index";
        }

        leaf cmmStackUnitIndex {
            type cml-data-types:CML_INT32_T;
            description "The unique index for this entry.Refer to the object cmmStackUnitIndexNext.";
        }

        leaf cmmSysTemperatureValue {
            type cml-data-types:CML_FLOAT_T;
            description "Value represents Temperature Sensor value. '-1000.01' indicates unavailable.";
        }

        leaf cmmSysTempCriticalThresholdMin {
            type cml-data-types:CML_FLOAT_T;
            description "Value represents Temperature Sensor Min Critical threshold. '-1000.01' indicates unavailable.";
        }

        leaf cmmSysTempCriticalThresholdMax {
            type cml-data-types:CML_FLOAT_T;
            description "Value represents Temperature Sensor Min Critical threshold. '-1000.01' indicates unavailable.";
        }

        leaf cmmSysTemperatureSensorName {
            type cml-data-types:CML_LINE_T;
            description "Temperature Sensor Name. Blank indicates unavailable.";
        }
    }

    notification cmmTemperatureHighCritical {

        description "notification sent when Temperature has reached high critical condition for sensor.";

        // severity "CRITICAL";
        // eventClass "STATE";
        leaf cmmSysTemperatureSensorIndex {
            type cml-data-types:CML_INT8_T;
            description "Value represents Temperature Sensor Index";
        }

        leaf cmmStackUnitIndex {
            type cml-data-types:CML_INT32_T;
            description "The unique index for this entry.Refer to the object cmmStackUnitIndexNext.";
        }

        leaf cmmSysTemperatureValue {
            type cml-data-types:CML_FLOAT_T;
            description "Value represents Temperature Sensor value. '-1000.01' indicates unavailable.";
        }

        leaf cmmSysTempCriticalThresholdMin {
            type cml-data-types:CML_FLOAT_T;
            description "Value represents Temperature Sensor Min Critical threshold. '-1000.01' indicates unavailable.";
        }

        leaf cmmSysTempCriticalThresholdMax {
            type cml-data-types:CML_FLOAT_T;
            description "Value represents Temperature Sensor Min Critical threshold. '-1000.01' indicates unavailable.";
        }

        leaf cmmSysTemperatureSensorName {
            type cml-data-types:CML_LINE_T;
            description "Temperature Sensor Name. Blank indicates unavailable.";
        }
    }

    notification cmmTemperatureHighAlertRecovery {

        description "notification sent when Temperature is recovered to normal range from alert level high for sensor..";

        // severity "MINOR";
        // eventClass "STATE";
        leaf cmmSysTemperatureSensorIndex {
            type cml-data-types:CML_INT8_T;
            description "Value represents Temperature Sensor Index";
        }

        leaf cmmStackUnitIndex {
            type cml-data-types:CML_INT32_T;
            description "The unique index for this entry.Refer to the object cmmStackUnitIndexNext.";
        }

        leaf cmmSysTemperatureValue {
            type cml-data-types:CML_FLOAT_T;
            description "Value represents Temperature Sensor value. '-1000.01' indicates unavailable.";
        }

        leaf cmmSysTempAlertThresholdMin {
            type cml-data-types:CML_FLOAT_T;
            description "Value represents Temperature Sensor Min Alert threshold. '-1000.01' indicates unavailable.";
        }

        leaf cmmSysTempAlertThresholdMax {
            type cml-data-types:CML_FLOAT_T;
            description "Value represents Temperature Sensor Max Alert threshold. '-1000.01' indicates unavailable.";
        }

        leaf cmmSysTemperatureSensorName {
            type cml-data-types:CML_LINE_T;
            description "Temperature Sensor Name. Blank indicates unavailable.";
        }
    }

    notification cmmTemperatureLowAlertRecovery {

        description "notification sent when Temperature is recovered to normal range from alert level low for sensor..";

        // severity "MINOR";
        // eventClass "STATE";
        leaf cmmSysTemperatureSensorIndex {
            type cml-data-types:CML_INT8_T;
            description "Value represents Temperature Sensor Index";
        }

        leaf cmmStackUnitIndex {
            type cml-data-types:CML_INT32_T;
            description "The unique index for this entry.Refer to the object cmmStackUnitIndexNext.";
        }

        leaf cmmSysTemperatureValue {
            type cml-data-types:CML_FLOAT_T;
            description "Value represents Temperature Sensor value. '-1000.01' indicates unavailable.";
        }

        leaf cmmSysTempAlertThresholdMin {
            type cml-data-types:CML_FLOAT_T;
            description "Value represents Temperature Sensor Min Alert threshold. '-1000.01' indicates unavailable.";
        }

        leaf cmmSysTempAlertThresholdMax {
            type cml-data-types:CML_FLOAT_T;
            description "Value represents Temperature Sensor Max Alert threshold. '-1000.01' indicates unavailable.";
        }

        leaf cmmSysTemperatureSensorName {
            type cml-data-types:CML_LINE_T;
            description "Temperature Sensor Name. Blank indicates unavailable.";
        }
    }

    notification cmmTemperatureHighCriticalRecovery {

        description "notification sent when Temperature is recovered to normal range from critical level high for sensor..";

        // severity "MINOR";
        // eventClass "STATE";
        leaf cmmSysTemperatureSensorIndex {
            type cml-data-types:CML_INT8_T;
            description "Value represents Temperature Sensor Index";
        }

        leaf cmmStackUnitIndex {
            type cml-data-types:CML_INT32_T;
            description "The unique index for this entry.Refer to the object cmmStackUnitIndexNext.";
        }

        leaf cmmSysTemperatureValue {
            type cml-data-types:CML_FLOAT_T;
            description "Value represents Temperature Sensor value. '-1000.01' indicates unavailable.";
        }

        leaf cmmSysTempCriticalThresholdMin {
            type cml-data-types:CML_FLOAT_T;
            description "Value represents Temperature Sensor Min Critical threshold. '-1000.01' indicates unavailable.";
        }

        leaf cmmSysTempCriticalThresholdMax {
            type cml-data-types:CML_FLOAT_T;
            description "Value represents Temperature Sensor Min Critical threshold. '-1000.01' indicates unavailable.";
        }

        leaf cmmSysTemperatureSensorName {
            type cml-data-types:CML_LINE_T;
            description "Temperature Sensor Name. Blank indicates unavailable.";
        }
    }

    notification cmmTemperatureLowCriticalRecovery {

        description "notification sent when Temperature is recovered to normal range from critical level low for sensor..";

        // severity "MINOR";
        // eventClass "STATE";
        leaf cmmSysTemperatureSensorIndex {
            type cml-data-types:CML_INT8_T;
            description "Value represents Temperature Sensor Index";
        }

        leaf cmmStackUnitIndex {
            type cml-data-types:CML_INT32_T;
            description "The unique index for this entry.Refer to the object cmmStackUnitIndexNext.";
        }

        leaf cmmSysTemperatureValue {
            type cml-data-types:CML_FLOAT_T;
            description "Value represents Temperature Sensor value. '-1000.01' indicates unavailable.";
        }

        leaf cmmSysTempCriticalThresholdMin {
            type cml-data-types:CML_FLOAT_T;
            description "Value represents Temperature Sensor Min Critical threshold. '-1000.01' indicates unavailable.";
        }

        leaf cmmSysTempCriticalThresholdMax {
            type cml-data-types:CML_FLOAT_T;
            description "Value represents Temperature Sensor Min Critical threshold. '-1000.01' indicates unavailable.";
        }

        leaf cmmSysTemperatureSensorName {
            type cml-data-types:CML_LINE_T;
            description "Temperature Sensor Name. Blank indicates unavailable.";
        }
    }

    notification cmmPsuInsertedNotify {

        description "Set when Power supply unit is inserted.";

        // severity "WARNING";
        // eventClass "STATE";
        leaf cmmSysPSUIndex {
            type cml-data-types:CML_INT32_T;
            description "The unique index of the power supply.";
        }

        leaf cmmStackUnitIndex {
            type cml-data-types:CML_INT32_T;
            description "The unique index for this entry.Refer to the object cmmStackUnitIndexNext.";
        }

        leaf cmmPsuSerialNumber {
            type cml-data-types:CML_STRING_T;
            description "PSU Date Code. Blank indicates unavailable.";
        }
    }

    notification cmmPsuRemovedAlert {

        description "Set when Power supply unit is Removed.";

        // severity "WARNING";
        // eventClass "STATE";
        leaf cmmSysPSUIndex {
            type cml-data-types:CML_INT32_T;
            description "The unique index of the power supply.";
        }

        leaf cmmStackUnitIndex {
            type cml-data-types:CML_INT32_T;
            description "The unique index for this entry.Refer to the object cmmStackUnitIndexNext.";
        }

        leaf cmmPsuSerialNumber {
            type cml-data-types:CML_STRING_T;
            description "PSU Date Code. Blank indicates unavailable.";
        }
    }

    notification cmmPsuAcFailedAlert {

        description " Set when Power supply unit has no input power..";

        // severity "CRITICAL";
        // eventClass "STATE";
        leaf cmmSysPSUIndex {
            type cml-data-types:CML_INT32_T;
            description "The unique index of the power supply.";
        }

        leaf cmmStackUnitIndex {
            type cml-data-types:CML_INT32_T;
            description "The unique index for this entry.Refer to the object cmmStackUnitIndexNext.";
        }
    }

    notification cmmPsuAcRecover {

        description " Set when Power supply unit input power is restored..";

        // severity "MINOR";
        // eventClass "STATE";
        leaf cmmSysPSUIndex {
            type cml-data-types:CML_INT32_T;
            description "The unique index of the power supply.";
        }

        leaf cmmStackUnitIndex {
            type cml-data-types:CML_INT32_T;
            description "The unique index for this entry.Refer to the object cmmStackUnitIndexNext.";
        }
    }

    notification cmmPsu12vPgFailedAlert {

        description " Set when Power supply unit has no output power..";

        // severity "CRITICAL";
        // eventClass "STATE";
        leaf cmmSysPSUIndex {
            type cml-data-types:CML_INT32_T;
            description "The unique index of the power supply.";
        }

        leaf cmmStackUnitIndex {
            type cml-data-types:CML_INT32_T;
            description "The unique index for this entry.Refer to the object cmmStackUnitIndexNext.";
        }
    }

    notification cmmPsu12vPgRecover {

        description " Set when Power supply unit output power is restored..";

        // severity "MINOR";
        // eventClass "STATE";
        leaf cmmSysPSUIndex {
            type cml-data-types:CML_INT32_T;
            description "The unique index of the power supply.";
        }

        leaf cmmStackUnitIndex {
            type cml-data-types:CML_INT32_T;
            description "The unique index for this entry.Refer to the object cmmStackUnitIndexNext.";
        }
    }

    notification cmmFanTrayInsertedNotify {

        description "Set when fan tray is inserted.";

        // severity "WARNING";
        // eventClass "STATE";
        leaf cmmFanTrayNumber {
            type cml-data-types:CML_INT8_T;
            description "Value represents the fan tray Number.";
        }

        leaf cmmStackUnitIndex {
            type cml-data-types:CML_INT32_T;
            description "The unique index for this entry.Refer to the object cmmStackUnitIndexNext.";
        }

        leaf cmmFanSerialNumber {
            type cml-data-types:CML_STRING_T;
            description "Fan Serial Number. Blank indicates unavailable.";
        }
    }

    notification cmmFanTrayRemovedAlert {

        description "Set when fan tray is Removed.";

        // severity "WARNING";
        // eventClass "STATE";
        leaf cmmFanTrayNumber {
            type cml-data-types:CML_INT8_T;
            description "Value represents the fan tray Number.";
        }

        leaf cmmStackUnitIndex {
            type cml-data-types:CML_INT32_T;
            description "The unique index for this entry.Refer to the object cmmStackUnitIndexNext.";
        }

        leaf cmmFanSerialNumber {
            type cml-data-types:CML_STRING_T;
            description "Fan Serial Number. Blank indicates unavailable.";
        }
    }

    notification cmmFanTrayFaultyAlert {

        description "Set when Given Fan Tray is faulty.";

        // severity "CRITICAL";
        // eventClass "STATE";
        leaf cmmFanTrayNumber {
            type cml-data-types:CML_INT8_T;
            description "Value represents the fan tray Number.";
        }

        leaf cmmStackUnitIndex {
            type cml-data-types:CML_INT32_T;
            description "The unique index for this entry.Refer to the object cmmStackUnitIndexNext.";
        }

        leaf cmmFanIndex {
            type cml-data-types:CML_INT8_T;
            description "Index of the fan per fantray.";
        }
    }

    notification cmmFanTrayRecovered {

        description "Set when Given Fan Tray is recovered.";

        // severity "MINOR";
        // eventClass "STATE";
        leaf cmmFanTrayNumber {
            type cml-data-types:CML_INT8_T;
            description "Value represents the fan tray Number.";
        }

        leaf cmmStackUnitIndex {
            type cml-data-types:CML_INT32_T;
            description "The unique index for this entry.Refer to the object cmmStackUnitIndexNext.";
        }

        leaf cmmFanIndex {
            type cml-data-types:CML_INT8_T;
            description "Index of the fan per fantray.";
        }
    }

    notification cmmFanTrayStallAlert {

        description "Set when Given Fan Tray Stalled.";

        // severity "CRITICAL";
        // eventClass "STATE";
        leaf cmmFanTrayNumber {
            type cml-data-types:CML_INT8_T;
            description "Value represents the fan tray Number.";
        }

        leaf cmmStackUnitIndex {
            type cml-data-types:CML_INT32_T;
            description "The unique index for this entry.Refer to the object cmmStackUnitIndexNext.";
        }

        leaf cmmFanIndex {
            type cml-data-types:CML_INT8_T;
            description "Index of the fan per fantray.";
        }
    }

    notification cmmFanTrayStallRecovered {

        description "Set when Given Fan Tray is recovered from stall.";

        // severity "MINOR";
        // eventClass "STATE";
        leaf cmmFanTrayNumber {
            type cml-data-types:CML_INT8_T;
            description "Value represents the fan tray Number.";
        }

        leaf cmmStackUnitIndex {
            type cml-data-types:CML_INT32_T;
            description "The unique index for this entry.Refer to the object cmmStackUnitIndexNext.";
        }

        leaf cmmFanIndex {
            type cml-data-types:CML_INT8_T;
            description "Index of the fan per fantray.";
        }
    }

    notification cmmFanRPMMinAlert {

        description " Set when fan RPM set to its minimum value..";

        // severity "CRITICAL";
        // eventClass "STATE";
        leaf cmmFanIndex {
            type cml-data-types:CML_INT8_T;
            description "Index of the fan per fantray.";
        }

        leaf cmmFanTrayNumber {
            type cml-data-types:CML_INT8_T;
            description "Value represents the fan tray Number.";
        }

        leaf cmmStackUnitIndex {
            type cml-data-types:CML_INT32_T;
            description "The unique index for this entry.Refer to the object cmmStackUnitIndexNext.";
        }

        leaf cmmFanRpmMin {
            type cml-data-types:CML_INT32_T;
            description "Value represents the minimum supported RPM of fan. '-100001' indicates unavailable.";
        }
    }

    notification cmmFanRPMMaxAlert {

        description " Set when fan RPM set to its maximum value..";

        // severity "CRITICAL";
        // eventClass "STATE";
        leaf cmmFanIndex {
            type cml-data-types:CML_INT8_T;
            description "Index of the fan per fantray.";
        }

        leaf cmmFanTrayNumber {
            type cml-data-types:CML_INT8_T;
            description "Value represents the fan tray Number.";
        }

        leaf cmmStackUnitIndex {
            type cml-data-types:CML_INT32_T;
            description "The unique index for this entry.Refer to the object cmmStackUnitIndexNext.";
        }

        leaf cmmFanRpmMax {
            type cml-data-types:CML_INT32_T;
            description "Value represents the maximum supported RPM of fan. '-100001' indicates unavailable.";
        }
    }

    notification cmmTransCriticalTempHigh {

        description "Set when internal temperature exceeds high warning level.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTemperature {
            type cml-data-types:CML_FLOAT_T;
            description "Internally measured temperature of the transceiver.This is common across channels for a transceiver. '-1000.01' indicates unavailable";
        }

        leaf cmmTransTempCriticalThresholdMin {
            type cml-data-types:CML_FLOAT_T;
            description "Min Alarm Threshold temperature of the transceiver.This is common across channels for a transceiver. '-1000.01' indicates unavailable.";
        }

        leaf cmmTransTempCriticalThresholdMax {
            type cml-data-types:CML_FLOAT_T;
            description "Max Alarm Threshold temperature of the transceiver.This is common across channels for a transceiver. '-1000.01' indicates unavailable.";
        }
    }

    notification cmmTransCriticalTempLow {

        description "Set when internal temperature is below low warning level.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTemperature {
            type cml-data-types:CML_FLOAT_T;
            description "Internally measured temperature of the transceiver.This is common across channels for a transceiver. '-1000.01' indicates unavailable";
        }

        leaf cmmTransTempCriticalThresholdMin {
            type cml-data-types:CML_FLOAT_T;
            description "Min Alarm Threshold temperature of the transceiver.This is common across channels for a transceiver. '-1000.01' indicates unavailable.";
        }

        leaf cmmTransTempCriticalThresholdMax {
            type cml-data-types:CML_FLOAT_T;
            description "Max Alarm Threshold temperature of the transceiver.This is common across channels for a transceiver. '-1000.01' indicates unavailable.";
        }
    }

    notification cmmTransAlertTempHigh {

        description "Set when internal temperature of transceiver exceeds high Alert level..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTemperature {
            type cml-data-types:CML_FLOAT_T;
            description "Internally measured temperature of the transceiver.This is common across channels for a transceiver. '-1000.01' indicates unavailable";
        }

        leaf cmmTransTempAlertThresholdMin {
            type cml-data-types:CML_FLOAT_T;
            description "Min Alert Threshold temperature of the transceiver.This is common across channels for a transceiver. '-1000.01' indicates unavailable.";
        }

        leaf cmmTransTempAlertThresholdMax {
            type cml-data-types:CML_FLOAT_T;
            description "Max Alert Threshold temperature of the transceiver.This is common across channels for a transceiver. '-1000.01' indicates unavailable.";
        }
    }

    notification cmmTransAlertTempLow {

        description "Set when internal temperature of transceiver falls below low Alert level..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTemperature {
            type cml-data-types:CML_FLOAT_T;
            description "Internally measured temperature of the transceiver.This is common across channels for a transceiver. '-1000.01' indicates unavailable";
        }

        leaf cmmTransTempAlertThresholdMin {
            type cml-data-types:CML_FLOAT_T;
            description "Min Alert Threshold temperature of the transceiver.This is common across channels for a transceiver. '-1000.01' indicates unavailable.";
        }

        leaf cmmTransTempAlertThresholdMax {
            type cml-data-types:CML_FLOAT_T;
            description "Max Alert Threshold temperature of the transceiver.This is common across channels for a transceiver. '-1000.01' indicates unavailable.";
        }
    }

    notification cmmTransNotifyTransceiverTempRecovered {

        description "Set when temperature of transceiver is recovered from temperature fault.";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTemperature {
            type cml-data-types:CML_FLOAT_T;
            description "Internally measured temperature of the transceiver.This is common across channels for a transceiver. '-1000.01' indicates unavailable";
        }
    }

    notification cmmTransCriticalVoltageHigh {

        description "Set when internal supply voltage of transceiver exceeds high alarm level..";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransVoltage {
            type cml-data-types:CML_FLOAT_PRECISION_3_T;
            description "Internally measured supply voltage of the transceiver.This is common across channels for a transceiver. '-100.001' indicates unavailable.";
        }

        leaf cmmTransVoltCriticalThresholdMin {
            type cml-data-types:CML_FLOAT_PRECISION_3_T;
            description "Min Alarm Threshold voltage of the transceiver.This is common across channels for a transceiver. '-100.001' indicates unavailable.";
        }

        leaf cmmTransVoltCriticalThresholdMax {
            type cml-data-types:CML_FLOAT_PRECISION_3_T;
            description "Max Alarm Threshold voltage of the transceiver.This is common across channels for a transceiver. '-100.001' indicates unavailable.";
        }
    }

    notification cmmTransCriticalVoltageLow {

        description "Set when internal supply voltage of transceiver is below low alarm level..";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransVoltage {
            type cml-data-types:CML_FLOAT_PRECISION_3_T;
            description "Internally measured supply voltage of the transceiver.This is common across channels for a transceiver. '-100.001' indicates unavailable.";
        }

        leaf cmmTransVoltCriticalThresholdMin {
            type cml-data-types:CML_FLOAT_PRECISION_3_T;
            description "Min Alarm Threshold voltage of the transceiver.This is common across channels for a transceiver. '-100.001' indicates unavailable.";
        }

        leaf cmmTransVoltCriticalThresholdMax {
            type cml-data-types:CML_FLOAT_PRECISION_3_T;
            description "Max Alarm Threshold voltage of the transceiver.This is common across channels for a transceiver. '-100.001' indicates unavailable.";
        }
    }

    notification cmmTransAlertVoltageHigh {

        description " Set when internal supply voltage of transceiver exceeds high Alert level..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransVoltage {
            type cml-data-types:CML_FLOAT_PRECISION_3_T;
            description "Internally measured supply voltage of the transceiver.This is common across channels for a transceiver. '-100.001' indicates unavailable.";
        }

        leaf cmmTransVoltAlertThresholdMin {
            type cml-data-types:CML_FLOAT_PRECISION_3_T;
            description "Min Alert Threshold voltage of the transceiver.This is common across channels for a transceiver. '-100.001' indicates unavailable.";
        }

        leaf cmmTransVoltAlertThresholdMax {
            type cml-data-types:CML_FLOAT_PRECISION_3_T;
            description "Max Alert Threshold voltage of the transceiver.This is common across channels for a transceiver. '-100.001' indicates unavailable.";
        }
    }

    notification cmmTransAlertVoltageLow {

        description " Set when internal supply voltage of transceiver is below low Alert level...";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransVoltage {
            type cml-data-types:CML_FLOAT_PRECISION_3_T;
            description "Internally measured supply voltage of the transceiver.This is common across channels for a transceiver. '-100.001' indicates unavailable.";
        }

        leaf cmmTransVoltAlertThresholdMin {
            type cml-data-types:CML_FLOAT_PRECISION_3_T;
            description "Min Alert Threshold voltage of the transceiver.This is common across channels for a transceiver. '-100.001' indicates unavailable.";
        }

        leaf cmmTransVoltAlertThresholdMax {
            type cml-data-types:CML_FLOAT_PRECISION_3_T;
            description "Max Alert Threshold voltage of the transceiver.This is common across channels for a transceiver. '-100.001' indicates unavailable.";
        }
    }

    notification cmmTransNotifyTransceiverVoltRecovered {

        description " Set when Trasceiver is recovered from voltage fault..";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransVoltage {
            type cml-data-types:CML_FLOAT_PRECISION_3_T;
            description "Internally measured supply voltage of the transceiver.This is common across channels for a transceiver. '-100.001' indicates unavailable.";
        }
    }

    notification cmmTransCriticalBiasHigh {

        description "Set when TX Bias current of transceiver exceeds high alarm level..";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLaserBiasCurrent {
            type cml-data-types:CML_FLOAT_PRECISION_3_T;
            description "Internally measured TX Bias Current in Channel of transceiver. '-100.001' indicates unavailable.";
        }

        leaf cmmTransLaserBiasCurrCriticalThresholdMin {
            type cml-data-types:CML_FLOAT_PRECISION_3_T;
            description "Min Alarm Threshold of Laser Bias Current per channel. '-100.001' indicates unavailable.";
        }

        leaf cmmTransLaserBiasCurrCriticalThresholdMax {
            type cml-data-types:CML_FLOAT_PRECISION_3_T;
            description "Max Alarm Threshold of Laser Bias Current per channel. '-100.001' indicates unavailable.";
        }
    }

    notification cmmTransCriticalBiasLow {

        description "Set when TX Bias current of transceiver is below low alarm level..";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLaserBiasCurrent {
            type cml-data-types:CML_FLOAT_PRECISION_3_T;
            description "Internally measured TX Bias Current in Channel of transceiver. '-100.001' indicates unavailable.";
        }

        leaf cmmTransLaserBiasCurrCriticalThresholdMin {
            type cml-data-types:CML_FLOAT_PRECISION_3_T;
            description "Min Alarm Threshold of Laser Bias Current per channel. '-100.001' indicates unavailable.";
        }

        leaf cmmTransLaserBiasCurrCriticalThresholdMax {
            type cml-data-types:CML_FLOAT_PRECISION_3_T;
            description "Max Alarm Threshold of Laser Bias Current per channel. '-100.001' indicates unavailable.";
        }
    }

    notification cmmTransAlertBiasHigh {

        description "Set when TX Bias current of transceiver exceeds high alert level..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLaserBiasCurrent {
            type cml-data-types:CML_FLOAT_PRECISION_3_T;
            description "Internally measured TX Bias Current in Channel of transceiver. '-100.001' indicates unavailable.";
        }

        leaf cmmTransLaserBiasCurrAlertThresholdMin {
            type cml-data-types:CML_FLOAT_PRECISION_3_T;
            description "Min Alert Threshold of Laser Bias Current per channel. '-100.001' indicates unavailable.";
        }

        leaf cmmTransLaserBiasCurrAlertThresholdMax {
            type cml-data-types:CML_FLOAT_PRECISION_3_T;
            description "Max Alert Threshold of Laser Bias Current per channel. '-100.001' indicates unavailable.";
        }
    }

    notification cmmTransAlertBiasLow {

        description "Set when TX Bias current of transceiver is below low alert level..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLaserBiasCurrent {
            type cml-data-types:CML_FLOAT_PRECISION_3_T;
            description "Internally measured TX Bias Current in Channel of transceiver. '-100.001' indicates unavailable.";
        }

        leaf cmmTransLaserBiasCurrAlertThresholdMin {
            type cml-data-types:CML_FLOAT_PRECISION_3_T;
            description "Min Alert Threshold of Laser Bias Current per channel. '-100.001' indicates unavailable.";
        }

        leaf cmmTransLaserBiasCurrAlertThresholdMax {
            type cml-data-types:CML_FLOAT_PRECISION_3_T;
            description "Max Alert Threshold of Laser Bias Current per channel. '-100.001' indicates unavailable.";
        }
    }

    notification cmmTransNotifyTransceiverBiasRecovered {

        description "Set when TX Bias current of transceiver is recovered to normal..";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLaserBiasCurrent {
            type cml-data-types:CML_FLOAT_PRECISION_3_T;
            description "Internally measured TX Bias Current in Channel of transceiver. '-100.001' indicates unavailable.";
        }
    }

    notification cmmTransCriticalRxPowerHigh {

        description "Set when Received Power of transceiver exceeds high alarm level..";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransRxPower {
            type cml-data-types:CML_FLOAT_PRECISION_3_T;
            description "Measured RX input power in Channel of transceiver.'-100' value represents no power. '-100.001' indicates unavailable.";
        }

        leaf cmmTransRxPowerCriticalThresholdMin {
            type cml-data-types:CML_FLOAT_PRECISION_3_T;
            description "Min Alarm Threshold value of Rx Input Power per channel.'-100' value represents no power. '-100.001' indicates unavailable.";
        }

        leaf cmmTransRxPowerCriticalThresholdMax {
            type cml-data-types:CML_FLOAT_PRECISION_3_T;
            description "Max Alarm Threshold value of Rx Input Power per channel.'-100' value represents no power. '-100.001' indicates unavailable.";
        }
    }

    notification cmmTransCriticalRxPowerlow {

        description "Set when Received Power of transceiver is below low alarm level..";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransRxPower {
            type cml-data-types:CML_FLOAT_PRECISION_3_T;
            description "Measured RX input power in Channel of transceiver.'-100' value represents no power. '-100.001' indicates unavailable.";
        }

        leaf cmmTransRxPowerCriticalThresholdMin {
            type cml-data-types:CML_FLOAT_PRECISION_3_T;
            description "Min Alarm Threshold value of Rx Input Power per channel.'-100' value represents no power. '-100.001' indicates unavailable.";
        }

        leaf cmmTransRxPowerCriticalThresholdMax {
            type cml-data-types:CML_FLOAT_PRECISION_3_T;
            description "Max Alarm Threshold value of Rx Input Power per channel.'-100' value represents no power. '-100.001' indicates unavailable.";
        }
    }

    notification cmmTransAlertRxPowerHigh {

        description "Set when Received Power of transceiver exceeds high alert level..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransRxPower {
            type cml-data-types:CML_FLOAT_PRECISION_3_T;
            description "Measured RX input power in Channel of transceiver.'-100' value represents no power. '-100.001' indicates unavailable.";
        }

        leaf cmmTransRxPowerAlertThresholdMin {
            type cml-data-types:CML_FLOAT_PRECISION_3_T;
            description "Min Alert Threshold value of Rx Input Power per channel.'-100' value represents no power. '-100.001' indicates unavailable.";
        }

        leaf cmmTransRxPowerAlertThresholdMax {
            type cml-data-types:CML_FLOAT_PRECISION_3_T;
            description "Max Alert Threshold value of Rx Input Power per channel.'-100' value represents no power. '-100.001' indicates unavailable.";
        }
    }

    notification cmmTransAlertRxPowerLow {

        description "Set when Received Power of transceiver is below low alert level..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransRxPower {
            type cml-data-types:CML_FLOAT_PRECISION_3_T;
            description "Measured RX input power in Channel of transceiver.'-100' value represents no power. '-100.001' indicates unavailable.";
        }

        leaf cmmTransRxPowerAlertThresholdMin {
            type cml-data-types:CML_FLOAT_PRECISION_3_T;
            description "Min Alert Threshold value of Rx Input Power per channel.'-100' value represents no power. '-100.001' indicates unavailable.";
        }

        leaf cmmTransRxPowerAlertThresholdMax {
            type cml-data-types:CML_FLOAT_PRECISION_3_T;
            description "Max Alert Threshold value of Rx Input Power per channel.'-100' value represents no power. '-100.001' indicates unavailable.";
        }
    }

    notification cmmTransNotifyTransceiverRxPowRecovered {

        description "Set when Received Power of transceiver is recovered to normal..";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransRxPower {
            type cml-data-types:CML_FLOAT_PRECISION_3_T;
            description "Measured RX input power in Channel of transceiver.'-100' value represents no power. '-100.001' indicates unavailable.";
        }
    }

    notification cmmTransCriticalTxPowerHigh {

        description "Set when Transferred Power of transceiver exceeds high alarm level..";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTxPower {
            type cml-data-types:CML_FLOAT_PRECISION_3_T;
            description "Measured TX output power in Channel of transceiver.'-100' value represents no power. '-100.001' indicates unavailable.";
        }

        leaf cmmTransTxPowerCriticalThresholdMin {
            type cml-data-types:CML_FLOAT_PRECISION_3_T;
            description "Min Alarm Threshold of TxOutput Power per channel.'-100' value represents no power. '-100.001' indicates unavailable.";
        }

        leaf cmmTransTxPowerCriticalThresholdMax {
            type cml-data-types:CML_FLOAT_PRECISION_3_T;
            description "Max Alarm Threshold of TxOutput Power per channel.'-100' value represents no power. '-100.001' indicates unavailable.";
        }
    }

    notification cmmTransCriticalTxPowerLow {

        description "Set when Transferred Power of transceiver is below low alarm level..";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTxPower {
            type cml-data-types:CML_FLOAT_PRECISION_3_T;
            description "Measured TX output power in Channel of transceiver.'-100' value represents no power. '-100.001' indicates unavailable.";
        }

        leaf cmmTransTxPowerCriticalThresholdMin {
            type cml-data-types:CML_FLOAT_PRECISION_3_T;
            description "Min Alarm Threshold of TxOutput Power per channel.'-100' value represents no power. '-100.001' indicates unavailable.";
        }

        leaf cmmTransTxPowerCriticalThresholdMax {
            type cml-data-types:CML_FLOAT_PRECISION_3_T;
            description "Max Alarm Threshold of TxOutput Power per channel.'-100' value represents no power. '-100.001' indicates unavailable.";
        }
    }

    notification cmmTransAlertTxPowerHigh {

        description "Set when Transferred Power of transceiver exceeds high alert level..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTxPower {
            type cml-data-types:CML_FLOAT_PRECISION_3_T;
            description "Measured TX output power in Channel of transceiver.'-100' value represents no power. '-100.001' indicates unavailable.";
        }

        leaf cmmTransTxPowerAlertThresholdMin {
            type cml-data-types:CML_FLOAT_PRECISION_3_T;
            description "Min Alert Threshold of TxOutput Power per channel.'-100' value represents no power. '-100.001' indicates unavailable.";
        }

        leaf cmmTransTxPowerAlertThresholdMax {
            type cml-data-types:CML_FLOAT_PRECISION_3_T;
            description "Max Alert Threshold of TxOutput Power per channel.'-100' value represents no power. '-100.001' indicates unavailable.";
        }
    }

    notification cmmTransAlertTxPowerLow {

        description "Set when Transferred Power of transceiver is below low alert level..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTxPower {
            type cml-data-types:CML_FLOAT_PRECISION_3_T;
            description "Measured TX output power in Channel of transceiver.'-100' value represents no power. '-100.001' indicates unavailable.";
        }

        leaf cmmTransTxPowerAlertThresholdMin {
            type cml-data-types:CML_FLOAT_PRECISION_3_T;
            description "Min Alert Threshold of TxOutput Power per channel.'-100' value represents no power. '-100.001' indicates unavailable.";
        }

        leaf cmmTransTxPowerAlertThresholdMax {
            type cml-data-types:CML_FLOAT_PRECISION_3_T;
            description "Max Alert Threshold of TxOutput Power per channel.'-100' value represents no power. '-100.001' indicates unavailable.";
        }
    }

    notification cmmTransNotifyTransceiverTxPowRecovered {

        description "Set when Transferred Power of transceiver is recovered to normal..";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTxPower {
            type cml-data-types:CML_FLOAT_PRECISION_3_T;
            description "Measured TX output power in Channel of transceiver.'-100' value represents no power. '-100.001' indicates unavailable.";
        }
    }

    notification cmmTransNotifyTransceiverInserted {

        description " Set when Trasceiver is inserted..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransVendorName {
            type cml-data-types:CML_STRING_T;
            description "Transceiver vendor name. Blank indicates unavailable.";
        }

        leaf cmmTransVendorSerialNumber {
            type cml-data-types:CML_STRING_T;
            description "Serial number provided by vendor. Blank indicates unavailable.";
        }

        leaf cmmTransconnectortype {
            type cml-data-types:CML_CMM_TRANS_CONNECTOR_TYPE_T;
            description "Connector type for the transceiver.";
        }
    }

    notification cmmTransAlertTransceiverRemoved {

        description " Set when Trasceiver is removed..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransVendorName {
            type cml-data-types:CML_STRING_T;
            description "Transceiver vendor name. Blank indicates unavailable.";
        }

        leaf cmmTransVendorSerialNumber {
            type cml-data-types:CML_STRING_T;
            description "Serial number provided by vendor. Blank indicates unavailable.";
        }

        leaf cmmTransconnectortype {
            type cml-data-types:CML_CMM_TRANS_CONNECTOR_TYPE_T;
            description "Connector type for the transceiver.";
        }
    }

    notification cmmTransAlertFaultyTransceiverInserted {

        description " Set when Faulty Trasceiver is inserted..";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }
    }

    notification cmmAlertIncompatibleTransceiverPresence {

        description "Set when Incompatible Trasceiver is Present..";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }
    }

    notification cmmNotifyIncompatibleTransceiverRemoved {

        description "Set when Incompatible Trasceiver is Removed..";

        // severity "INFO";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }
    }

    notification cmmTransAlertPreFecBerErrHigh {

        description "Notification sent when FEC bit error rate falls above alert max value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransPreFecBerVal {
            type cml-data-types:CML_STRING_T;
            description "Forward error correction bit error rate value, -100002' indicates not-applicable";
        }

        leaf cmmTransPreFecBerAlertMax {
            type cml-data-types:CML_STRING_T;
            description "Max alert value for pre-forward error correction ber, -100002' indicates not-applicable";
        }

        leaf cmmTransPreFecBerAlertMin {
            type cml-data-types:CML_STRING_T;
            description "Min alert value for pre-forward error correction ber, -100002' indicates not-applicable";
        }
    }

    notification cmmTransAlertPreFecBerErrLow {

        description "Notification sent when FEC bit error rate falls below alert min value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransPreFecBerVal {
            type cml-data-types:CML_STRING_T;
            description "Forward error correction bit error rate value, -100002' indicates not-applicable";
        }

        leaf cmmTransPreFecBerAlertMax {
            type cml-data-types:CML_STRING_T;
            description "Max alert value for pre-forward error correction ber, -100002' indicates not-applicable";
        }

        leaf cmmTransPreFecBerAlertMin {
            type cml-data-types:CML_STRING_T;
            description "Min alert value for pre-forward error correction ber, -100002' indicates not-applicable";
        }
    }

    notification cmmTransCriticalPreFecBerErrHigh {

        description "Notification sent when FEC bit error rate falls above critical max value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransPreFecBerVal {
            type cml-data-types:CML_STRING_T;
            description "Forward error correction bit error rate value, -100002' indicates not-applicable";
        }

        leaf cmmTransPreFecBerCriticMax {
            type cml-data-types:CML_STRING_T;
            description "Max critical value for pre-forward error correction ber, -100002' indicates not-applicable";
        }

        leaf cmmTransPreFecBerCriticMin {
            type cml-data-types:CML_STRING_T;
            description "Min critical value for pre-forward error correction ber, -100002' indicates not-applicable";
        }
    }

    notification cmmTransCriticalPreFecBerErrLow {

        description "Notification sent when FEC bit error rate falls below critical min value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransPreFecBerVal {
            type cml-data-types:CML_STRING_T;
            description "Forward error correction bit error rate value, -100002' indicates not-applicable";
        }

        leaf cmmTransPreFecBerCriticMax {
            type cml-data-types:CML_STRING_T;
            description "Max critical value for pre-forward error correction ber, -100002' indicates not-applicable";
        }

        leaf cmmTransPreFecBerCriticMin {
            type cml-data-types:CML_STRING_T;
            description "Min critical value for pre-forward error correction ber, -100002' indicates not-applicable";
        }
    }

    notification cmmTransNotifyTransceiverPreFecBerRecovered {

        description "Set when FEC bit error rate of transceiver is recovered from BER fault.";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransPreFecBerVal {
            type cml-data-types:CML_STRING_T;
            description "Forward error correction bit error rate value, -100002' indicates not-applicable";
        }
    }

    notification cmmTransAlertUncorrectedBerHigh {

        description "Notification sent when Uncorrected BER falls above alert max value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransUncorrectedBerVal {
            type cml-data-types:CML_STRING_T;
            description "Frame error rate value, -100002' indicates not-applicable";
        }

        leaf cmmTransUncorrectedBerValAlertMax {
            type cml-data-types:CML_STRING_T;
            description "Max alert value for Uncorrected BER, -100002' indicates not-applicable";
        }

        leaf cmmTransUncorrectedBerValAlertMin {
            type cml-data-types:CML_STRING_T;
            description "Min alert value for Uncorrected BER, -100002' indicates not-applicable";
        }
    }

    notification cmmTransAlertUncorrectedBerLow {

        description "Notification sent when Uncorrected BER falls below alert min value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransUncorrectedBerVal {
            type cml-data-types:CML_STRING_T;
            description "Frame error rate value, -100002' indicates not-applicable";
        }

        leaf cmmTransUncorrectedBerValAlertMax {
            type cml-data-types:CML_STRING_T;
            description "Max alert value for Uncorrected BER, -100002' indicates not-applicable";
        }

        leaf cmmTransUncorrectedBerValAlertMin {
            type cml-data-types:CML_STRING_T;
            description "Min alert value for Uncorrected BER, -100002' indicates not-applicable";
        }
    }

    notification cmmTransCriticalUncorrectedBerHigh {

        description "Notification sent when Uncorrected BER falls above critical max value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransUncorrectedBerVal {
            type cml-data-types:CML_STRING_T;
            description "Frame error rate value, -100002' indicates not-applicable";
        }

        leaf cmmTransUncorrectedBerValCriticMax {
            type cml-data-types:CML_STRING_T;
            description "Max critical value for Uncorrected BER, -100002' indicates not-applicable";
        }

        leaf cmmTransUncorrectedBerValCriticMin {
            type cml-data-types:CML_STRING_T;
            description "Min critical value for Uncorrected BER, -100002' indicates not-applicable";
        }
    }

    notification cmmTransCriticalUncorrectedBerLow {

        description "Notification sent when Uncorrected BER falls below critical min value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransUncorrectedBerVal {
            type cml-data-types:CML_STRING_T;
            description "Frame error rate value, -100002' indicates not-applicable";
        }

        leaf cmmTransUncorrectedBerValCriticMax {
            type cml-data-types:CML_STRING_T;
            description "Max critical value for Uncorrected BER, -100002' indicates not-applicable";
        }

        leaf cmmTransUncorrectedBerValCriticMin {
            type cml-data-types:CML_STRING_T;
            description "Min critical value for Uncorrected BER, -100002' indicates not-applicable";
        }
    }

    notification cmmTransNotifyTransceiverUncorrectedBerRecovered {

        description "Set when Uncorrected BER transceiver is recovered from BER fault.";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransUncorrectedBerVal {
            type cml-data-types:CML_STRING_T;
            description "Frame error rate value, -100002' indicates not-applicable";
        }
    }

    notification cmmTransAlertSnrHigh {

        description "Notification sent when SNR falls above alert max value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransSnrVal {
            type cml-data-types:CML_FLOAT_PRECISION_3_T;
            description "Signal to noise ratio on ingress lane, -100002' indicates not-applicable";
        }

        leaf cmmTransSnrAlertMax {
            type cml-data-types:CML_FLOAT_PRECISION_3_T;
            description "Max alert value for signal-to-noise ratio on ingress lane, -100002' indicates not-applicable";
        }

        leaf cmmTransSnrAlertMin {
            type cml-data-types:CML_FLOAT_PRECISION_3_T;
            description "Min alert value for signal-to-noise ratio on ingress lane, -100002' indicates not-applicable";
        }
    }

    notification cmmTransAlertSnrLow {

        description "Notification sent when SNR falls below alert min value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransSnrVal {
            type cml-data-types:CML_FLOAT_PRECISION_3_T;
            description "Signal to noise ratio on ingress lane, -100002' indicates not-applicable";
        }

        leaf cmmTransSnrAlertMax {
            type cml-data-types:CML_FLOAT_PRECISION_3_T;
            description "Max alert value for signal-to-noise ratio on ingress lane, -100002' indicates not-applicable";
        }

        leaf cmmTransSnrAlertMin {
            type cml-data-types:CML_FLOAT_PRECISION_3_T;
            description "Min alert value for signal-to-noise ratio on ingress lane, -100002' indicates not-applicable";
        }
    }

    notification cmmTransCriticalSnrHigh {

        description "Notification sent when SNR falls above critical max value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransSnrVal {
            type cml-data-types:CML_FLOAT_PRECISION_3_T;
            description "Signal to noise ratio on ingress lane, -100002' indicates not-applicable";
        }

        leaf cmmTransSnrCriticMax {
            type cml-data-types:CML_FLOAT_PRECISION_3_T;
            description "Max critical value for signal-to-noise ratio on ingress lane, -100002' indicates not-applicable";
        }

        leaf cmmTransSnrCriticMin {
            type cml-data-types:CML_FLOAT_PRECISION_3_T;
            description "Min critical value for signal-to-noise ratio on ingress lane, -100002' indicates not-applicable";
        }
    }

    notification cmmTransCriticalSnrLow {

        description "Notification sent when SNR falls below critical min value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransSnrVal {
            type cml-data-types:CML_FLOAT_PRECISION_3_T;
            description "Signal to noise ratio on ingress lane, -100002' indicates not-applicable";
        }

        leaf cmmTransSnrCriticMax {
            type cml-data-types:CML_FLOAT_PRECISION_3_T;
            description "Max critical value for signal-to-noise ratio on ingress lane, -100002' indicates not-applicable";
        }

        leaf cmmTransSnrCriticMin {
            type cml-data-types:CML_FLOAT_PRECISION_3_T;
            description "Min critical value for signal-to-noise ratio on ingress lane, -100002' indicates not-applicable";
        }
    }

    notification cmmTransNotifyTransceiverSnrRecovered {

        description "Set when SNR of transceiver is recovered from SNR fault.";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransSnrVal {
            type cml-data-types:CML_FLOAT_PRECISION_3_T;
            description "Signal to noise ratio on ingress lane, -100002' indicates not-applicable";
        }
    }

    notification cmmTransAlertResIsiHigh {

        description "Notification sent when residual-isi falls above alert max value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransResIsiVal {
            type cml-data-types:CML_FLOAT_PRECISION_3_T;
            description "Residual-isi value, -100002' indicates not-applicable";
        }

        leaf cmmTransResIsiAlertMax {
            type cml-data-types:CML_FLOAT_PRECISION_3_T;
            description "Max alert value for residual-isi, -100002' indicates not-applicable";
        }

        leaf cmmTransResIsiAlertMin {
            type cml-data-types:CML_FLOAT_PRECISION_3_T;
            description "Min alert value for residual-isi, -100002' indicates not-applicable";
        }
    }

    notification cmmTransAlertResIsiLow {

        description "Notification sent when residual-isi falls below alert min value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransResIsiVal {
            type cml-data-types:CML_FLOAT_PRECISION_3_T;
            description "Residual-isi value, -100002' indicates not-applicable";
        }

        leaf cmmTransResIsiAlertMax {
            type cml-data-types:CML_FLOAT_PRECISION_3_T;
            description "Max alert value for residual-isi, -100002' indicates not-applicable";
        }

        leaf cmmTransResIsiAlertMin {
            type cml-data-types:CML_FLOAT_PRECISION_3_T;
            description "Min alert value for residual-isi, -100002' indicates not-applicable";
        }
    }

    notification cmmTransCriticalresIsiHigh {

        description "Notification sent when residual-isi falls above critical max value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransResIsiVal {
            type cml-data-types:CML_FLOAT_PRECISION_3_T;
            description "Residual-isi value, -100002' indicates not-applicable";
        }

        leaf cmmTransResIsiCriticMax {
            type cml-data-types:CML_FLOAT_PRECISION_3_T;
            description "Max critical value for residual-isi, -100002' indicates not-applicable";
        }

        leaf cmmTransResIsiCriticMin {
            type cml-data-types:CML_FLOAT_PRECISION_3_T;
            description "Min critical value for residual-isi, -100002' indicates not-applicable";
        }
    }

    notification cmmTransCriticalresIsiLow {

        description "Notification sent when residual-isi falls below critical min value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransResIsiVal {
            type cml-data-types:CML_FLOAT_PRECISION_3_T;
            description "Residual-isi value, -100002' indicates not-applicable";
        }

        leaf cmmTransResIsiCriticMax {
            type cml-data-types:CML_FLOAT_PRECISION_3_T;
            description "Max critical value for residual-isi, -100002' indicates not-applicable";
        }

        leaf cmmTransResIsiCriticMin {
            type cml-data-types:CML_FLOAT_PRECISION_3_T;
            description "Min critical value for residual-isi, -100002' indicates not-applicable";
        }
    }

    notification cmmTransNotifyTransceiverResIsiRecovered {

        description "Set when residual-isi of transceiver is recovered from residual-isi fault.";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransResIsiVal {
            type cml-data-types:CML_FLOAT_PRECISION_3_T;
            description "Residual-isi value, -100002' indicates not-applicable";
        }
    }

    notification cmmTransAlertLvlTranHigh {

        description "Notification sent when level transition falls above alert max value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLvlTransVal {
            type cml-data-types:CML_FLOAT_PRECISION_3_T;
            description "Level transition value, -100002' indicates not-applicable";
        }

        leaf cmmTransLvlTransAlertMax {
            type cml-data-types:CML_FLOAT_PRECISION_3_T;
            description "Max alert value for level transition, -100002' indicates not-applicable";
        }

        leaf cmmTransLvlTransAlertMin {
            type cml-data-types:CML_FLOAT_PRECISION_3_T;
            description "Min alert value for level transition, -100002' indicates not-applicable";
        }
    }

    notification cmmTransAlertLvlTranLow {

        description "Notification sent when level transition falls below alert min value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLvlTransVal {
            type cml-data-types:CML_FLOAT_PRECISION_3_T;
            description "Level transition value, -100002' indicates not-applicable";
        }

        leaf cmmTransLvlTransAlertMax {
            type cml-data-types:CML_FLOAT_PRECISION_3_T;
            description "Max alert value for level transition, -100002' indicates not-applicable";
        }

        leaf cmmTransLvlTransAlertMin {
            type cml-data-types:CML_FLOAT_PRECISION_3_T;
            description "Min alert value for level transition, -100002' indicates not-applicable";
        }
    }

    notification cmmTransCriticalLvlTranHigh {

        description "Notification sent when level transition falls above critical max value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLvlTransVal {
            type cml-data-types:CML_FLOAT_PRECISION_3_T;
            description "Level transition value, -100002' indicates not-applicable";
        }

        leaf cmmTransLvlTransCriticMax {
            type cml-data-types:CML_FLOAT_PRECISION_3_T;
            description "Max critical value for level transition, -100002' indicates not-applicable";
        }

        leaf cmmTransLvlTransCriticMin {
            type cml-data-types:CML_FLOAT_PRECISION_3_T;
            description "Min critical value for level transition, -100002' indicates not-applicable";
        }
    }

    notification cmmTransCriticalLvlTranLow {

        description "Notification sent when level transition falls below critical min value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLvlTransVal {
            type cml-data-types:CML_FLOAT_PRECISION_3_T;
            description "Level transition value, -100002' indicates not-applicable";
        }

        leaf cmmTransLvlTransCriticMax {
            type cml-data-types:CML_FLOAT_PRECISION_3_T;
            description "Max critical value for level transition, -100002' indicates not-applicable";
        }

        leaf cmmTransLvlTransCriticMin {
            type cml-data-types:CML_FLOAT_PRECISION_3_T;
            description "Min critical value for level transition, -100002' indicates not-applicable";
        }
    }

    notification cmmTransNotifyTransceiverLvlTranRecovered {

        description "Set when level transition of transceiver is recovered from level transition fault.";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLvlTransVal {
            type cml-data-types:CML_FLOAT_PRECISION_3_T;
            description "Level transition value, -100002' indicates not-applicable";
        }
    }

    notification cmmTransAlertTecCurrErrHigh {

        description "Notification sent when thermo-electric cooler current falls above alert max value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTecCurrErrVal {
            type cml-data-types:CML_FLOAT_PRECISION_3_T;
            description "Thermo-elecrical cooler current value, -100002' indicates not-applicable";
        }

        leaf cmmTransTecCurrErrAlertMax {
            type cml-data-types:CML_FLOAT_PRECISION_3_T;
            description "Max alert value for thermo-elecrical cooler current, -100002' indicates not-applicable";
        }

        leaf cmmTransTecCurrErrAlertMin {
            type cml-data-types:CML_FLOAT_PRECISION_3_T;
            description "Min alert value for thermo-elecrical cooler current, -100002' indicates not-applicable";
        }
    }

    notification cmmTransAlertTecCurrErrLow {

        description "Notification sent when thermo-electric cooler current falls below alert min value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTecCurrErrVal {
            type cml-data-types:CML_FLOAT_PRECISION_3_T;
            description "Thermo-elecrical cooler current value, -100002' indicates not-applicable";
        }

        leaf cmmTransTecCurrErrAlertMax {
            type cml-data-types:CML_FLOAT_PRECISION_3_T;
            description "Max alert value for thermo-elecrical cooler current, -100002' indicates not-applicable";
        }

        leaf cmmTransTecCurrErrAlertMin {
            type cml-data-types:CML_FLOAT_PRECISION_3_T;
            description "Min alert value for thermo-elecrical cooler current, -100002' indicates not-applicable";
        }
    }

    notification cmmTransCriticalTecCurrErrHigh {

        description "Notification sent when thermo-electric cooler current falls above critical max value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTecCurrErrVal {
            type cml-data-types:CML_FLOAT_PRECISION_3_T;
            description "Thermo-elecrical cooler current value, -100002' indicates not-applicable";
        }

        leaf cmmTransTecCurrErrCriticMax {
            type cml-data-types:CML_FLOAT_PRECISION_3_T;
            description "Max critical value for thermo-elecrical cooler current, -100002' indicates not-applicable";
        }

        leaf cmmTransTecCurrErrCriticMin {
            type cml-data-types:CML_FLOAT_PRECISION_3_T;
            description "Min critical value for thermo-elecrical cooler current, -100002' indicates not-applicable";
        }
    }

    notification cmmTransCriticalTecCurrErrLow {

        description "Notification sent when thermo-electric cooler current falls below critical min value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTecCurrErrVal {
            type cml-data-types:CML_FLOAT_PRECISION_3_T;
            description "Thermo-elecrical cooler current value, -100002' indicates not-applicable";
        }

        leaf cmmTransTecCurrErrCriticMax {
            type cml-data-types:CML_FLOAT_PRECISION_3_T;
            description "Max critical value for thermo-elecrical cooler current, -100002' indicates not-applicable";
        }

        leaf cmmTransTecCurrErrCriticMin {
            type cml-data-types:CML_FLOAT_PRECISION_3_T;
            description "Min critical value for thermo-elecrical cooler current, -100002' indicates not-applicable";
        }
    }

    notification cmmTransNotifyTransceiverTecCurrErrRecovered {

        description "Set when thermo-electric cooler current of transceiver is recovered thermo-electric cooler current fault.";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransTecCurrErrVal {
            type cml-data-types:CML_FLOAT_PRECISION_3_T;
            description "Thermo-elecrical cooler current value, -100002' indicates not-applicable";
        }
    }

    notification cmmTransAlertLaserTempValHigh {

        description "Notification sent when laser temperature falls above alert max value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLaserTempVal {
            type cml-data-types:CML_FLOAT_PRECISION_3_T;
            description "Laser Temparature value, -100002' indicates not-applicable";
        }

        leaf cmmTransLaserTempAlertMax {
            type cml-data-types:CML_FLOAT_PRECISION_3_T;
            description "Max alert value for Laser Temperature, -100002' indicates not-applicable";
        }

        leaf cmmTransLaserTempAlertMin {
            type cml-data-types:CML_FLOAT_PRECISION_3_T;
            description "Min alert value for Laser Temperature, -100002' indicates not-applicable";
        }
    }

    notification cmmTransAlertLaserTempValLow {

        description "Notification sent when laser temperature falls below alert min value.";

        // severity "WARNING";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLaserTempVal {
            type cml-data-types:CML_FLOAT_PRECISION_3_T;
            description "Laser Temparature value, -100002' indicates not-applicable";
        }

        leaf cmmTransLaserTempAlertMax {
            type cml-data-types:CML_FLOAT_PRECISION_3_T;
            description "Max alert value for Laser Temperature, -100002' indicates not-applicable";
        }

        leaf cmmTransLaserTempAlertMin {
            type cml-data-types:CML_FLOAT_PRECISION_3_T;
            description "Min alert value for Laser Temperature, -100002' indicates not-applicable";
        }
    }

    notification cmmTransCriticalLaserTempValHigh {

        description "Notification sent when laser temperature falls above crictical max value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLaserTempVal {
            type cml-data-types:CML_FLOAT_PRECISION_3_T;
            description "Laser Temparature value, -100002' indicates not-applicable";
        }

        leaf cmmTransLaserTempCriticMax {
            type cml-data-types:CML_FLOAT_PRECISION_3_T;
            description "Max critical value for Laser Temperature, -100002' indicates not-applicable";
        }

        leaf cmmTransLaserTempCriticMin {
            type cml-data-types:CML_FLOAT_PRECISION_3_T;
            description "Min critical value for Laser Temperature, -100002' indicates not-applicable";
        }
    }

    notification cmmTransCriticalLaserTempValLow {

        description "Notification sent when laser temperature falls below critical min value.";

        // severity "CRITICAL";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLaserTempVal {
            type cml-data-types:CML_FLOAT_PRECISION_3_T;
            description "Laser Temparature value, -100002' indicates not-applicable";
        }

        leaf cmmTransLaserTempCriticMax {
            type cml-data-types:CML_FLOAT_PRECISION_3_T;
            description "Max critical value for Laser Temperature, -100002' indicates not-applicable";
        }

        leaf cmmTransLaserTempCriticMin {
            type cml-data-types:CML_FLOAT_PRECISION_3_T;
            description "Min critical value for Laser Temperature, -100002' indicates not-applicable";
        }
    }

    notification cmmTransNotifyTransceiverLaserTempRecovered {

        description "Set when laser temperature of transceiver is recovered from temperature fault.";

        // severity "MINOR";
        // eventClass "STATE";
        leaf cmmTransIndex {
            type cml-data-types:CML_UINT32_T;
            description "A unique index for each slot within the unit.";
        }

        leaf cmmStackUnitIndex {
            type cml-data-types:CML_INT32_T;
            description "The unique index for this entry.Refer to the object cmmStackUnitIndexNext.";
        }

        leaf cmmTransType {
            type cml-data-types:CML_CMM_TRANS_TYPE_T;
            description "Type of the transceiver SFP/QSFP.";
        }

        leaf cmmTransChannelIndex {
            type cml-data-types:CML_UINT8_T;
            description "A unique value, greater than zero, for each channel in the transceiver within the unit.For SFP transceivers, only channel '1' is applicable.";
        }

        leaf cmmTransLaserTempVal {
            type cml-data-types:CML_FLOAT_PRECISION_3_T;
            description "Laser Temparature value, -100002' indicates not-applicable";
        }
    }

    notification cmmCoherentOpticalModuleNotifyInserted {

        description "Set when coherent optical module is inserted..";

        // eventClass "STATE";
        leaf slotIndex {
            type cml-data-types:CML_UINT8_T;
            description "Index to select a optical module slot.";
        }

        leaf modulePresence {
            type cml-data-types:CML_CMM_DEVICE_PRESENCE_T;
            description "Specifies whether coherent optical module is Present in the slot.";
        }

        leaf cardType {
            type  CML_CMM_CARD_TYPE_T;
            description "Specifies the coherent optical module Type, currently supported module types are ACO and DCO.";
        }
    }

    notification cmmCoherentOpticalModuleNotifyRemoved {

        description "Set when coherent optical module is removed..";

        // eventClass "STATE";
        leaf slotIndex {
            type cml-data-types:CML_UINT8_T;
            description "Index to select a optical module slot.";
        }

        leaf modulePresence {
            type cml-data-types:CML_CMM_DEVICE_PRESENCE_T;
            description "Specifies whether coherent optical module is Present in the slot.";
        }

        leaf cardType {
            type  CML_CMM_CARD_TYPE_T;
            description "Specifies the coherent optical module Type, currently supported module types are ACO and DCO.";
        }
    }

    notification cmmCoherentOpticalCFPTransInserted {

        description "Notification sent when CFP transceiver is inserted..";

        // eventClass "STATE";
        leaf slotIndex {
            type cml-data-types:CML_UINT8_T;
            description "Index to select a optical module slot.";
        }

        leaf cardType {
            type  CML_CMM_CARD_TYPE_T;
            description "Specifies the coherent optical module Type, currently supported module types are ACO and DCO.";
        }

        leaf netIndex {
            type cml-data-types:CML_UINT8_T;
            description "Index of network interface in a coherent optical module.";
        }
    }

    notification cmmCoherentOpticalCFPTransRemoved {

        description "Notification sent when CFP transceiver is removed..";

        // eventClass "STATE";
        leaf slotIndex {
            type cml-data-types:CML_UINT8_T;
            description "Index to select a optical module slot.";
        }

        leaf cardType {
            type  CML_CMM_CARD_TYPE_T;
            description "Specifies the coherent optical module Type, currently supported module types are ACO and DCO.";
        }

        leaf netIndex {
            type cml-data-types:CML_UINT8_T;
            description "Index of network interface in a coherent optical module.";
        }
    }

    notification cmmCoherentOpticalChannelRxLosAlarm {

        description "Notification sent when RX LOS Alarm is raised or cleared..";

        // eventClass "STATE";
        leaf slotIndex {
            type cml-data-types:CML_UINT8_T;
            description "Index to select a optical module slot.";
        }

        leaf netIndex {
            type cml-data-types:CML_UINT8_T;
            description "Index of network interface in a coherent optical module.";
        }

        leaf operRxLosAlarm {
            type cml-data-types:CML_UINT32_T;
            description "Specifies netif rx-los-alarm.";
        }
    }

    notification hostp_vm_start_db {

        description "Notify to db when 'stop' cli is executed.";

        // severity "INFO";
        // eventClass "CONFIG";
        leaf vmName {
            type cml-data-types:CML_STRING_T;
            description "Name of the VM";
        }

        leaf vrId {
            type cml-data-types:CML_UINT32_T;
            description "Virtual router id";
        }
    }

    notification SysUpdateInstallation {

        description "This system update event is generated when the software installation starts and ends..";

        // severity "INFO";
        // eventClass "MESSAGE";
        leaf message {
            type string;
            description " alarm message notification";
        }
    }

    notification SysUpdateDownloadStatus {

        description "Notification sent on download operation completion, on success with INFO severity/on failure with MAJOR severity..";

        // severity "INFO";
        // eventClass "MESSAGE";
        leaf message {
            type string;
            description " alarm message notification";
        }
    }

    notification cpuQueueFull {

        description "notification to send information when CPU queue is full..";

        // severity "CRITICAL";
        // eventClass "STATE";
        leaf queueId {
            type cml-data-types:CML_UINT8_T;
            description "cpuqueueId is a unique number representing each queue in CPU";
        }

        leaf queueName {
            type cml-data-types:CML_STRING_T;
            description "Queue Name corresponding to the QueueId.";
        }

        leaf ratePercent {
            type cml-data-types:CML_INT8_T;
            description "Percentage of control packets transmitted in the CPU queue.
            Value of -1 indicates rate percentage is not applicable.";
        }

        leaf txPktRate {
            type cml-data-types:CML_UINT32_T;
            description "The number of Tx Pkts transmitted from the corresponding CPU queue.";
        }

        leaf lastIncrementCnt {
            type cml-data-types:CML_COUNTER64_T;
            description "The number of Last Dropped Pkts in the corresponding CPU queue.
            This is Updated at every 5sec interval.";
        }

        leaf lastIncrementTime {
            type cml-data-types:CML_DATE_TIME_T;
            description "Last increment time of Tx Dropped Packets in CPU Queue.
             This is Updated at every 5sec interval.";
        }
    }

    notification cpuQueueHigh {

        description "notification to send information when CPU queue is high crossing threshold of 90%..";

        // severity "WARNING";
        // eventClass "STATE";
        leaf queueId {
            type cml-data-types:CML_UINT8_T;
            description "cpuqueueId is a unique number representing each queue in CPU";
        }

        leaf queueName {
            type cml-data-types:CML_STRING_T;
            description "Queue Name corresponding to the QueueId.";
        }

        leaf ratePercent {
            type cml-data-types:CML_INT8_T;
            description "Percentage of control packets transmitted in the CPU queue.
            Value of -1 indicates rate percentage is not applicable.";
        }

        leaf txPktRate {
            type cml-data-types:CML_UINT32_T;
            description "The number of Tx Pkts transmitted from the corresponding CPU queue.";
        }
    }

    notification cpuQueueRecovery {

        description "notification to send information when CPU queue is recovered from full/high..";

        // severity "MINOR";
        // eventClass "STATE";
        leaf queueId {
            type cml-data-types:CML_UINT8_T;
            description "cpuqueueId is a unique number representing each queue in CPU";
        }

        leaf queueName {
            type cml-data-types:CML_STRING_T;
            description "Queue Name corresponding to the QueueId.";
        }

        leaf ratePercent {
            type cml-data-types:CML_INT8_T;
            description "Percentage of control packets transmitted in the CPU queue.
            Value of -1 indicates rate percentage is not applicable.";
        }
    }

    notification cpuCRCErrorPkts {

        description "notification to send information for CRC error packets received on the cpu interface..";

        // severity "WARNING";
        // eventClass "STATE";
        leaf badCrc {
            type cml-data-types:CML_COUNTER64_T;
            description "Last increment time of Bad CRC packets.
             This is Updated at every 5sec interval.";
        }
    }

    notification cpuUndersizeErrorPkts {

        description "notification to send information for undersize error packets received on the cpu interface..";

        // severity "WARNING";
        // eventClass "STATE";
        leaf undersizePkts {
            type cml-data-types:CML_COUNTER64_T;
            description "Last inbound packets discarded whose size are less than
             64 octets (which exclude framing bits, but include the FCS)
             and have a good FCS value.
             This is Updated at every 5sec interval.";
        }
    }

    notification cpuOversizeErrorPkts {

        description "notification to send information for oversize error packets received on the cpu interface..";

        // severity "WARNING";
        // eventClass "STATE";
        leaf mtuExceed {
            type cml-data-types:CML_COUNTER64_T;
            description "Rx Oversize Packets";
        }
    }

    notification cpuFragementErrorPkts {

        description "notification to send information for fragment error packets received on the cpu interface..";

        // severity "WARNING";
        // eventClass "STATE";
        leaf fragmentsPkts {
            type cml-data-types:CML_COUNTER64_T;
            description "Last inbound packets discarded whose size are less than
             64 octets (which exclude framing bits, but include the FCS)
             and have a bad FCS value.
             This is Updated at every 5sec interval.";
        }
    }

    notification cpuJabberErrorPkts {

        description "notification to send information for jabber error packets received on the cpu interface..";

        // severity "WARNING";
        // eventClass "STATE";
        leaf jabberPkts {
            type cml-data-types:CML_COUNTER64_T;
            description "Last inbound packets whose size are more than maximum
            transmission unit size (which excludes framing bits, but include
            FCS) and have a bad FCS value.
            This is Updated at every 5sec interval.";
        }
    }

    notification ifCRCErrorPkts {

        description "notification to send information for CRC error packets received on the interface..";

        // severity "WARNING";
        // eventClass "STATE";
        leaf ifName {
            type cml-data-types:CML_STRING_T;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type cml-data-types:CML_UINT32_T;
            description "Virtual router id";
        }

        leaf badCrc {
            type cml-data-types:CML_COUNTER64_T;
            description "Last increment time of Bad CRC packets.
             This is Updated at every 5sec interval.";
        }
    }

    notification ifUndersizeErrorPkts {

        description "notification to send information for undersize error packets received on the interface..";

        // severity "WARNING";
        // eventClass "STATE";
        leaf ifName {
            type cml-data-types:CML_STRING_T;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type cml-data-types:CML_UINT32_T;
            description "Virtual router id";
        }

        leaf undersizePkts {
            type cml-data-types:CML_COUNTER64_T;
            description "Last inbound packets discarded whose size are less than
             64 octets (which exclude framing bits, but include the FCS)
             and have a good FCS value.
             This is Updated at every 5sec interval.";
        }
    }

    notification ifOversizeErrorPkts {

        description "notification to send information for oversize error packets received on the interface..";

        // severity "WARNING";
        // eventClass "STATE";
        leaf ifName {
            type cml-data-types:CML_STRING_T;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type cml-data-types:CML_UINT32_T;
            description "Virtual router id";
        }

        leaf mtuExceed {
            type cml-data-types:CML_COUNTER64_T;
            description "Rx Oversize Packets";
        }
    }

    notification ifFragementErrorPkts {

        description "notification to send information for fragment error packets received on the interface..";

        // severity "WARNING";
        // eventClass "STATE";
        leaf ifName {
            type cml-data-types:CML_STRING_T;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type cml-data-types:CML_UINT32_T;
            description "Virtual router id";
        }

        leaf fragmentsPkts {
            type cml-data-types:CML_COUNTER64_T;
            description "Last inbound packets discarded whose size are less than
             64 octets (which exclude framing bits, but include the FCS)
             and have a bad FCS value.
             This is Updated at every 5sec interval.";
        }
    }

    notification ifJabberErrorPkts {

        description "notification to send information for jabber error packets received on the interface..";

        // severity "WARNING";
        // eventClass "STATE";
        leaf ifName {
            type cml-data-types:CML_STRING_T;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type cml-data-types:CML_UINT32_T;
            description "Virtual router id";
        }

        leaf jabberPkts {
            type cml-data-types:CML_COUNTER64_T;
            description "Last inbound packets whose size are more than maximum
            transmission unit size (which excludes framing bits, but include
            FCS) and have a bad FCS value.
            This is Updated at every 5sec interval.";
        }
    }

}
