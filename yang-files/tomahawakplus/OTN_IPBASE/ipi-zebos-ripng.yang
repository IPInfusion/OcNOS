/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-ripng.yang
*
*/

submodule ipi-zebos-ripng {

    belongs-to  ipi-zebos { prefix ipi-zebos; }

    import cml-data-types {
        prefix cml-data-types;
    }

    import feature-list {
        prefix feature-list;
    }

    include ipi-zebos-interface;
    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "";


    revision "2018-06-21" {
        description " Initial Version.";
        reference "";
    }

    grouping ripngContents {
        description
            "Elements for all ripng instances";
        leaf-list passiveifName  {
            type  cml-data-types:CML_STRING_T;
            description "";
        } // END of passiveifName definition.

        leaf command  {
            type  cml-data-types:CML_UINT8_T;
            config false;
            description "";
        } // END of command definition.

        leaf version  {
            type  cml-data-types:CML_UINT8_T;
            config false;
            description "";
        } // END of version definition.

        leaf defaultDistance  {
            type  cml-data-types:CML_UINT8_T {
                 range "1..255";
            }
            description "";
        } // END of defaultDistance definition.

        leaf maxMtu  {
            type  cml-data-types:CML_INT32_T;
            config false;
            description "";
        } // END of maxMtu definition.

        leaf-list route  {
            type  cml-data-types:CML_IPV6_PREFIX_T;
            description "";
        } // END of route definition.

        leaf-list aggregatePrefix  {
            type  cml-data-types:CML_IPV6_PREFIX_T;
            description "";
        } // END of aggregatePrefix definition.

        leaf updateTime  {
            type  cml-data-types:CML_UINT32_T {
                 range "5..2147483647";
            }
            default "30";
            description "";
        } // END of updateTime definition.

        leaf timeoutTime  {
            type  cml-data-types:CML_UINT32_T {
                 range "5..2147483647";
            }
            default "180";
            description "";
        } // END of timeoutTime definition.

        leaf garbageTime  {
            type  cml-data-types:CML_UINT32_T {
                 range "5..2147483647";
            }
            default "120";
            description "";
        } // END of garbageTime definition.

        leaf pcounter  {
            type  cml-data-types:CML_UINT32_T;
            config false;
            description "";
        } // END of pcounter definition.

        leaf pmax  {
            type  cml-data-types:CML_UINT32_T;
            config false;
            description "";
        } // END of pmax definition.

        leaf pconnect  {
            type  cml-data-types:CML_UINT32_T;
            config false;
            description "";
        } // END of pconnect definition.

        leaf defaultMetric  {
            type  cml-data-types:CML_INT32_T {
                 range "1..15";
            }
            description "";
        } // END of defaultMetric definition.

        leaf defaultInformation  {
            type  cml-data-types:CML_BOOL_T;
            description "";
        } // END of defaultInformation definition.

        leaf metricType  {
            type  cml-data-types:CML_RIP_METRIC_T;
            default "disable";
            description "";
        } // END of metricType definition.

        leaf recvBufsize  {
            type  cml-data-types:CML_UINT32_T {
                 range "8192..2147483647";
            }
            default "8192";
            description "";
        } // END of recvBufsize definition.


        list ripngInterface {
            key "ifName";
            config false;
            description
                "RIP specific interface configuration";
            leaf ifName  {
                type  cml-data-types:CML_STRING_T;
                description "";
            } // END of ifName definition.

            leaf ifFlags  {
                type  cml-data-types:CML_UINT8_T;
                description "";
            } // END of ifFlags definition.

            leaf lock  {
                type  cml-data-types:CML_UINT16_T;
                description "";
            } // END of lock definition.

            leaf ifSplitHorizon  {
                type  cml-data-types:CML_RIP_SPLIT_HORIZON_T;
                description "";
            } // END of ifSplitHorizon definition.

            leaf-list ifAccessList  {
                type  cml-data-types:CML_STRING_T;
                description "";
            } // END of ifAccessList definition.

            leaf-list ifPrefixList  {
                type  cml-data-types:CML_STRING_T;
                description "";
            } // END of ifPrefixList definition.

            leaf-list ifRouteMap  {
                type  cml-data-types:CML_STRING_T;
                description "";
            } // END of ifRouteMap definition.

        } // End of ripngInterface-list

        list nbrTable {
            key "neighborAddr";
            description
                "nbrTable";
            leaf neighborAddr  {
                type  cml-data-types:CML_IPV6_ADDR_T;
                description "";
            } // END of neighborAddr definition.

            leaf ifName  {
                type  cml-data-types:CML_STRING_T;
                mandatory true;
                description "";
            } // END of ifName definition.

        } // End of nbrTable-list

        list ripngDatabase {
            key "prefix";
            config false;
            description
                "RIP routing information base";
            leaf prefix  {
                type  cml-data-types:CML_STRING_T;
                description "";
            } // END of prefix definition.

            container ripngInfo {
                config false;
                description
                    "RIP routing information base";
                leaf routeType  {
                    type  cml-data-types:CML_INT32_T;
                    description "";
                } // END of routeType definition.

                leaf subType  {
                    type  cml-data-types:CML_INT32_T;
                    description "";
                } // END of subType definition.

                leaf nexthop  {
                    type  cml-data-types:CML_STRING_T;
                    description "";
                } // END of nexthop definition.

                leaf from  {
                    type  cml-data-types:CML_STRING_T;
                    description "";
                } // END of from definition.

                leaf metric  {
                    type  cml-data-types:CML_UINT8_T;
                    description "";
                } // END of metric definition.

                leaf tag  {
                    type  cml-data-types:CML_UINT16_T;
                    description "";
                } // END of tag definition.

                leaf suppress  {
                    type  cml-data-types:CML_UINT32_T;
                    description "";
                } // END of suppress definition.

                leaf metricSet  {
                    type  cml-data-types:CML_UINT8_T;
                    description "";
                } // END of metricSet definition.

                leaf flags  {
                    type  cml-data-types:CML_UINT8_T;
                    description "";
                } // END of flags definition.

                leaf distance  {
                    type  cml-data-types:CML_UINT8_T;
                    description "";
                } // END of distance definition.


                list nexthopList {
                    key "nextHopAddr";
                    config false;
                    description
                        "RIP nexthop";
                    leaf nextHopAddr  {
                        type  cml-data-types:CML_STRING_T;
                        description "";
                    } // END of nextHopAddr definition.

                    leaf from  {
                        type  cml-data-types:CML_STRING_T;
                        description "";
                    } // END of from definition.

                    leaf ifindex  {
                        type  cml-data-types:CML_UINT32_T;
                        description "";
                    } // END of ifindex definition.

                    leaf nexthopFlags  {
                        type  cml-data-types:CML_UINT8_T;
                        description "";
                    } // END of nexthopFlags definition.

                    leaf timeout  {
                        type  cml-data-types:CML_STRING_T;
                        description "";
                    } // END of timeout definition.

                    leaf nextHopOut  {
                        type  cml-data-types:CML_STRING_T;
                        description "";
                    } // END of nextHopOut definition.

                    leaf metricSet  {
                        type  cml-data-types:CML_UINT8_T;
                        description "";
                    } // END of metricSet definition.

                    leaf metricOut  {
                        type  cml-data-types:CML_UINT8_T;
                        description "";
                    } // END of metricOut definition.

                    leaf routeMetric  {
                        type  cml-data-types:CML_UINT8_T;
                        description "";
                    } // END of routeMetric definition.

                    leaf nexthopTimeoutTime  {
                        type  cml-data-types:CML_UINT32_T;
                        description "";
                    } // END of nexthopTimeoutTime definition.

                } // End of nexthopList-list
            } // END of ripngInfo-container definition.
            container aggregate {
                config false;
                description
                    "RIP aggregated";
                leaf count  {
                    type  cml-data-types:CML_INT32_T;
                    description "";
                } // END of count definition.

                leaf suppress  {
                    type  cml-data-types:CML_INT32_T;
                    description "";
                } // END of suppress definition.

                leaf metric  {
                    type  cml-data-types:CML_INT8_T;
                    description "";
                } // END of metric definition.

                leaf tag  {
                    type  cml-data-types:CML_INT16_T;
                    description "";
                } // END of tag definition.

            } // END of aggregate-container definition.
        } // End of ripngDatabase-list

        list ripOffsetDistributeListIfname {
            key "ifName";
            description
                "ripOffsetDistributeListIfname";
            leaf ifName  {
                type  cml-data-types:CML_STRING_T;
                description "";
            } // END of ifName definition.

            uses ripngListCmdsUtility;
        } // End of ripOffsetDistributeListIfname-list

        list ifrm {
            key "routemapName";
            description
                "RIPng if rmap master";
            leaf routemapName  {
                type  cml-data-types:CML_STRING_T;
                description "";
            } // END of routemapName definition.

            leaf routemapType  {
                type  cml-data-types:CML_RIPNG_FILTERING_T;
                mandatory true;
                description "";
            } // END of routemapType definition.

            leaf ifName  {
                type  cml-data-types:CML_STRING_T;
                mandatory true;
                description "";
            } // END of ifName definition.

        } // End of ifrm-list
        uses ripngListCmdsUtility;
    } // END of ripngContents definition.
    grouping ripngListCmdsUtility {
        description
            "ripngListCmdsUtility";

        list offsetList {
            key "directStr";
            description
                "offsetList";
            leaf alistName  {
                type  cml-data-types:CML_STRING_T;
                mandatory true;
                description "";
            } // END of alistName definition.

            leaf directStr  {
                type  cml-data-types:CML_RIP_DIRECTION_T;
                description "";
            } // END of directStr definition.

            leaf metric  {
                type  cml-data-types:CML_UINT32_T {
                     range "0..16";
                }
                mandatory true;
                description "";
            } // END of metric definition.

        } // End of offsetList-list

        list distributionList {
            key "directionStr";
            description
                "distributionList";
            leaf listName  {
                type  cml-data-types:CML_STRING_T;
                mandatory true;
                description "";
            } // END of listName definition.

            leaf directionStr  {
                type  cml-data-types:CML_RIP_DIRECTION_T;
                description "";
            } // END of directionStr definition.

        } // End of distributionList-list

        list distributionPrefixList {
            key "distributeType";
            description
                "distributionPrefixList";
            leaf prefixListName  {
                type  cml-data-types:CML_STRING_T;
                mandatory true;
                description "";
            } // END of prefixListName definition.

            leaf distributeType  {
                type  cml-data-types:CML_RIP_DIRECTION_T;
                description "";
            } // END of distributeType definition.

        } // End of distributionPrefixList-list
    } // END of ripngListCmdsUtility definition.

    grouping  ripngConfiguration-grouping {
    description
        "RIPNG master for system wide configuration and variables";
    container ripngConfiguration {
        description
            "RIPNG master for system wide configuration and variables";
        leaf termDebugFlag  {
            type  cml-data-types:CML_RIPNG_DEBUG_T;
            description "";
        } // END of termDebugFlag definition.

        leaf confDebugFlag  {
            type  cml-data-types:CML_RIPNG_DEBUG_T;
            description "";
        } // END of confDebugFlag definition.

        leaf globalRouteChanges  {
            type  cml-data-types:CML_INT32_T;
            config false;
            description "";
        } // END of globalRouteChanges definition.


        list ripngIntParam {
            key "ifName";
            description
                "RIPNG interface parameter pool";
            leaf ifName  {
                type  cml-data-types:CML_STRING_T;
                description "";
            } // END of ifName definition.

            leaf router  {
                type  cml-data-types:CML_BOOL_T;
                description "";
            } // END of router definition.

            leaf splitHorizon  {
                type  cml-data-types:CML_RIPNG_SPLIT_HORIZON_T;
                description "";
            } // END of splitHorizon definition.

            leaf metricOffset  {
                type  cml-data-types:CML_UINT8_T {
                     range "1..16";
                }
                description "";
            } // END of metricOffset definition.

        } // End of ripngIntParam-list
        container ripng {
            presence "yes";
            description
                "RIPNG Default instance";
            leaf ripngDefaultInstance  {
                type  cml-data-types:CML_RIPNG_INSTANCE_T;
                mandatory true;
                description "";
            } // END of ripngDefaultInstance definition.


            list redistributeMap {
                key "routeTypeVal";
                description
                    "redistributeMap";
                leaf routeTypeVal  {
                    type  cml-data-types:CML_RIPNG_REDIST_PROTOS_T;
                    description "";
                } // END of routeTypeVal definition.

                leaf metric  {
                    type  cml-data-types:CML_INT32_T {
                         range "0..16";
                    }
                    mandatory true;
                    description "";
                } // END of metric definition.

                leaf routeMap  {
                    type  cml-data-types:CML_STRING_T;
                    mandatory true;
                    description "";
                } // END of routeMap definition.

            } // End of redistributeMap-list

            list vrfRipng {
                if-feature feature-list:HAVE_VRF_RIPNG;
                key "vrfName";
                description
                    "Configure a RIPNG address family for each VRF configured";
                leaf vrfName  {
                    type  cml-data-types:CML_STRING_T;
                    description "";
                } // END of vrfName definition.


                list redistributeMapVRF {
                    key "vrfRouteType";
                    description
                        "redistributeMapVRF";
                    leaf vrfRouteType  {
                        type  cml-data-types:CML_RIPNG_VRF_REDIST_PROTOS_T;
                        description "";
                    } // END of vrfRouteType definition.

                    leaf metric  {
                        type  cml-data-types:CML_INT32_T {
                             range "0..16";
                        }
                        mandatory true;
                        description "";
                    } // END of metric definition.

                    leaf vrfRouteMap  {
                        type  cml-data-types:CML_STRING_T;
                        mandatory true;
                        description "";
                    } // END of vrfRouteMap definition.

                } // End of redistributeMapVRF-list
                uses ripngContents;
            } // End of vrfRipng-list
            uses ripngContents;
        } // END of ripng-container definition.
    } // END of ripngConfiguration-container definition.
    } // END of ripngConfiguration-container definition.


}
