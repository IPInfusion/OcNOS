/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-mlag.yang
*
*/

submodule ipi-zebos-mlag {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "NSM Mlag configurations";


    revision "2018-06-21" {
        description " Initial Version.";
        reference "";
    }


    grouping  mlagAgg-grouping {
    description
        "mlagAgg";
    container mlagAgg {
        presence "yes";
        description
            "mlagAgg";
        leaf mlagGroupNumber  {
            type  cml-data-types:CML_UINT16_T {
                 range "1..255";
            }
            mandatory true;
            description "";
        } // END of mlagGroupNumber definition.

    } // END of mlagAgg-container definition.
    } // END of mlagAgg-container definition.

    grouping  nsmMlag-grouping {
    description
        "nsm mlag master";
    container nsmMlag {
        config false;
        description
            "nsm mlag master";

        list mlagInterface {
            key "mlagId";
            config false;
            description
                "struct nsm_mlag_admin_info";
            leaf mlagId  {
                type  cml-data-types:CML_UINT16_T;
                description "";
            } // END of mlagId definition.

            leaf ifFlags  {
                type  cml-data-types:CML_UINT16_T;
                description "";
            } // END of ifFlags definition.

            leaf bandwidth  {
                type  cml-data-types:CML_UINT64_T;
                description "";
            } // END of bandwidth definition.

            leaf adminInfoConfig  {
                type  cml-data-types:CML_UINT8_T;
                description "";
            } // END of adminInfoConfig definition.

        } // End of mlagInterface-list
        container idp {
            config false;
            description
                "idp";
            leaf idpIfname  {
                type  cml-data-types:CML_STRING_T;
                description "";
            } // END of idpIfname definition.

            leaf idpIfIndex  {
                type  cml-data-types:CML_UINT32_T;
                description "";
            } // END of idpIfIndex definition.

            leaf idpIfFlags  {
                type  cml-data-types:CML_UINT8_T;
                description "";
            } // END of idpIfFlags definition.

            leaf ifType  {
                type  cml-data-types:CML_UINT8_T;
                description "";
            } // END of ifType definition.

            leaf bridgeName  {
                type  cml-data-types:CML_STRING_T;
                description "";
            } // END of bridgeName definition.

            leaf switchport  {
                type  cml-data-types:CML_STRING_T;
                description "";
            } // END of switchport definition.

            leaf zifType  {
                type  cml-data-types:CML_UINT8_T;
                description "";
            } // END of zifType definition.

            leaf info  {
                type  cml-data-types:CML_STRING_T;
                description "";
            } // END of info definition.

        } // END of idp-container definition.
        container mstpSyncInfo {
            config false;
            description
                "mstpSyncInfo";
            leaf msgType  {
                type  cml-data-types:CML_UINT8_T;
                description "";
            } // END of msgType definition.

            leaf bridgePriority  {
                type  cml-data-types:CML_UINT16_T;
                description "";
            } // END of bridgePriority definition.

            leaf pathcostMethod  {
                type  cml-data-types:CML_UINT8_T;
                description "";
            } // END of pathcostMethod definition.

            leaf numOfEntries  {
                type  cml-data-types:CML_UINT16_T;
                description "";
            } // END of numOfEntries definition.

            leaf-list domainDigest  {
                type  cml-data-types:CML_UINT8_T;
                description "";
            } // END of domainDigest definition.


            list mcecMstpIfSyncEntry {
                key "IfSyncMlagId";
                config false;
                description
                    "nsm_mcec_mstp_if_sync_entry";
                leaf IfSyncMlagId  {
                    type  cml-data-types:CML_UINT16_T;
                    description "";
                } // END of IfSyncMlagId definition.

                leaf portPriority  {
                    type  cml-data-types:CML_UINT16_T;
                    description "";
                } // END of portPriority definition.

                leaf pathCost  {
                    type  cml-data-types:CML_UINT32_T;
                    description "";
                } // END of pathCost definition.

                leaf-list interfaceDigest  {
                    type  cml-data-types:CML_UINT8_T;
                    description "";
                } // END of interfaceDigest definition.

            } // End of mcecMstpIfSyncEntry-list
        } // END of mstpSyncInfo-container definition.
    } // END of nsmMlag-container definition.
    } // END of nsmMlag-container definition.


}
