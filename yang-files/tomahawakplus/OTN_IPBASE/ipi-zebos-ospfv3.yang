/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-ospfv3.yang
*
*/

submodule ipi-zebos-ospfv3 {

    belongs-to  ipi-zebos { prefix ipi-zebos; }

    import cml-data-types {
        prefix cml-data-types;
    }

    import feature-list {
        prefix feature-list;
    }

    include ipi-zebos-interface;
    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "Layer-3 OSPFv3 configurations";


    revision "2018-06-21" {
        description " Initial Version.";
        reference "";
    }

    grouping lsdb {
        description
            "lsdb";
        leaf lsdbIfName  {
            type  cml-data-types:CML_STRING_T;
            config false;
            description "";
        } // END of lsdbIfName definition.

        leaf lsdbAreaId  {
            type  cml-data-types:CML_STRING_T;
            config false;
            description "";
        } // END of lsdbAreaId definition.


        list lsdbSlot {
            key "lsdbSlotType";
            config false;
            description
                "LSDB of AS-external-LSAs.";
            leaf lsdbSlotType  {
                type  cml-data-types:CML_UINT32_T;
                description "";
            } // END of lsdbSlotType definition.


            list lsa {
                key "lsaLinkId";
                config false;
                description
                    "OSPFv3 Link State Advertisement (LSA) list";
                leaf lsaLinkId  {
                    type  cml-data-types:CML_STRING_T;
                    description "";
                } // END of lsaLinkId definition.

                leaf lsaAge  {
                    type  cml-data-types:CML_UINT32_T;
                    description "";
                } // END of lsaAge definition.

                leaf lsaType  {
                    type  cml-data-types:CML_UINT32_T;
                    description "";
                } // END of lsaType definition.

                leaf lsaLength  {
                    type  cml-data-types:CML_UINT32_T;
                    description "";
                } // END of lsaLength definition.

                leaf lsaAdvRouter  {
                    type  cml-data-types:CML_STRING_T;
                    description "";
                } // END of lsaAdvRouter definition.

                leaf lsaSeqNum  {
                    type  cml-data-types:CML_STRING_T;
                    description "";
                } // END of lsaSeqNum definition.

                leaf lsaCheckSum  {
                    type  cml-data-types:CML_STRING_T;
                    description "";
                } // END of lsaCheckSum definition.

                leaf isLsaInterRouter  {
                    type  cml-data-types:CML_BOOL_T;
                    description "";
                } // END of isLsaInterRouter definition.

                leaf lsaRouterLinkCount  {
                    type  cml-data-types:CML_UINT32_T;
                    description "";
                } // END of lsaRouterLinkCount definition.

                leaf lsaRefTypeStr  {
                    type  cml-data-types:CML_STRING_T;
                    description "";
                } // END of lsaRefTypeStr definition.

            } // End of lsa-list
        } // End of lsdbSlot-list
    } // END of lsdb definition.
    grouping Route {
        description
            "Route";

        list ospf6Route {
            key "routeIPV6Prefix";
            config false;
            description
                "OSPFv3 Route";
            leaf routeIPV6Prefix  {
                type  cml-data-types:CML_STRING_T;
                description "";
            } // END of routeIPV6Prefix definition.

            leaf routeDistance  {
                type  cml-data-types:CML_UINT8_T;
                description "";
            } // END of routeDistance definition.

            container ospf6Path {
                config false;
                description
                    "OSPFv3 path details for different routes";
                leaf pathType  {
                    type  cml-data-types:CML_OSPF6_PATH_TYPE_T;
                    description "";
                } // END of pathType definition.

                leaf pathCode  {
                    type  cml-data-types:CML_STRING_T;
                    description "";
                } // END of pathCode definition.

                leaf pathDiscardConnection  {
                    type  cml-data-types:CML_STRING_T;
                    description "";
                } // END of pathDiscardConnection definition.

                leaf pathCost  {
                    type  cml-data-types:CML_UINT32_T;
                    description "";
                } // END of pathCost definition.

                leaf pathType2Cost  {
                    type  cml-data-types:CML_UINT32_T;
                    description "";
                } // END of pathType2Cost definition.

                leaf pathFlags  {
                    type  cml-data-types:CML_OSPF6_PATH_FLAGS_T;
                    description "";
                } // END of pathFlags definition.

            } // END of ospf6Path-container definition.
            uses ospf6NextHop;
        } // End of ospf6Route-list
    } // END of Route definition.
    grouping ospf6NextHop {
        description
            "ospf6NextHop";

        list nextHop {
            key "nextHopAddr";
            config false;
            description
                "OSPFv3 next hop details";
            leaf nextHopAddr  {
                type  cml-data-types:CML_STRING_T;
                description "";
            } // END of nextHopAddr definition.

            leaf nextHopInterfaceName  {
                type  cml-data-types:CML_STRING_T;
                description "";
            } // END of nextHopInterfaceName definition.

            leaf nextHopTransitAreaId  {
                type  cml-data-types:CML_STRING_T;
                description "";
            } // END of nextHopTransitAreaId definition.

            leaf nextHopAreaId  {
                type  cml-data-types:CML_STRING_T;
                description "";
            } // END of nextHopAreaId definition.

            leaf isNextHopConnected  {
                type  cml-data-types:CML_BOOL_T;
                description "";
            } // END of isNextHopConnected definition.

            leaf nextHopIsAreaTransit  {
                type  cml-data-types:CML_BOOL_T;
                description "";
            } // END of nextHopIsAreaTransit definition.

            leaf IsnextHopInvalid  {
                type  cml-data-types:CML_BOOL_T;
                description "";
            } // END of IsnextHopInvalid definition.

            leaf nextHopCode  {
                type  cml-data-types:CML_STRING_T;
                description "";
            } // END of nextHopCode definition.

        } // End of nextHop-list
    } // END of ospf6NextHop definition.
    grouping ospf6LsaHeader {
        description
            "ospf6LsaHeader";
        leaf lsaLength  {
            type  cml-data-types:CML_UINT32_T;
            description "";
        } // END of lsaLength definition.

        leaf lsaCheckSum  {
            type  cml-data-types:CML_STRING_T;
            description "";
        } // END of lsaCheckSum definition.

        leaf lsaSeqNum  {
            type  cml-data-types:CML_STRING_T;
            description "";
        } // END of lsaSeqNum definition.

        leaf lsaLinkId  {
            type  cml-data-types:CML_STRING_T;
            description "";
        } // END of lsaLinkId definition.

        leaf lsaType  {
            type  cml-data-types:CML_STRING_T;
            description "";
        } // END of lsaType definition.

        leaf lsaAge  {
            type  cml-data-types:CML_UINT32_T;
            description "";
        } // END of lsaAge definition.

    } // END of ospf6LsaHeader definition.
    grouping helper {
        description
            "helper";
        leaf restartHelperOnlyReload  {
            if-feature feature-list:HAVE_RESTART;
            type  cml-data-types:CML_BOOL_T;
            description "";
        } // END of restartHelperOnlyReload definition.

        leaf restartHelperOnlyGracePeriod  {
            if-feature feature-list:HAVE_RESTART;
            type  cml-data-types:CML_UINT16_T {
                 range "2..1800";
            }
            description "";
        } // END of restartHelperOnlyGracePeriod definition.

        leaf restartHelperOnlyUpgrade  {
            if-feature feature-list:HAVE_RESTART;
            type  cml-data-types:CML_BOOL_T;
            description "";
        } // END of restartHelperOnlyUpgrade definition.

        leaf-list restartHelperRouterId  {
            if-feature feature-list:HAVE_RESTART;
            type  cml-data-types:CML_STRING_T;
            description "Router ID in an IPv4 format";
        } // END of restartHelperRouterId definition.

    } // END of helper definition.
    grouping default-information-originate {
        description
            "defaultCMLSEPinformationCMLSEPoriginate";

        list default-information {
            key "defaultInformationOriginate";
            description
                "Default external route Information";
            leaf defaultInformationOriginate  {
                type  cml-data-types:CML_BOOL_T;
                description "";
            } // END of defaultInformationOriginate definition.

            container default-information-always {
                description
                    "Default external route Information Always";
                leaf alwaysSet  {
                    type  cml-data-types:CML_BOOL_T;
                    description "";
                } // END of alwaysSet definition.

                uses metric-group;
            } // END of default-information-always-container definition.
        } // End of default-information-list
    } // END of default-information-originate definition.
    grouping redistribute {
        description
            "redistribute";

        list ospf6_redist_conf {
            key "ospf6RedistProtocol";
            description
                "Redistribute IPv4 routes ";
            leaf ospf6RedistProtocol  {
                type  cml-data-types:CML_OSPF6_ROUTE_SOURCE_TYPE_T;
                description "";
            } // END of ospf6RedistProtocol definition.

            container redistribute-tag {
                description
                    "Redistribute IPv4 routes tag options";
                leaf ospf6RedistTagVal  {
                    type  cml-data-types:CML_UINT32_T {
                         range "0..4294967295";
                    }
                    default "0";
                    description "";
                } // END of ospf6RedistTagVal definition.

                uses metric-group;
            } // END of redistribute-tag-container definition.
        } // End of ospf6_redist_conf-list

        list ospf6_redist_ospf {
            key "ospf6RedistOspfProtocol";
            description
                "Redistribute IPv4 routes for OSPF option";
            leaf ospf6RedistOspfProtocol  {
                type  cml-data-types:CML_OSPF_AREA_ID_T;
                description "";
            } // END of ospf6RedistOspfProtocol definition.

            container redistribute-tag {
                description
                    "Redistribute IPv4 routes for OSPF tag option";
                leaf ospf6RedistOspfTagVal  {
                    type  cml-data-types:CML_UINT32_T {
                         range "0..4294967295";
                    }
                    default "0";
                    description "";
                } // END of ospf6RedistOspfTagVal definition.

                uses metric-group;
            } // END of redistribute-tag-container definition.
        } // End of ospf6_redist_ospf-list
    } // END of redistribute definition.
    grouping metric-group {
        description
            "metricCMLSEPgroup";
        leaf metric  {
            type  cml-data-types:CML_UINT32_T {
                 range "0..16777214";
            }
            description "";
        } // END of metric definition.

        leaf metricType  {
            type  cml-data-types:CML_OSPF_METRIC_TYPE_T;
            description "";
        } // END of metricType definition.

        leaf routeMap  {
            type  cml-data-types:CML_STRING_T;
            description "";
        } // END of routeMap definition.

    } // END of metric-group definition.

    grouping  ospf6Master-grouping {
    description
        "OSPFv3 master for system wide configurations and variables.";
    container ospf6Master {
        description
            "OSPFv3 master for system wide configurations and variables.";
        leaf displaySingleLine  {
            type  cml-data-types:CML_BOOL_T;
            description "";
        } // END of displaySingleLine definition.

        leaf gracePeriod  {
            if-feature feature-list:HAVE_RESTART;
            type  cml-data-types:CML_UINT16_T {
                 range "2..1800";
            }
            description "Grace period in seconds ";
        } // END of gracePeriod definition.

        leaf restartPlannedOnly  {
            if-feature feature-list:HAVE_RESTART;
            type  cml-data-types:CML_BOOL_T;
            description "";
        } // END of restartPlannedOnly definition.


        list ospf6 {
            key "ospf6ProcessTag";
            description
                "OSPFv3 datastructure is for system-wide configuration and variables.";
            leaf ospf6ProcessTag  {
                type  cml-data-types:CML_STRING_T;
                description "OSPFv3 Process tag";
            } // END of ospf6ProcessTag definition.

            leaf vrfName  {
                if-feature feature-list:HAVE_VRF_OSPF6;
                type  cml-data-types:CML_STRING_T;
                description "";
            } // END of vrfName definition.

            leaf routerId  {
                type  cml-data-types:CML_IPV4_ADDR_T;
                description "";
            } // END of routerId definition.

            leaf config_frr  {
                if-feature feature-list:HAVE_OSPF6_LFA;
                type  cml-data-types:CML_BOOL_T;
                description "";
            } // END of config_frr definition.

            leaf abrType  {
                type  cml-data-types:CML_OSPF6_ABR_TYPE_T;
                default "cisco";
                description "The type of area border router";
            } // END of abrType definition.

            leaf teEnabled  {
                if-feature feature-list:HAVE_OSPF6_TE;
                type  cml-data-types:CML_BOOL_T;
                description "";
            } // END of teEnabled definition.

            leaf restartMethod  {
                if-feature feature-list:HAVE_RESTART;
                type  cml-data-types:CML_BOOL_T;
                description "Graceful restart";
            } // END of restartMethod definition.

            leaf dbSummaryOpt  {
                type  cml-data-types:CML_BOOL_T;
                description "";
            } // END of dbSummaryOpt definition.

            leaf bfdEnabled  {
                if-feature feature-list:HAVE_BFD;
                type  cml-data-types:CML_BOOL_T;
                description "";
            } // END of bfdEnabled definition.

            leaf floodReductionEnabled  {
                if-feature feature-list:HAVE_OSPF6_OD;
                type  cml-data-types:CML_BOOL_T;
                description "";
            } // END of floodReductionEnabled definition.

            leaf defaultMetric  {
                type  cml-data-types:CML_UINT32_T {
                     range "1..16777214";
                }
                default "20";
                description "Default metric";
            } // END of defaultMetric definition.

            leaf minspfDelay  {
                type  cml-data-types:CML_UINT32_T {
                     range "0..2147483647";
                }
                default "500";
                description "";
            } // END of minspfDelay definition.

            leaf maxspfDelay  {
                type  cml-data-types:CML_UINT32_T {
                     range "0..2147483647";
                }
                default "50000";
                description "";
            } // END of maxspfDelay definition.

            leaf minDelay  {
                type  cml-data-types:CML_UINT32_T {
                     range "0..2147483647";
                }
                default "500";
                description "The minimum SPF hold delay time in milliseconds";
            } // END of minDelay definition.

            leaf maxDelay  {
                type  cml-data-types:CML_UINT32_T {
                     range "0..2147483647";
                }
                default "50000";
                description "The maximum SPF hold delay time in milliseconds";
            } // END of maxDelay definition.

            leaf refBandwidth  {
                type  cml-data-types:CML_UINT32_T {
                     range "1..4294967";
                }
                default "100000";
                description "The reference bandwidth in Mbits/sec numeric";
            } // END of refBandwidth definition.

            leaf maxConcurrentDd  {
                type  cml-data-types:CML_UINT16_T {
                     range "1..65535";
                }
                default "5";
                description "The maximum number of database descriptor processes numeric ";
            } // END of maxConcurrentDd definition.

            leaf maxUnusePacket  {
                type  cml-data-types:CML_UINT32_T {
                     range "0..65535";
                }
                default "200";
                description "Maximum number of unused OSPFv3 packets";
            } // END of maxUnusePacket definition.

            leaf maxUnuseLsa  {
                type  cml-data-types:CML_UINT32_T {
                     range "0..65535";
                }
                default "200";
                description " Maximum no LSA packets";
            } // END of maxUnuseLsa definition.

            leaf distanceAll  {
                type  cml-data-types:CML_UINT16_T {
                     range "1..254";
                }
                default "110";
                description "";
            } // END of distanceAll definition.

            leaf shutDown  {
                type  cml-data-types:CML_BOOL_T;
                description "";
            } // END of shutDown definition.

            leaf logAdjChanges  {
                type  cml-data-types:CML_BOOL_T;
                description "";
            } // END of logAdjChanges definition.

            leaf logAdjChangesDetail  {
                type  cml-data-types:CML_BOOL_T;
                description "";
            } // END of logAdjChangesDetail definition.

            leaf ospfv3VersionNumber  {
                type  cml-data-types:CML_UINT32_T;
                config false;
                description "";
            } // END of ospfv3VersionNumber definition.

            leaf ospfv3AreaBdrRtrStatus  {
                type  cml-data-types:CML_BOOL_T;
                config false;
                description "";
            } // END of ospfv3AreaBdrRtrStatus definition.

            leaf ospfv3ASBdrRtrStatus  {
                type  cml-data-types:CML_BOOL_T;
                config false;
                description "";
            } // END of ospfv3ASBdrRtrStatus definition.

            leaf processUpTime  {
                type  cml-data-types:CML_STRING_T;
                config false;
                description "";
            } // END of processUpTime definition.

            leaf ddCountIn  {
                type  cml-data-types:CML_UINT16_T;
                config false;
                description "";
            } // END of ddCountIn definition.

            leaf ddCountOut  {
                type  cml-data-types:CML_UINT16_T;
                config false;
                description "";
            } // END of ddCountOut definition.

            leaf extenalLSACount  {
                type  cml-data-types:CML_UINT32_T;
                config false;
                description "";
            } // END of extenalLSACount definition.

            leaf lsdbChecksum  {
                type  cml-data-types:CML_STRING_T;
                config false;
                description "";
            } // END of lsdbChecksum definition.

            leaf unknownLSACount  {
                type  cml-data-types:CML_UINT32_T;
                config false;
                description "";
            } // END of unknownLSACount definition.

            leaf lSASelfCount  {
                type  cml-data-types:CML_UINT32_T;
                config false;
                description "";
            } // END of lSASelfCount definition.

            leaf lSARxCount  {
                type  cml-data-types:CML_UINT32_T;
                config false;
                description "";
            } // END of lSARxCount definition.

            leaf areaCount  {
                type  cml-data-types:CML_UINT32_T;
                config false;
                description "";
            } // END of areaCount definition.

            leaf isDsteEnabled  {
                type  cml-data-types:CML_BOOL_T;
                config false;
                description "";
            } // END of isDsteEnabled definition.


            list passive {
                key "passiveIfName";
                description
                    "Suppress routing updates";
                leaf passiveIfName  {
                    type  cml-data-types:CML_STRING_T;
                    description "";
                } // END of passiveIfName definition.

            } // End of passive-list

            list frr_pref {
                if-feature feature-list:HAVE_OSPF6_LFA;
                key "frrPrefIndex";
                description
                    "Keeps user preferences, lower index in the array is higher priority";
                leaf frrPrefIndex  {
                    type  cml-data-types:CML_UINT32_T {
                         range "1..4";
                    }
                    description "";
                } // END of frrPrefIndex definition.

                leaf frrPrefVal  {
                    if-feature feature-list:HAVE_OSPF6_LFA;
                    type  cml-data-types:CML_OSPF_FRR_TIE_BREAK_VAL_T;
                    mandatory true;
                    description "";
                } // END of frrPrefVal definition.

            } // End of frr_pref-list

            list Ospf6LinkLsa {
                key "LinkLsaIndex";
                config false;
                description
                    "OSPFv3 Link Lsa Info";
                leaf LinkLsaIndex  {
                    type  cml-data-types:CML_INT32_T;
                    description "";
                } // END of LinkLsaIndex definition.

                leaf NumberOfPrefixes  {
                    type  cml-data-types:CML_UINT32_T;
                    description "";
                } // END of NumberOfPrefixes definition.

                leaf LinkLocalAddress  {
                    type  cml-data-types:CML_IPV6_ADDR_T;
                    description "";
                } // END of LinkLocalAddress definition.

                leaf LinkLsaOptions  {
                    type  cml-data-types:CML_STRING_T;
                    description "";
                } // END of LinkLsaOptions definition.

                leaf Priority  {
                    type  cml-data-types:CML_UINT32_T;
                    description "";
                } // END of Priority definition.

                leaf LinklsaAdvRouter  {
                    type  cml-data-types:CML_STRING_T;
                    description "";
                } // END of LinklsaAdvRouter definition.

                leaf LinkLsaIfName  {
                    type  cml-data-types:CML_STRING_T;
                    description "";
                } // END of LinkLsaIfName definition.


                list Ospf6LinkLsaPrefixes {
                    key "LinkLsaPrefix";
                    config false;
                    description
                        "OSPFv3 Link Lsa Prefixes";
                    leaf LinkLsaPrefixNUbit  {
                        type  cml-data-types:CML_STRING_T;
                        description "";
                    } // END of LinkLsaPrefixNUbit definition.

                    leaf LinkLsaPrefixOptions  {
                        type  cml-data-types:CML_STRING_T;
                        description "";
                    } // END of LinkLsaPrefixOptions definition.

                    leaf LinkLsaPrefix  {
                        type  cml-data-types:CML_STRING_T;
                        description "";
                    } // END of LinkLsaPrefix definition.

                } // End of Ospf6LinkLsaPrefixes-list
                uses ospf6LsaHeader;
            } // End of Ospf6LinkLsa-list

            list Ospf6RouterLsa {
                key "RouterLsaIndex";
                config false;
                description
                    "OSPFv3 Router Lsa Info";
                leaf LsaAreaId  {
                    type  cml-data-types:CML_STRING_T;
                    description "";
                } // END of LsaAreaId definition.

                leaf RouterLsaIndex  {
                    type  cml-data-types:CML_INT32_T;
                    description "";
                } // END of RouterLsaIndex definition.

                leaf LsaOptions  {
                    type  cml-data-types:CML_STRING_T;
                    description "";
                } // END of LsaOptions definition.

                leaf LsaFlag  {
                    type  cml-data-types:CML_STRING_T;
                    description "";
                } // END of LsaFlag definition.

                leaf RouterlsaAdvRouter  {
                    type  cml-data-types:CML_STRING_T;
                    description "";
                } // END of RouterlsaAdvRouter definition.


                list RouterLsaLink {
                    key "LinkIndex";
                    config false;
                    description
                        "OSPFv3 Router Lsa Transit";
                    leaf LinkIndex  {
                        type  cml-data-types:CML_INT32_T;
                        description "";
                    } // END of LinkIndex definition.

                    leaf nbrRouterId  {
                        type  cml-data-types:CML_STRING_T;
                        description "";
                    } // END of nbrRouterId definition.

                    leaf NbrInterfaceId  {
                        type  cml-data-types:CML_UINT32_T;
                        description "";
                    } // END of NbrInterfaceId definition.

                    leaf InterfaceId  {
                        type  cml-data-types:CML_UINT32_T;
                        description "";
                    } // END of InterfaceId definition.

                    leaf LinkMetric  {
                        type  cml-data-types:CML_UINT32_T;
                        description "";
                    } // END of LinkMetric definition.

                    leaf LinkType  {
                        type  cml-data-types:CML_STRING_T;
                        description "";
                    } // END of LinkType definition.

                } // End of RouterLsaLink-list
                uses ospf6LsaHeader;
            } // End of Ospf6RouterLsa-list

            list Ospf6NetworkLsa {
                key "NetworklsaAdvRouter";
                config false;
                description
                    "OSPFv3 Network Lsa Info";
                leaf NetworkLsaOptions  {
                    type  cml-data-types:CML_STRING_T;
                    description "";
                } // END of NetworkLsaOptions definition.

                leaf NetworklsaAdvRouter  {
                    type  cml-data-types:CML_STRING_T;
                    description "";
                } // END of NetworklsaAdvRouter definition.


                list NetworkLsaAttachedRouters {
                    key "AttachedRouter";
                    config false;
                    description
                        "OSPFv3 Lsa Attached Routers";
                    leaf AttachedRouter  {
                        type  cml-data-types:CML_STRING_T;
                        description "";
                    } // END of AttachedRouter definition.

                } // End of NetworkLsaAttachedRouters-list
                uses ospf6LsaHeader;
            } // End of Ospf6NetworkLsa-list

            list Ospf6IntraPrefixLsa {
                key "IntraPrefixLsaIndex";
                config false;
                description
                    "OSPFv3 Intra-Prefix Lsa Info";
                leaf IntraPrefixLsaIndex  {
                    type  cml-data-types:CML_INT32_T;
                    description "";
                } // END of IntraPrefixLsaIndex definition.

                leaf IntraLsaAreaId  {
                    type  cml-data-types:CML_STRING_T;
                    description "";
                } // END of IntraLsaAreaId definition.

                leaf IntraPrefixReferencedAdvRouter  {
                    type  cml-data-types:CML_STRING_T;
                    description "";
                } // END of IntraPrefixReferencedAdvRouter definition.

                leaf IntraPrefixReferencedLinkId  {
                    type  cml-data-types:CML_STRING_T;
                    description "";
                } // END of IntraPrefixReferencedLinkId definition.

                leaf IntraPrefixReferencedLsType  {
                    type  cml-data-types:CML_STRING_T;
                    description "";
                } // END of IntraPrefixReferencedLsType definition.

                leaf NumberOfPrefixes  {
                    type  cml-data-types:CML_UINT32_T;
                    description "";
                } // END of NumberOfPrefixes definition.

                leaf IntraPrefixlsaAdvRouter  {
                    type  cml-data-types:CML_STRING_T;
                    description "";
                } // END of IntraPrefixlsaAdvRouter definition.


                list Ospf6IntraPrefixLsaPrefixes {
                    key "IntraPrefixLsaPrefix";
                    config false;
                    description
                        "OSPFv3 Link Lsa Prefixes";
                    leaf IntraPrefixLsaPrefixNUbit  {
                        type  cml-data-types:CML_STRING_T;
                        description "";
                    } // END of IntraPrefixLsaPrefixNUbit definition.

                    leaf IntraPrefixLsaPrefixMetric  {
                        type  cml-data-types:CML_UINT32_T;
                        description "";
                    } // END of IntraPrefixLsaPrefixMetric definition.

                    leaf IntraPrefixLsaPrefixOptions  {
                        type  cml-data-types:CML_STRING_T;
                        description "";
                    } // END of IntraPrefixLsaPrefixOptions definition.

                    leaf IntraPrefixLsaPrefix  {
                        type  cml-data-types:CML_STRING_T;
                        description "";
                    } // END of IntraPrefixLsaPrefix definition.

                } // End of Ospf6IntraPrefixLsaPrefixes-list
                uses ospf6LsaHeader;
            } // End of Ospf6IntraPrefixLsa-list

            list Ospf6InterPrefixLsa {
                key "InterPrefixLsaIndex";
                config false;
                description
                    "OSPFv3 Inter-Prefix Lsa Info";
                leaf InterPrefixLsaIndex  {
                    type  cml-data-types:CML_INT32_T;
                    description "";
                } // END of InterPrefixLsaIndex definition.

                leaf InterLsaAreaId  {
                    type  cml-data-types:CML_STRING_T;
                    description "";
                } // END of InterLsaAreaId definition.

                leaf InterPrefixNUbit  {
                    type  cml-data-types:CML_STRING_T;
                    description "";
                } // END of InterPrefixNUbit definition.

                leaf InterPrefixLsaPrefixMetric  {
                    type  cml-data-types:CML_UINT32_T;
                    description "";
                } // END of InterPrefixLsaPrefixMetric definition.

                leaf InterPrefixLsaPrefixOptions  {
                    type  cml-data-types:CML_UINT32_T;
                    description "";
                } // END of InterPrefixLsaPrefixOptions definition.

                leaf InterPrefixLsaPrefix  {
                    type  cml-data-types:CML_STRING_T;
                    description "";
                } // END of InterPrefixLsaPrefix definition.

                leaf InterPrefixlsaAdvRouter  {
                    type  cml-data-types:CML_STRING_T;
                    description "";
                } // END of InterPrefixlsaAdvRouter definition.

                uses ospf6LsaHeader;
            } // End of Ospf6InterPrefixLsa-list

            list Ospf6InterRouterLsa {
                key "InterRouterLsaIndex";
                config false;
                description
                    "OSPFv3 Inter-Router Lsa Info";
                leaf InterRouterLsaIndex  {
                    type  cml-data-types:CML_INT32_T;
                    description "";
                } // END of InterRouterLsaIndex definition.

                leaf InterRouterLsaAreaId  {
                    type  cml-data-types:CML_STRING_T;
                    description "";
                } // END of InterRouterLsaAreaId definition.

                leaf InterRouterDestRouter  {
                    type  cml-data-types:CML_STRING_T;
                    description "";
                } // END of InterRouterDestRouter definition.

                leaf InterRouterLsaPrefixMetric  {
                    type  cml-data-types:CML_UINT32_T;
                    description "";
                } // END of InterRouterLsaPrefixMetric definition.

                leaf InterRouterLsaOptions  {
                    type  cml-data-types:CML_STRING_T;
                    description "";
                } // END of InterRouterLsaOptions definition.

                leaf InterRouterlsaAdvRouter  {
                    type  cml-data-types:CML_STRING_T;
                    description "";
                } // END of InterRouterlsaAdvRouter definition.

                uses ospf6LsaHeader;
            } // End of Ospf6InterRouterLsa-list

            list Ospf6ExternalLsa {
                key "ExternalLsaIndex";
                config false;
                description
                    "OSPFv3 External Lsa Info";
                leaf ExternalLsaIndex  {
                    type  cml-data-types:CML_INT32_T;
                    description "";
                } // END of ExternalLsaIndex definition.

                leaf ExternalLsaPrefixNUbit  {
                    type  cml-data-types:CML_STRING_T;
                    description "";
                } // END of ExternalLsaPrefixNUbit definition.

                leaf ExternalReferencedLinkId  {
                    type  cml-data-types:CML_STRING_T;
                    description "";
                } // END of ExternalReferencedLinkId definition.

                leaf ExternalReferencedLsType  {
                    type  cml-data-types:CML_UINT32_T;
                    description "";
                } // END of ExternalReferencedLsType definition.

                leaf ExternalRouteTag  {
                    type  cml-data-types:CML_UINT32_T;
                    description "";
                } // END of ExternalRouteTag definition.

                leaf ExternalForwardingAddress  {
                    type  cml-data-types:CML_STRING_T;
                    description "";
                } // END of ExternalForwardingAddress definition.

                leaf ExternalPrefixOptions  {
                    type  cml-data-types:CML_STRING_T;
                    description "";
                } // END of ExternalPrefixOptions definition.

                leaf ExternalPrefix  {
                    type  cml-data-types:CML_STRING_T;
                    description "";
                } // END of ExternalPrefix definition.

                leaf ExternalLsaMetric  {
                    type  cml-data-types:CML_UINT32_T;
                    description "";
                } // END of ExternalLsaMetric definition.

                leaf ExternalLsaMetricType  {
                    type  cml-data-types:CML_STRING_T;
                    description "";
                } // END of ExternalLsaMetricType definition.

                leaf ExternallsaAdvRouter  {
                    type  cml-data-types:CML_STRING_T;
                    description "";
                } // END of ExternallsaAdvRouter definition.

                uses ospf6LsaHeader;
            } // End of Ospf6ExternalLsa-list

            list Ospf6NssaExternalLsa {
                key "NssaExternalLsaIndex";
                config false;
                description
                    "OSPFv3 Nssa-External Lsa Info";
                leaf NssaExternalLsaIndex  {
                    type  cml-data-types:CML_INT32_T;
                    description "";
                } // END of NssaExternalLsaIndex definition.

                leaf NssaExternalLsaPrefixNUbit  {
                    type  cml-data-types:CML_STRING_T;
                    description "";
                } // END of NssaExternalLsaPrefixNUbit definition.

                leaf NssaExternalReferencedLsType  {
                    type  cml-data-types:CML_STRING_T;
                    description "";
                } // END of NssaExternalReferencedLsType definition.

                leaf NssaExternalReferencedLinkId  {
                    type  cml-data-types:CML_STRING_T;
                    description "";
                } // END of NssaExternalReferencedLinkId definition.

                leaf NssaExternalRouteTag  {
                    type  cml-data-types:CML_UINT32_T;
                    description "";
                } // END of NssaExternalRouteTag definition.

                leaf NssaExternalForwardingAddress  {
                    type  cml-data-types:CML_STRING_T;
                    description "";
                } // END of NssaExternalForwardingAddress definition.

                leaf NssaExternalPrefixOptions  {
                    type  cml-data-types:CML_STRING_T;
                    description "";
                } // END of NssaExternalPrefixOptions definition.

                leaf NssaExternalPrefix  {
                    type  cml-data-types:CML_STRING_T;
                    description "";
                } // END of NssaExternalPrefix definition.

                leaf NssaExternalLsaMetric  {
                    type  cml-data-types:CML_UINT32_T;
                    description "";
                } // END of NssaExternalLsaMetric definition.

                leaf NssaExternalLsaMetricType  {
                    type  cml-data-types:CML_STRING_T;
                    description "";
                } // END of NssaExternalLsaMetricType definition.

                leaf NssaExternallsaAdvRouter  {
                    type  cml-data-types:CML_STRING_T;
                    description "";
                } // END of NssaExternallsaAdvRouter definition.

                uses ospf6LsaHeader;
            } // End of Ospf6NssaExternalLsa-list

            list areaTable {
                key "areaId";
                description
                    "OSPFv3 area structure.";
                leaf areaId  {
                    type  cml-data-types:CML_AREA_T;
                    description "OSPFv3 area ID in an IPv4 address format";
                } // END of areaId definition.

                leaf areaDefaultCost  {
                    type  cml-data-types:CML_UINT32_T {
                         range "0..16777215";
                    }
                    default "1";
                    description "Stub advertised cost";
                } // END of areaDefaultCost definition.

                leaf isAreaBackbone  {
                    type  cml-data-types:CML_BOOL_T;
                    config false;
                    description "";
                } // END of isAreaBackbone definition.

                leaf isAreaActive  {
                    type  cml-data-types:CML_BOOL_T;
                    config false;
                    description "";
                } // END of isAreaActive definition.

                leaf activeIfCount  {
                    type  cml-data-types:CML_UINT32_T;
                    config false;
                    description "";
                } // END of activeIfCount definition.

                leaf areaIfCount  {
                    type  cml-data-types:CML_UINT32_T;
                    config false;
                    description "";
                } // END of areaIfCount definition.

                leaf spfCalcCount  {
                    type  cml-data-types:CML_UINT32_T;
                    config false;
                    description "";
                } // END of spfCalcCount definition.

                leaf lsaCount  {
                    type  cml-data-types:CML_UINT32_T;
                    config false;
                    description "";
                } // END of lsaCount definition.

                leaf lsdbChecksum  {
                    type  cml-data-types:CML_STRING_T;
                    config false;
                    description "";
                } // END of lsdbChecksum definition.

                leaf unknownLSACount  {
                    type  cml-data-types:CML_UINT32_T;
                    config false;
                    description "";
                } // END of unknownLSACount definition.

                leaf isAreaAsbr  {
                    type  cml-data-types:CML_BOOL_T;
                    config false;
                    description "";
                } // END of isAreaAsbr definition.


                list Stub {
                    key "isAreaStub";
                    description
                        "ospf area stub configuration";
                    leaf isAreaStub  {
                        type  cml-data-types:CML_OSPF_STUB_T;
                        description "";
                    } // END of isAreaStub definition.

                    leaf isAreaStubNoSummary  {
                        type  cml-data-types:CML_BOOL_T;
                        description "";
                    } // END of isAreaStubNoSummary definition.

                } // End of Stub-list

                list Nssa {
                    if-feature feature-list:HAVE_NSSA;
                    key "isAreaNssa";
                    description
                        "ospf area stub configuration";
                    leaf isAreaNssa  {
                        type  cml-data-types:CML_OSPF_NSSA_T;
                        description "isAreaNssa";
                    } // END of isAreaNssa definition.

                    leaf nssaStabilityInterval  {
                        type  cml-data-types:CML_INT32_T {
                             range "0..2147483647";
                        }
                        default "40";
                        description "Stability interval in seconds";
                    } // END of nssaStabilityInterval definition.

                    leaf nssaTranslatorRole  {
                        type  cml-data-types:CML_OSPF_TRANSLATOR_ROLE_T;
                        default "candidate";
                        description "NSSA-ABR translator role 1-OSPF_NSSA_TRANSLATE_ALWAYS 2-OSPF_NSSA_TRANSLATE_CANDIDATE";
                    } // END of nssaTranslatorRole definition.

                    leaf nssaDefaultOriginMetric  {
                        type  cml-data-types:CML_INT32_T {
                             range "0..16777214";
                        }
                        default "0";
                        description "";
                    } // END of nssaDefaultOriginMetric definition.

                    leaf nssaDefaultOriginMetricType  {
                        type  cml-data-types:CML_INT32_T {
                             range "1..2";
                        }
                        default "2";
                        description "";
                    } // END of nssaDefaultOriginMetricType definition.

                    leaf isNssaNoDist  {
                        type  cml-data-types:CML_BOOL_T;
                        description "isNssaNoDist";
                    } // END of isNssaNoDist definition.

                    leaf isNssaDefaultOriginate  {
                        type  cml-data-types:CML_BOOL_T;
                        description "";
                    } // END of isNssaDefaultOriginate definition.

                    leaf nssaAreaNoSummary  {
                        type  cml-data-types:CML_BOOL_T;
                        description "";
                    } // END of nssaAreaNoSummary definition.

                    leaf nssarouteMap  {
                        type  cml-data-types:CML_STRING_T;
                        description "";
                    } // END of nssarouteMap definition.

                } // End of Nssa-list

                list ospf6Vertex {
                    key "vertexlinkId";
                    config false;
                    description
                        "Shortest Path Tree/ABR table.";
                    leaf vertexlinkId  {
                        type  cml-data-types:CML_STRING_T;
                        description "";
                    } // END of vertexlinkId definition.

                    leaf vertexDistance  {
                        type  cml-data-types:CML_UINT32_T;
                        description "";
                    } // END of vertexDistance definition.

                    uses ospf6NextHop;
                } // End of ospf6Vertex-list

                list areaRangeIPv6 {
                    key "rangeAddr";
                    description
                        "OSPFv3 Intra-area IPv4 routes";
                    leaf rangeAddr  {
                        type  cml-data-types:CML_IPV6_PREFIX_T;
                        description "IPv6 Area range address";
                    } // END of rangeAddr definition.

                    leaf rangeStatus  {
                        type  cml-data-types:CML_OSPF6_AREA_RANGE_T;
                        description "";
                    } // END of rangeStatus definition.

                } // End of areaRangeIPv6-list

                list areaVirtualLink {
                    key "peerId";
                    description
                        "OSPFv3 Area Virtual-link";
                    leaf peerId  {
                        type  cml-data-types:CML_IPV4_ADDR_T;
                        description "";
                    } // END of peerId definition.

                    leaf helloInterval  {
                        type  cml-data-types:CML_UINT32_T {
                             range "1..65535";
                        }
                        default "10";
                        description "";
                    } // END of helloInterval definition.

                    leaf deadInterval  {
                        type  cml-data-types:CML_UINT32_T {
                             range "1..65535";
                        }
                        default "40";
                        description "";
                    } // END of deadInterval definition.

                    leaf retransmitInterval  {
                        type  cml-data-types:CML_UINT32_T {
                             range "1..1800";
                        }
                        default "5";
                        description "";
                    } // END of retransmitInterval definition.

                    leaf transmitDelay  {
                        type  cml-data-types:CML_UINT32_T {
                             range "1..1800";
                        }
                        default "1";
                        description "";
                    } // END of transmitDelay definition.

                    leaf fallOverBfd  {
                        if-feature feature-list:HAVE_BFD;
                        type  cml-data-types:CML_BOOL_T;
                        description "";
                    } // END of fallOverBfd definition.

                    leaf instanceId  {
                        type  cml-data-types:CML_UINT32_T {
                             range "0..31 | 64..95";
                        }
                        description "";
                    } // END of instanceId definition.

                    leaf vlinkName  {
                        type  cml-data-types:CML_STRING_T;
                        config false;
                        description "";
                    } // END of vlinkName definition.

                    leaf vlinkStatus  {
                        type  cml-data-types:CML_OSPFV3_LINK_STATUS_T;
                        config false;
                        description "";
                    } // END of vlinkStatus definition.

                    leaf vlinkInterfaceName  {
                        type  cml-data-types:CML_STRING_T;
                        config false;
                        description "";
                    } // END of vlinkInterfaceName definition.

                    leaf vlinkInstanceId  {
                        type  cml-data-types:CML_UINT32_T;
                        config false;
                        description "";
                    } // END of vlinkInstanceId definition.

                    leaf vlinkisHelloSupEnabled  {
                        type  cml-data-types:CML_BOOL_T;
                        config false;
                        description "";
                    } // END of vlinkisHelloSupEnabled definition.

                    leaf vlinkIsDNAEnabled  {
                        type  cml-data-types:CML_BOOL_T;
                        config false;
                        description "";
                    } // END of vlinkIsDNAEnabled definition.

                    leaf vlinkLocalAddress  {
                        type  cml-data-types:CML_STRING_T;
                        config false;
                        description "";
                    } // END of vlinkLocalAddress definition.

                    leaf vlinkRemoteAddress  {
                        type  cml-data-types:CML_STRING_T;
                        config false;
                        description "";
                    } // END of vlinkRemoteAddress definition.

                    leaf vlinkState  {
                        type  cml-data-types:CML_STRING_T;
                        config false;
                        description "";
                    } // END of vlinkState definition.

                    leaf vlinkHelloDueTime  {
                        type  cml-data-types:CML_STRING_T;
                        config false;
                        description "";
                    } // END of vlinkHelloDueTime definition.

                    leaf vlinkAdjacencyState  {
                        type  cml-data-types:CML_STRING_T;
                        config false;
                        description "";
                    } // END of vlinkAdjacencyState definition.

                } // End of areaVirtualLink-list
                uses lsdb;
            } // End of areaTable-list

            list addressFamily {
                key "isAddrFamily";
                description
                    " OSPFv3 Address Family.";
                leaf isAddrFamily  {
                    type  cml-data-types:CML_BOOL_T;
                    description "";
                } // END of isAddrFamily definition.


                list areaTable {
                    key "areaId";
                    description
                        "OSPFv3 area structure.";
                    leaf areaId  {
                        type  cml-data-types:CML_AREA_T;
                        description "";
                    } // END of areaId definition.


                    list areaRangeIPv4 {
                        key "rangeAddrIPV4";
                        description
                            "Area Range IPv4 address list";
                        leaf rangeAddrIPV4  {
                            type  cml-data-types:CML_IPV4_ADDR_PREFIX_T;
                            description "";
                        } // END of rangeAddrIPV4 definition.

                        leaf rangeStatusIPv4  {
                            type  cml-data-types:CML_OSPF6_AREA_RANGE_T;
                            description "";
                        } // END of rangeStatusIPv4 definition.

                    } // End of areaRangeIPv4-list
                } // End of areaTable-list

                list summaryAddressIpv4 {
                    key "summaryIpv4Addr";
                    description
                        "OSPFv3 IPv4 Summary Address list";
                    leaf summaryIpv4Addr  {
                        type  cml-data-types:CML_IPV4_PREFIX_T;
                        description "";
                    } // END of summaryIpv4Addr definition.

                    leaf setTag  {
                        type  cml-data-types:CML_UINT32_T {
                             range "0..4294967295";
                        }
                        description "";
                    } // END of setTag definition.

                    leaf not-advertise  {
                        type  cml-data-types:CML_BOOL_T;
                        description "";
                    } // END of not-advertise definition.

                } // End of summaryAddressIpv4-list
                uses redistribute;
                uses default-information-originate;
            } // End of addressFamily-list

            list distributeList {
                if-feature feature-list:HAVE_ACL;
                key "accessListName";
                description
                    "Distribute list for OSPFv3 Protocol";
                leaf accessListName  {
                    type  cml-data-types:CML_STRING_T;
                    description "Access-list name";
                } // END of accessListName definition.

                leaf ospf6DistIn  {
                    type  cml-data-types:CML_BOOL_T;
                    description "ospf6DistIn";
                } // END of ospf6DistIn definition.


                list distributeListProtocol {
                    key "ospf6distProtocol";
                    description
                        "Distribute list for OSPFv3 Protocol";
                    leaf ospf6distProtocol  {
                        type  cml-data-types:CML_OSPF6_ROUTE_SOURCE_TYPE_T;
                        description "proto Redistributed protocol type 1-IPI_ROUTE_KERNEL, 2-IPI_ROUTE_CONNECT, 3-IPI_ROUTE_STATIC, 4-IPI_ROUTE_RIP, 5-IPI_ROUTE_RIPNG, 6-IPI_ROUTE_OSPF, 7-IPI_ROUTE_OSPF6, 8-IPI_ROUTE_BGP, 9-IPI_ROUTE_ISIS";
                    } // END of ospf6distProtocol definition.

                } // End of distributeListProtocol-list

                list distributeListOspf {
                    key "ospf6distOspfProtocol";
                    description
                        "Distribute list for OSPFv3 Protocol";
                    leaf ospf6distOspfProtocol  {
                        type  cml-data-types:CML_OSPF_AREA_ID_T;
                        description "";
                    } // END of ospf6distOspfProtocol definition.

                } // End of distributeListOspf-list
            } // End of distributeList-list

            list summaryAddressIpv6 {
                key "summaryIpv6Addr";
                description
                    "OSPFv3 IPv6 Summary Address";
                leaf summaryIpv6Addr  {
                    type  cml-data-types:CML_IPV6_PREFIX_T;
                    description "summaryIpv6Addr";
                } // END of summaryIpv6Addr definition.

                leaf all-tag  {
                    type  cml-data-types:CML_UINT32_T {
                         range "0..4294967295";
                    }
                    default "0";
                    description "";
                } // END of all-tag definition.

                leaf not-advertise6  {
                    type  cml-data-types:CML_BOOL_T;
                    description "";
                } // END of not-advertise6 definition.

                leaf translate-tag  {
                    type  cml-data-types:CML_UINT32_T {
                         range "0..4294967295";
                    }
                    default "0";
                    description "";
                } // END of translate-tag definition.

            } // End of summaryAddressIpv6-list
            container cspf {
                if-feature feature-list:HAVE_OSPF6_CSPF;
                description
                    "Constrained Shortest Path First (CSPF) Instance";
                leaf cspfEnabled  {
                    if-feature feature-list:HAVE_OSPF6_CSPF;
                    type  cml-data-types:CML_BOOL_T;
                    description "cspfEnabled";
                } // END of cspfEnabled definition.

                leaf cspfTieBreak  {
                    if-feature feature-list:HAVE_OSPF6_CSPF;
                    type  cml-data-types:CML_OSPF6_CSPF_TYPE_T;
                    description "";
                } // END of cspfTieBreak definition.

                leaf cspfDefRetryInterval  {
                    if-feature feature-list:HAVE_OSPF6_CSPF;
                    type  cml-data-types:CML_UINT16_T {
                         range "1..3600";
                    }
                    description "";
                } // END of cspfDefRetryInterval definition.

            } // END of cspf-container definition.
            container distance {
                description
                    "Define an administrative distance";
                leaf distanceIntra  {
                    type  cml-data-types:CML_UINT32_T {
                         range "1..254";
                    }
                    default "110";
                    description "";
                } // END of distanceIntra definition.

                leaf distanceInter  {
                    type  cml-data-types:CML_UINT32_T {
                         range "1..254";
                    }
                    default "110";
                    description "";
                } // END of distanceInter definition.

                leaf distanceExternal  {
                    type  cml-data-types:CML_UINT32_T {
                         range "1..254";
                    }
                    default "110";
                    description "";
                } // END of distanceExternal definition.

            } // END of distance-container definition.
            uses redistribute;
            uses default-information-originate;
            uses lsdb;
            uses Route;
        } // End of ospf6-list

        list ospf6Interface {
            key "ifName";
            description
                "OSPFv3 interface related operations";
            leaf ifName  {
                type  cml-data-types:CML_STRING_T;
                description "";
            } // END of ifName definition.

            leaf ifShutDown  {
                type  cml-data-types:CML_BOOL_T;
                description "Unconfigure OSPFV3 on an interface";
            } // END of ifShutDown definition.


            list ospf6IfinstanceId {
                key "instanceId6";
                description
                    "OSPFv3 instanceId of interface related operations";
                leaf instanceId6  {
                    type  cml-data-types:CML_INT32_T {
                         range "0..31 | 64..95";
                    }
                    description "Interface instance ID <0-255>.";
                } // END of instanceId6 definition.

                leaf networkType  {
                    type  cml-data-types:CML_OSPF6_NETWORK_T;
                    description "The network type.";
                } // END of networkType definition.

                leaf cost  {
                    type  cml-data-types:CML_UINT32_T {
                         range "1..65535";
                    }
                    description "Interface output cost <1-65535>";
                } // END of cost definition.

                leaf teMetric  {
                    if-feature feature-list:HAVE_OSPF6_TE;
                    type  cml-data-types:CML_UINT32_T {
                         range "1..65535";
                    }
                    description "Interface TE metric";
                } // END of teMetric definition.

                leaf ifHelloInterval  {
                    type  cml-data-types:CML_UINT32_T {
                         range "1..65535";
                    }
                    description "Hello interval in seconds <1-65535>";
                } // END of ifHelloInterval definition.

                leaf ifDeadInterval  {
                    type  cml-data-types:CML_UINT32_T {
                         range "1..65535";
                    }
                    default "40";
                    description "Router dead interval in seconds <1-65535>";
                } // END of ifDeadInterval definition.

                leaf ifRetransmitInterval  {
                    type  cml-data-types:CML_UINT32_T {
                         range "1..1800";
                    }
                    default "5";
                    description "Retransmit Interval in seconds <1-65535>";
                } // END of ifRetransmitInterval definition.

                leaf ifPriority  {
                    type  cml-data-types:CML_UINT8_T {
                         range "0..255";
                    }
                    default "1";
                    description "Router priority of the interface <0-255>";
                } // END of ifPriority definition.

                leaf ifTransmitDelay  {
                    type  cml-data-types:CML_UINT32_T {
                         range "1..1800";
                    }
                    default "1";
                    description "Transmit Delay in seconds <1-65535>";
                } // END of ifTransmitDelay definition.

                leaf ifMtuIgnore  {
                    type  cml-data-types:CML_BOOL_T;
                    description "Ignore MTU size check";
                } // END of ifMtuIgnore definition.

                leaf ifDemandCircuit  {
                    if-feature feature-list:HAVE_OSPF6_OD;
                    type  cml-data-types:CML_BOOL_T;
                    description "";
                } // END of ifDemandCircuit definition.

                leaf ifFloodReduction  {
                    if-feature feature-list:HAVE_OSPF6_OD;
                    type  cml-data-types:CML_BOOL_T;
                    description "";
                } // END of ifFloodReduction definition.

                leaf ifFrrDisable  {
                    if-feature feature-list:HAVE_OSPF6_LFA;
                    type  cml-data-types:CML_BOOL_T;
                    description "";
                } // END of ifFrrDisable definition.

                leaf ifAreaId  {
                    type  cml-data-types:CML_AREA_T;
                    description "OSPFv3 area ID in an IPv4 address format";
                } // END of ifAreaId definition.

                leaf ifTagId  {
                    type  cml-data-types:CML_STRING_T;
                    description "OSPFv3 process tag";
                } // END of ifTagId definition.

                leaf ifLinkLsaSuppression  {
                    type  cml-data-types:CML_OSPF6_LSA_SUPRESSION_STATE_T;
                    description " Whether to enable/disable link LSA suppression";
                } // END of ifLinkLsaSuppression definition.

                leaf ifBfdEnable  {
                    if-feature feature-list:HAVE_BFD;
                    type  cml-data-types:CML_OSPF_BFD_STATE;
                    description "";
                } // END of ifBfdEnable definition.

                leaf InterfaceLineProtocolState  {
                    type  cml-data-types:CML_INTERFACE_ADMIN_STATE_T;
                    config false;
                    description "";
                } // END of InterfaceLineProtocolState definition.

                leaf InterfaceIfIndex  {
                    type  cml-data-types:CML_UINT32_T;
                    config false;
                    description "";
                } // END of InterfaceIfIndex definition.

                leaf InterfaceIPV6Address  {
                    type  cml-data-types:CML_STRING_T;
                    config false;
                    description "";
                } // END of InterfaceIPV6Address definition.

                leaf InterfaceIPV6LinkLocalAddress  {
                    type  cml-data-types:CML_STRING_T;
                    config false;
                    description "";
                } // END of InterfaceIPV6LinkLocalAddress definition.

                leaf Ospfv3ProcessId  {
                    type  cml-data-types:CML_STRING_T;
                    config false;
                    description "";
                } // END of Ospfv3ProcessId definition.

                leaf Ospfv3RouterId  {
                    type  cml-data-types:CML_STRING_T;
                    config false;
                    description "";
                } // END of Ospfv3RouterId definition.

                leaf InterfaceState  {
                    type  cml-data-types:CML_OSPF_INTERFACE_STATE_MSG_T;
                    config false;
                    description "";
                } // END of InterfaceState definition.

                leaf DesignatedRouter  {
                    type  cml-data-types:CML_STRING_T;
                    config false;
                    description "";
                } // END of DesignatedRouter definition.

                leaf DRInterfaceAddr  {
                    type  cml-data-types:CML_STRING_T;
                    config false;
                    description "";
                } // END of DRInterfaceAddr definition.

                leaf BackUpDesignatedRouter  {
                    type  cml-data-types:CML_STRING_T;
                    config false;
                    description "";
                } // END of BackUpDesignatedRouter definition.

                leaf BackUpDRInterfaceAddr  {
                    type  cml-data-types:CML_STRING_T;
                    config false;
                    description "";
                } // END of BackUpDRInterfaceAddr definition.

                leaf HelloDueIn  {
                    type  cml-data-types:CML_STRING_T;
                    config false;
                    description "";
                } // END of HelloDueIn definition.

                leaf NeighborCount  {
                    type  cml-data-types:CML_UINT32_T;
                    config false;
                    description "";
                } // END of NeighborCount definition.

                leaf AdjacentNeighborCount  {
                    type  cml-data-types:CML_UINT32_T;
                    config false;
                    description "";
                } // END of AdjacentNeighborCount definition.

                leaf SuppressHelloCount  {
                    if-feature feature-list:HAVE_OSPF6_OD;
                    type  cml-data-types:CML_UINT32_T;
                    config false;
                    description "";
                } // END of SuppressHelloCount definition.

                leaf HelloReceived  {
                    type  cml-data-types:CML_UINT32_T;
                    config false;
                    description "";
                } // END of HelloReceived definition.

                leaf HelloSent  {
                    type  cml-data-types:CML_UINT32_T;
                    config false;
                    description "";
                } // END of HelloSent definition.

                leaf DDReceived  {
                    type  cml-data-types:CML_UINT32_T;
                    config false;
                    description "";
                } // END of DDReceived definition.

                leaf DDSent  {
                    type  cml-data-types:CML_UINT32_T;
                    config false;
                    description "";
                } // END of DDSent definition.

                leaf LSReqReceived  {
                    type  cml-data-types:CML_UINT32_T;
                    config false;
                    description "";
                } // END of LSReqReceived definition.

                leaf LSReqSent  {
                    type  cml-data-types:CML_UINT32_T;
                    config false;
                    description "";
                } // END of LSReqSent definition.

                leaf LSUpdReceived  {
                    type  cml-data-types:CML_UINT32_T;
                    config false;
                    description "";
                } // END of LSUpdReceived definition.

                leaf LSUpdSent  {
                    type  cml-data-types:CML_UINT32_T;
                    config false;
                    description "";
                } // END of LSUpdSent definition.

                leaf LSAckReceived  {
                    type  cml-data-types:CML_UINT32_T;
                    config false;
                    description "";
                } // END of LSAckReceived definition.

                leaf LSAckSent  {
                    type  cml-data-types:CML_UINT32_T;
                    config false;
                    description "";
                } // END of LSAckSent definition.

                leaf LSAckDiscarded  {
                    type  cml-data-types:CML_UINT32_T;
                    config false;
                    description "";
                } // END of LSAckDiscarded definition.


                list nbrStatic {
                    key "nbrStaticAddr";
                    description
                        "Static neighbor data structure.";
                    leaf nbrStaticAddr  {
                        type  cml-data-types:CML_IPV6_ADDR_T;
                        description "Neighbor address in an IPv6 format";
                    } // END of nbrStaticAddr definition.

                    leaf nbrStaticPollInterval  {
                        type  cml-data-types:CML_UINT32_T {
                             range "0..4294967295";
                        }
                        description "Poll interval for neighbor <1-65535>";
                    } // END of nbrStaticPollInterval definition.

                    leaf nbrStaticCost  {
                        type  cml-data-types:CML_UINT32_T {
                             range "1..65535";
                        }
                        description "Cost for neighbor <1-65535>";
                    } // END of nbrStaticCost definition.

                    leaf nbrStaticPriority  {
                        type  cml-data-types:CML_UINT8_T {
                             range "0..255";
                        }
                        description "Priority for neighbor <1-65535>";
                    } // END of nbrStaticPriority definition.

                    leaf nbrInterfaceState  {
                        type  cml-data-types:CML_STRING_T;
                        config false;
                        description "";
                    } // END of nbrInterfaceState definition.

                    leaf nbrInterfaceDesc  {
                        type  cml-data-types:CML_STRING_T;
                        config false;
                        description "";
                    } // END of nbrInterfaceDesc definition.

                } // End of nbrStatic-list

                list ospf6_neighbor {
                    key "nbrRouterId";
                    config false;
                    description
                        "Neighbor Data Structure";
                    leaf nbrRouterId  {
                        type  cml-data-types:CML_STRING_T;
                        description "";
                    } // END of nbrRouterId definition.

                    leaf nbrInterfaceAddress  {
                        type  cml-data-types:CML_STRING_T;
                        description "";
                    } // END of nbrInterfaceAddress definition.

                    leaf nbrAreaId  {
                        type  cml-data-types:CML_STRING_T;
                        description "";
                    } // END of nbrAreaId definition.

                    leaf nbrTimerDump  {
                        type  cml-data-types:CML_STRING_T;
                        description "";
                    } // END of nbrTimerDump definition.

                    leaf nbrState  {
                        type  cml-data-types:CML_STRING_T;
                        description "";
                    } // END of nbrState definition.

                    leaf nbrStateMessage  {
                        type  cml-data-types:CML_STRING_T;
                        description "";
                    } // END of nbrStateMessage definition.

                    leaf nbrStateChange  {
                        type  cml-data-types:CML_UINT32_T;
                        description "";
                    } // END of nbrStateChange definition.

                    leaf nbrPriority  {
                        type  cml-data-types:CML_UINT8_T;
                        description "";
                    } // END of nbrPriority definition.

                    leaf nbrisHelloSuppressed  {
                        type  cml-data-types:CML_BOOL_T;
                        description "";
                    } // END of nbrisHelloSuppressed definition.

                    leaf nbrDRouter  {
                        type  cml-data-types:CML_STRING_T;
                        description "";
                    } // END of nbrDRouter definition.

                    leaf nbrBDRouter  {
                        type  cml-data-types:CML_STRING_T;
                        description "";
                    } // END of nbrBDRouter definition.

                    leaf nbrOptions  {
                        type  cml-data-types:CML_STRING_T;
                        description "";
                    } // END of nbrOptions definition.

                    leaf nbrDeadTimer  {
                        type  cml-data-types:CML_STRING_T;
                        description "";
                    } // END of nbrDeadTimer definition.

                    leaf nbrDbSummaryCount  {
                        type  cml-data-types:CML_UINT32_T;
                        description "";
                    } // END of nbrDbSummaryCount definition.

                    leaf nbrLsRequestCount  {
                        type  cml-data-types:CML_UINT32_T;
                        description "";
                    } // END of nbrLsRequestCount definition.

                    leaf nbrLsRetransmissionCount  {
                        type  cml-data-types:CML_UINT32_T;
                        description "";
                    } // END of nbrLsRetransmissionCount definition.

                    leaf nbrBfdEnabled  {
                        type  cml-data-types:CML_BOOL_T;
                        description "";
                    } // END of nbrBfdEnabled definition.

                    container asbr {
                        config false;
                        description
                            "ASBR routing table.";
                        uses Route;
                    } // END of asbr-container definition.
                    uses Route;
                } // End of ospf6_neighbor-list
                uses lsdb;
            } // End of ospf6IfinstanceId-list
        } // End of ospf6Interface-list
        container ospf6Helper {
            description
                "OSPFv3 Restart module properties";
            uses helper;
        } // END of ospf6Helper-container definition.
        container ospf6HitlessRestartHelper {
            description
                "OSPFv3 Restart module properties";
            uses helper;
        } // END of ospf6HitlessRestartHelper-container definition.
        container ospf6Debug {
            description
                "OSPFv3 Debug Configurations";
            leaf debugIfsm  {
                type  cml-data-types:CML_OSPF6_DEBUG_IFSM_T;
                description "";
            } // END of debugIfsm definition.

            leaf debugNfsm  {
                type  cml-data-types:CML_OSPF6_DEBUG_NFSM_T;
                description "";
            } // END of debugNfsm definition.

            leaf debugLsa  {
                type  cml-data-types:CML_OSPF6_DEBUG_LSA_T;
                description "";
            } // END of debugLsa definition.

            leaf debugNsm  {
                type  cml-data-types:CML_OSPF6_DEBUG_NSM_T;
                description "";
            } // END of debugNsm definition.

            leaf debugRib  {
                if-feature feature-list:HAVE_RIBD;
                type  cml-data-types:CML_OSPF6_DEBUG_RIB_T;
                description "";
            } // END of debugRib definition.

            leaf debugRoute  {
                type  cml-data-types:CML_OSPF6_DEBUG_ROUTE_T;
                description "";
            } // END of debugRoute definition.

            leaf debugRetransmission  {
                type  cml-data-types:CML_BOOL_T;
                description "";
            } // END of debugRetransmission definition.

            leaf debugBfd  {
                if-feature feature-list:HAVE_BFD;
                type  cml-data-types:CML_BOOL_T;
                description "";
            } // END of debugBfd definition.

            leaf debugEvent  {
                type  cml-data-types:CML_OSPF6_DEBUG_EVENT_T;
                description "";
            } // END of debugEvent definition.

            leaf debugPacket  {
                type  cml-data-types:CML_OSPF6_DEBUG_PACKET_TYPE_T;
                description "";
            } // END of debugPacket definition.

            leaf debugLfa  {
                if-feature feature-list:HAVE_OSPF6_LFA;
                type  cml-data-types:CML_BOOL_T;
                description "";
            } // END of debugLfa definition.

            leaf debugAll  {
                type  cml-data-types:CML_BOOL_T;
                description "";
            } // END of debugAll definition.

        } // END of ospf6Debug-container definition.
        container ospf6TermDebug {
            description
                "OSPFv3 Term Debug Configurations";
            leaf TermdebugIfsm  {
                type  cml-data-types:CML_OSPF6_DEBUG_IFSM_T;
                description "";
            } // END of TermdebugIfsm definition.

            leaf TermdebugNfsm  {
                type  cml-data-types:CML_OSPF6_DEBUG_NFSM_T;
                description "";
            } // END of TermdebugNfsm definition.

            leaf TermdebugLsa  {
                type  cml-data-types:CML_OSPF6_DEBUG_LSA_T;
                description "";
            } // END of TermdebugLsa definition.

            leaf TermdebugNsm  {
                type  cml-data-types:CML_OSPF6_DEBUG_NSM_T;
                description "";
            } // END of TermdebugNsm definition.

            leaf TermdebugRib  {
                if-feature feature-list:HAVE_RIBD;
                type  cml-data-types:CML_OSPF6_DEBUG_RIB_T;
                description "";
            } // END of TermdebugRib definition.

            leaf TermdebugRoute  {
                type  cml-data-types:CML_OSPF6_DEBUG_ROUTE_T;
                description "";
            } // END of TermdebugRoute definition.

            leaf TermdebugRetransmission  {
                type  cml-data-types:CML_BOOL_T;
                description "";
            } // END of TermdebugRetransmission definition.

            leaf TermdebugBfd  {
                if-feature feature-list:HAVE_BFD;
                type  cml-data-types:CML_BOOL_T;
                description "";
            } // END of TermdebugBfd definition.

            leaf TermdebugEvent  {
                type  cml-data-types:CML_OSPF6_DEBUG_EVENT_T;
                description "";
            } // END of TermdebugEvent definition.

            leaf TermdebugPacket  {
                type  cml-data-types:CML_OSPF6_DEBUG_PACKET_TYPE_T;
                description "";
            } // END of TermdebugPacket definition.

            leaf TermdebugLfa  {
                if-feature feature-list:HAVE_OSPF6_LFA;
                type  cml-data-types:CML_BOOL_T;
                description "";
            } // END of TermdebugLfa definition.

            leaf TermdebugAll  {
                type  cml-data-types:CML_BOOL_T;
                description "";
            } // END of TermdebugAll definition.

        } // END of ospf6TermDebug-container definition.
    } // END of ospf6Master-container definition.
    } // END of ospf6Master-container definition.


}
