/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-dhcpc.yang
*
*/

submodule ipi-zebos-dhcpc {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "dhcp_client_configuration";


    revision "2018-06-21" {
        description " Initial Version.";
        reference "";
    }


    grouping  dhcpClientInterface-grouping {
    description
        "DHCP interface related operations";
    container dhcpClientInterface {
        description
            "DHCP interface related operations";
        leaf address  {
            type  cml-data-types:CML_BOOL_T;
            description "";
        } // END of address definition.

        leaf nameserver  {
            type  cml-data-types:CML_BOOL_T;
            description "";
        } // END of nameserver definition.

        leaf logserver  {
            type  cml-data-types:CML_BOOL_T;
            description "";
        } // END of logserver definition.

        leaf hostname  {
            type  cml-data-types:CML_BOOL_T;
            description "";
        } // END of hostname definition.

        leaf ntpserver  {
            type  cml-data-types:CML_BOOL_T;
            description "";
        } // END of ntpserver definition.

        leaf ipv6address  {
            type  cml-data-types:CML_BOOL_T;
            description "";
        } // END of ipv6address definition.

        leaf ipv6nameserver  {
            type  cml-data-types:CML_BOOL_T;
            description "";
        } // END of ipv6nameserver definition.

    } // END of dhcpClientInterface-container definition.
    } // END of dhcpClientInterface-container definition.


}
