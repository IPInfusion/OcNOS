/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-linktrack.yang
*
*/

submodule ipi-zebos-linktrack {

    belongs-to  ipi-zebos { prefix ipi-zebos; }

    import cml-data-types {
        prefix cml-data-types;
    }

    include ipi-zebos-interface;
    organization
        "IP Infusion Inc.";

    contact
        "Address: 3965 Freedom Circle, Suite 200, Santa Clara, CA 95054
        Phone: +1 408-400-1900
        E-mail: support@ipinfusion.com
        Web: http://www.ipinfusion.com/";

    description
        "Interface tracking configurations";


    revision "2018-06-21" {
        description " Initial Version.";
        reference "";
    }



    grouping interfaceTrack-grouping {
    description
        "Interface event tracking";
        list interfaceTrack {
            key "eventOspf";
            description
                "Interface event tracking";
            leaf eventOspf  {
                type  cml-data-types:CML_STRING_T;
                description "";
            } // END of eventOspf definition.

            leaf eventOspfMatch  {
                type  cml-data-types:CML_INT_TRACK_MATCH_TYPE_T;
                mandatory true;
                description "";
            } // END of eventOspfMatch definition.

            leaf-list eventNbr  {
                type  cml-data-types:CML_IPV4_ADDR_T;
                description "";
            } // END of eventNbr definition.


            list actionCost {
                key "actionCostIface";
                description
                    "Interface event tracking";
                leaf actionCostIface  {
                    type  cml-data-types:CML_STRING_T;
                    description "";
                } // END of actionCostIface definition.

                leaf actionIfaceCost  {
                    type  cml-data-types:CML_UINT32_T {
                         range "1..65535";
                    }
                    mandatory true;
                    description "";
                } // END of actionIfaceCost definition.

            } // End of actionCost-list
        } // End of interfaceTrack-list
    } // END of interfaceTrack-grouping definition.


}
