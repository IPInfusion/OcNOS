/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-pmirror.yang
*
*/

submodule ipi-zebos-pmirror {

    belongs-to  ipi-zebos { prefix ipi-zebos; }

    import cml-data-types {
        prefix cml-data-types;
    }

    import feature-list {
        prefix feature-list;
    }

    include ipi-zebos-interface;
    organization
        "IP Infusion Inc.";

    contact
        "Address: 3965 Freedom Circle, Suite 200, Santa Clara, CA 95054
        Phone: +1 408-400-1900
        E-mail: support@ipinfusion.com
        Web: http://www.ipinfusion.com/";

    description
        "Datamodel for Port Mirroring";


    revision "2018-06-21" {
        description " Initial Version.";
        reference "";
    }



    grouping pmNode-grouping {
    description
        "Port Mirroring Node";
        list pmNode {
            if-feature feature-list:HAVE_ADVANCE_MIRROR;
            key "pmirrorSessId";
            description
                "Port Mirroring Node";
            leaf pmirrorSessId  {
                type  cml-data-types:CML_PMIRROR_SESS_T;
                description "";
            } // END of pmirrorSessId definition.

            leaf sessType  {
                type  cml-data-types:CML_PMIRROR_SESS_TYPE_T;
                mandatory true;
                description "";
            } // END of sessType definition.

            leaf state  {
                type  cml-data-types:CML_PMIRROR_STATE_T;
                description "";
            } // END of state definition.

            leaf toIfName  {
                type  cml-data-types:CML_STRING_T;
                default "NULL";
                description "";
            } // END of toIfName definition.

            leaf rspanVid  {
                type  cml-data-types:CML_UINT16_T {
                     range "2..4094";
                }
                description "";
            } // END of rspanVid definition.

            leaf description  {
                type  cml-data-types:CML_STRING_T;
                description "";
            } // END of description definition.

            leaf-list srcVlan  {
                type  cml-data-types:CML_RANGE_T;
                description "";
            } // END of srcVlan definition.

            leaf filterCnt  {
                type  cml-data-types:CML_INT32_T;
                config false;
                description "";
            } // END of filterCnt definition.

            leaf txSrcCnt  {
                type  cml-data-types:CML_INT32_T;
                config false;
                description "";
            } // END of txSrcCnt definition.


            list srcList {
                key "fromIfName";
                description
                    "src port node";
                leaf fromIfName  {
                    type  cml-data-types:CML_STRING_T;
                    description "";
                } // END of fromIfName definition.

                leaf dir  {
                    type  cml-data-types:CML_PMIRROR_DIR_T;
                    mandatory true;
                    description "";
                } // END of dir definition.

            } // End of srcList-list
            container filterList {
                description
                    "mirror filter";
                leaf proto  {
                    type  cml-data-types:CML_INT32_T;
                    description "";
                } // END of proto definition.

                leaf cos  {
                    type  cml-data-types:CML_INT8_T {
                         range "0..7";
                    }
                    description "";
                } // END of cos definition.

                leaf vlan  {
                    type  cml-data-types:CML_UINT16_T {
                         range "2..4094";
                    }
                    description "";
                } // END of vlan definition.

                leaf flags  {
                    type  cml-data-types:CML_INT32_T;
                    description "";
                } // END of flags definition.

                leaf sourceMacAddr  {
                    type  cml-data-types:CML_STRING_T;
                    description "";
                } // END of sourceMacAddr definition.

                leaf sourceMacMask  {
                    type  cml-data-types:CML_STRING_T;
                    description "";
                } // END of sourceMacMask definition.

                leaf destinationMacAddr  {
                    type  cml-data-types:CML_STRING_T;
                    description "";
                } // END of destinationMacAddr definition.

                leaf destinationMacMask  {
                    type  cml-data-types:CML_STRING_T;
                    description "";
                } // END of destinationMacMask definition.

                leaf sourceAddr  {
                    type  cml-data-types:CML_STRING_T;
                    description "";
                } // END of sourceAddr definition.

                leaf sourceMask  {
                    type  cml-data-types:CML_STRING_T;
                    description "";
                } // END of sourceMask definition.

                leaf destinationAddr  {
                    type  cml-data-types:CML_STRING_T;
                    description "";
                } // END of destinationAddr definition.

                leaf destinationMask  {
                    type  cml-data-types:CML_STRING_T;
                    description "";
                } // END of destinationMask definition.

                leaf sourceIp6Addr  {
                    type  cml-data-types:CML_IPV6_PREFIX_T;
                    description "";
                } // END of sourceIp6Addr definition.

                leaf destinationIp6Addr  {
                    type  cml-data-types:CML_IPV6_PREFIX_T;
                    description "";
                } // END of destinationIp6Addr definition.

            } // END of filterList-container definition.
        } // End of pmNode-list
    } // END of pmNode-grouping definition.


    grouping pmNodeALternate-grouping {
    description
        "Port Mirroring Node";
        list pmNodeALternate {
            if-feature feature-list:NOT_HAVE_ADVANCE_MIRROR;
            key "ifName";
            description
                "Port Mirroring Node";
            leaf ifName  {
                type  cml-data-types:CML_STRING_T;
                description "";
            } // END of ifName definition.

            leaf fromIfName  {
                type  cml-data-types:CML_STRING_T;
                description "";
            } // END of fromIfName definition.

            leaf direction  {
                type  cml-data-types:CML_PMIRROR_ALT_DIR_T;
                description "";
            } // END of direction definition.

        } // End of pmNodeALternate-list
    } // END of pmNodeALternate-grouping definition.


}
