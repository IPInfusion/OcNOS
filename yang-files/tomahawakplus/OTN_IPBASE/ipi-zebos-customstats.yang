/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-customstats.yang
*
*/

submodule ipi-zebos-customstats {

    belongs-to  ipi-zebos { prefix ipi-zebos; }

    include ipi-zebos-interface;
    organization
        "IP Infusion Inc.";

    contact
        "Address: 3965 Freedom Circle, Suite 200, Santa Clara, CA 95054
        Phone: +1 408-400-1900
        E-mail: support@ipinfusion.com
        Web: http://www.ipinfusion.com/";

    description
        "Custom Stats Managed Object";


    revision "2018-05-06" {
        description " Initial Version.";
        reference "";
    }



}
