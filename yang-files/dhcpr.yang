/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : dhcpr.yang
*
*/

submodule dhcpr {

    belongs-to  ZebOS { prefix ZebOS; }
    include interface;
    include featuredhcp;


    import cml_data_types {
        prefix cml_data_types;
    }

    description
        "dhcp_relay_configuration";


    revision "2016-12-27" {
        description "Added snmp oid.";
    }

    revision "2016-10-28" {
        description "Initial version of dhcpr datamodel.";
    }



    grouping dhcprelayinterface-grouping {
        list dhcprelayinterface {
             
            description
                "DHCP interface related operations";

            config true;
            key "ifName";

            
            leaf ifName  {
                type  cml_data_types:CML_STRING_T {
                    length "0..255";
                }
            } // END of ifName definition.

            leaf-list address  {
                type  cml_data_types:CML_IPV4_ADDR_T;  
            } // END of address definition.

        } // End of dhcprelayinterface-list
    } // END of dhcprelayinterface-grouping definition.


    grouping dhcp6nterface-grouping {
        list dhcp6nterface {
             
            description
                "DHCP interface related operations";

            config true;
            key "ifName";

            
            leaf ifName  {
                type  cml_data_types:CML_STRING_T {
                    length "0..255";
                }
            } // END of ifName definition.


            list dhcprelayaddress6 {
                 
                description
                    "dhcprelayaddress6";

                config true;
                key "ipv6address";

                
                leaf ipv6address  {
                    type  cml_data_types:CML_IPV6_ADDR_T;  
                } // END of ipv6address definition.

                leaf interface  {
                    type  cml_data_types:CML_STRING_T {
                        length "0..255";
                    }
                } // END of interface definition.

            } // End of dhcprelayaddress6-list
        } // End of dhcp6nterface-list
    } // END of dhcp6nterface-grouping definition.

    grouping  dhcprelay-grouping {
    container dhcprelay {
                config true;

        description
            "dhcprelay";

        leaf relay  {
            type  cml_data_types:CML_BOOL_T;  
        } // END of relay definition.

        leaf option  {
            type  cml_data_types:CML_BOOL_T;  
        } // END of option definition.

    } // END of dhcprelay-container definition.
    } // END of dhcprelay-container definition.

    grouping  dhcprelay6-grouping {
    container dhcprelay6 {
                config true;

        description
            "DHCP";

        leaf relay6  {
            type  cml_data_types:CML_BOOL_T;  
        } // END of relay6 definition.

    } // END of dhcprelay6-container definition.
    } // END of dhcprelay6-container definition.


}
