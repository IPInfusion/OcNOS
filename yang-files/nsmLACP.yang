/*
* Copyright (C) 2016 IP Infusion, Inc. 
*  All Rights Reserved.
*
*** Auto generated by zebmdc

* Unless required by applicable law or agreed to in writing,
* software distributed under the License is distributed on an
* "AS IS" BASIS, WITHOUT WARRANTIES OR CONDITIONS OF ANY
* KIND, either express or implied.

* File name : nsmLACP.yang
*
*/

submodule nsmLACP {

    belongs-to  ZebOS { prefix ZebOS; }
    include interface;


    import cml_data_types {
        prefix cml_data_types;
    }

    description
        "Layer-2 lacp  configurations";


    revision "2015-10-20" {
        description "Revisied on 2015-10-20.";    }



    grouping nsmlacpInterface-grouping {
        list nsmlacpInterface {
             

            description
                "NSM LACP interface related operations";

            config true;
            key "ifName";

            
            leaf ifName  {
                mandatory true;                
                type  leafref {
                    path  "/vr/interface/ifName";
                }
            } // END of ifName definition.

            leaf vrId  {
                mandatory false;                
                type  leafref {
                    path  "/vr/vrId";
                }
            } // END of vrId definition.

            leaf channelGroup  {
                mandatory true;                
                type  cml_data_types:CML_UINT16_T {
                     range "1..65535";
                }
                config true;
            } // END of channelGroup definition.

            leaf modeOperation  {
                mandatory true;                
                type  cml_data_types:CML_LACP_MODE_T;  
                config true;
            } // END of modeOperation definition.

        } // End of nsmlacpInterface-list
    } // END of nsmlacpInterface-grouping definition.


    grouping nsmportInterface-grouping {
        list nsmportInterface {
             

            description
                "NSM LACP interface related operations";

            config true;
            key "ifName";

            
            leaf ifName  {
                mandatory true;                
                type  leafref {
                    path  "/vr/interface/ifName";
                }
            } // END of ifName definition.

            leaf psc  {
                mandatory false;                
                type  cml_data_types:CML_LACP_PSC_T;  
                default "src-dst-mac";
                config true;
            } // END of psc definition.

            leaf static-channel-group  {
                mandatory false;                
                type  cml_data_types:CML_UINT16_T {
                     range "1..12";
                }
                config true;
            } // END of static-channel-group definition.

        } // End of nsmportInterface-list
    } // END of nsmportInterface-grouping definition.


}
