/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : snmp.yang
*
*/

submodule snmp {

    belongs-to  ZebOS { prefix ZebOS; }
    include vrf;


    import cml_data_types {
        prefix cml_data_types;
    }

    import feature_list {
        prefix feature_list;
    }

    description
        "Simple Network Management Protocol";


    revision "2017-02-20" {
        description "Added snmp server enable cli.";
    }

    revision "2016-12-27" {
        description "Added snmp oid and documentation tag.";
    }

    revision "2016-10-28" {
        description "Initial version of SNMP datamodel.";
    }


    grouping  snmp-grouping {
    container snmp {
                config true;

        description
            "snmp  related operations";

        leaf vrfName  {
            type  cml_data_types:CML_STRING_T {
                length "0..255";
            }
            default "default";
        } // END of vrfName definition.

        leaf enabled  {
            type  cml_data_types:CML_BOOL_T;  
        } // END of enabled definition.

        leaf tcpsession  {
            if-feature feature_list:HAVE_SNMP_AGENT;
            type  cml_data_types:CML_BOOL_T;  
            description "snmp-server tcp-session";
        } // END of tcpsession definition.

        leaf linkup  {
            type  cml_data_types:CML_BOOL_T;  
        } // END of linkup definition.

        leaf linkdown  {
            type  cml_data_types:CML_BOOL_T;  
        } // END of linkdown definition.

        leaf trapenable  {
            type  cml_data_types:CML_BOOL_T;  
        } // END of trapenable definition.

        leaf pktIn  {
            type  cml_data_types:CML_UINT32_T;  
            config false;
            description "SNMP packets input";
        } // END of pktIn definition.

        leaf pktInBadVer  {
            type  cml_data_types:CML_UINT32_T;  
            config false;
            description "Bad SNMP versions";
        } // END of pktInBadVer definition.

        leaf pktInUnknownCommunity  {
            type  cml_data_types:CML_UINT32_T;  
            config false;
            description "Unknown community name";
        } // END of pktInUnknownCommunity definition.

        leaf pktInIllOperation  {
            type  cml_data_types:CML_UINT32_T;  
            config false;
            description "Illegal operation for community name supplied";
        } // END of pktInIllOperation definition.

        leaf pktInEncodingError  {
            type  cml_data_types:CML_UINT32_T;  
            config false;
            description "Encoding errors";
        } // END of pktInEncodingError definition.

        leaf pktInRequestedVariables  {
            type  cml_data_types:CML_UINT32_T;  
            config false;
            description "Number of requested variables";
        } // END of pktInRequestedVariables definition.

        leaf pktInNumOfSetRequest  {
            type  cml_data_types:CML_UINT32_T;  
            config false;
            description "Number of altered variables";
        } // END of pktInNumOfSetRequest definition.

        leaf pktInNumOfGetPdu  {
            type  cml_data_types:CML_UINT32_T;  
            config false;
            description "Get-request PDUs";
        } // END of pktInNumOfGetPdu definition.

        leaf pktInNumOfGetNextPdu  {
            type  cml_data_types:CML_UINT32_T;  
            config false;
            description "Get-next PDUs";
        } // END of pktInNumOfGetNextPdu definition.

        leaf pktInNumOfSetPdu  {
            type  cml_data_types:CML_UINT32_T;  
            config false;
            description "Set-request PDUs";
        } // END of pktInNumOfSetPdu definition.

        leaf pktOut  {
            type  cml_data_types:CML_UINT32_T;  
            config false;
            description "SNMP packets output";
        } // END of pktOut definition.

        leaf pktOutTooBigError  {
            type  cml_data_types:CML_UINT32_T;  
            config false;
            description "Too big errors";
        } // END of pktOutTooBigError definition.

        leaf pktOutNoSuchNameError  {
            type  cml_data_types:CML_UINT32_T;  
            config false;
            description "No such name errors";
        } // END of pktOutNoSuchNameError definition.

        leaf pktOutBadValueError  {
            type  cml_data_types:CML_UINT32_T;  
            config false;
            description "Bad values errors";
        } // END of pktOutBadValueError definition.

        leaf pktOutGenError  {
            type  cml_data_types:CML_UINT32_T;  
            config false;
            description "General errors";
        } // END of pktOutGenError definition.

        leaf pktOutRespPdu  {
            type  cml_data_types:CML_UINT32_T;  
            config false;
            description "Response PDUs";
        } // END of pktOutRespPdu definition.

        leaf pktOutTrapPdu  {
            type  cml_data_types:CML_UINT32_T;  
            config false;
            description "Trap PDUs";
        } // END of pktOutTrapPdu definition.

        leaf engineID  {
            type  cml_data_types:CML_STRING_T {
                length "0..255";
            }
            config false;
            description "snmp engineId";
        } // END of engineID definition.

        leaf debug  {
            type  cml_data_types:CML_BOOL_T;  
        } // END of debug definition.


        list snmpview {
                         if-feature feature_list:HAVE_SNMP_AGENT;

            description
                "List of SNMP Views configured";

            config true;
            key "view";

            
            leaf vrfName  {
                type  cml_data_types:CML_STRING_T {
                    length "0..255";
                }
                default "default";
            } // END of vrfName definition.

            leaf view  {
                type  cml_data_types:CML_STRING_T {
                    length "0..255";
                }
            } // END of view definition.

            leaf snmpoid  {
                type  cml_data_types:CML_STRING_T {
                    length "0..255";
                }
            } // END of snmpoid definition.

            leaf oidtree  {
                type  cml_data_types:CML_SNMP_OID_TREE_T;  
                description "snmp-server view";
            } // END of oidtree definition.

        } // End of snmpview-list

        list snmpCommunity {
                         if-feature feature_list:HAVE_SNMP_AGENT;

            description
                "List of SNMP communities configured";

            config true;
            key "community";

            
            leaf vrfName  {
                type  cml_data_types:CML_STRING_T {
                    length "0..255";
                }
                default "default";
            } // END of vrfName definition.

            leaf community  {
                type  cml_data_types:CML_STRING_T {
                    length "0..255";
                }
                description "snmp-server community";
            } // END of community definition.

            leaf communityView  {
                type  cml_data_types:CML_STRING_T {
                    length "0..255";
                }
                description "view name";
            } // END of communityView definition.

            leaf communityViewVersion  {
                type  cml_data_types:CML_SNMP_VERSION_T;  
            } // END of communityViewVersion definition.

            leaf communityViewVersionAccess  {
                type  cml_data_types:CML_SNMP_ACCESS_T;  
                description "snmp-server community view";
            } // END of communityViewVersionAccess definition.

            leaf communityGroup  {
                type  cml_data_types:CML_STRING_T {
                    length "0..255";
                }
                description "snmp-server community group";
            } // END of communityGroup definition.

            leaf communityAccess  {
                type  cml_data_types:CML_SNMP_ACCESS_T;  
                description "snmp-server community access-privileges";
            } // END of communityAccess definition.

            leaf communityAcl  {
                type  cml_data_types:CML_STRING_T {
                    length "0..255";
                }
                description "snmp-server community usr-acl";
            } // END of communityAcl definition.

        } // End of snmpCommunity-list

        list snmpuser {
                         if-feature feature_list:HAVE_SNMP_AGENT;
            if-feature feature_list:HAVE_SNMP_V3;

            description
                "List of SNMP users configured";

            config true;
            key "user";

            
            leaf vrfName  {
                type  cml_data_types:CML_STRING_T {
                    length "0..255";
                }
                default "default";
            } // END of vrfName definition.

            leaf user  {
                type  cml_data_types:CML_STRING_T {
                    length "0..255";
                }
            } // END of user definition.

            leaf usertype  {
                type  cml_data_types:CML_SNMP_USER_T;  
            } // END of usertype definition.

            leaf authtype  {
                type  cml_data_types:CML_SNMP_AUTH_T;  
            } // END of authtype definition.

            leaf authpassword  {
                type  cml_data_types:CML_STRING_T {
                    length "0..255";
                }
            } // END of authpassword definition.

            leaf privtype  {
                type  cml_data_types:CML_SNMP_PRIV_T;  
            } // END of privtype definition.

            leaf privpassword  {
                type  cml_data_types:CML_STRING_T {
                    length "0..255";
                }
            } // END of privpassword definition.

        } // End of snmpuser-list

        list snmphost {
                         if-feature feature_list:HAVE_SNMP_AGENT;

            description
                "remote_trap_host_configurations";

            config true;
            key "host";

            
            leaf vrfName  {
                type  cml_data_types:CML_STRING_T {
                    length "0..255";
                }
                default "default";
            } // END of vrfName definition.

            leaf host  {
                type  cml_data_types:CML_HOSTPNAME_T;  
            } // END of host definition.

            leaf hosttraps  {
                type  cml_data_types:CML_SNMP_TYPE_T;  
            } // END of hosttraps definition.

            leaf version  {
                type  cml_data_types:CML_SNMP_VERSION_T;  
            } // END of version definition.

            leaf versionstr  {
                type  cml_data_types:CML_STRING_T {
                    length "0..255";
                }
            } // END of versionstr definition.

            leaf version3  {
                type  cml_data_types:CML_VERSION3_T;  
            } // END of version3 definition.

            leaf version3str  {
                type  cml_data_types:CML_STRING_T {
                    length "0..255";
                }
            } // END of version3str definition.

            leaf hostuser  {
                type  cml_data_types:CML_STRING_T {
                    length "0..255";
                }
            } // END of hostuser definition.

            leaf udp  {
                type  cml_data_types:CML_INT32_T {
                     range "1..65535";
                }
                default "162";
            } // END of udp definition.

        } // End of snmphost-list
    } // END of snmp-container definition.
    } // END of snmp-container definition.


}
