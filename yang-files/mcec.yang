/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : mcec.yang
*
*/

submodule mcec {

    belongs-to  ZebOS { prefix ZebOS; }
    include interface;


    import cml_data_types {
        prefix cml_data_types;
    }

    description
        "Multi Chassis Ethernet Channel (MCEC)";


    revision "2016-07-02" {
        description "Initial draft version for MCEC module.";
    }


    grouping  mcecMaster-grouping {
    container mcecMaster {
                config true;

        description
            "mcecMaster";

        leaf mcecDebug  {
            type  cml_data_types:MCEC_DEBUG_T;  
            description "debug mcec";
        } // END of mcecDebug definition.


        list portal {
             
            description
                "struct mcec_portal";

            config false;
            key "mlagId";

            
            leaf mlagId  {
                type  cml_data_types:CML_UINT16_T;  
            } // END of mlagId definition.

            leaf ifName  {
                type  cml_data_types:CML_STRING_T {
                    length "0..255";
                }
            } // END of ifName definition.

            leaf homeAggKey  {
                type  cml_data_types:CML_UINT16_T;  
            } // END of homeAggKey definition.

            leaf homeAdminAggKey  {
                type  cml_data_types:CML_UINT16_T;  
            } // END of homeAdminAggKey definition.

            leaf homeOperAggKey  {
                type  cml_data_types:CML_UINT16_T;  
            } // END of homeOperAggKey definition.

            leaf homeOperPartnerAggKey  {
                type  cml_data_types:CML_UINT16_T;  
            } // END of homeOperPartnerAggKey definition.

            leaf homePartnerSystem  {
                type  cml_data_types:CML_STRING_T {
                    length "0..255";
                }
            } // END of homePartnerSystem definition.

            leaf homePartnerSystemPriority  {
                type  cml_data_types:CML_UINT16_T;  
            } // END of homePartnerSystemPriority definition.

            leaf homeMemberIfBandwidth  {
                type  cml_data_types:CML_UINT64_T;  
            } // END of homeMemberIfBandwidth definition.

            leaf homePhyPropertiesDigest  {
                type  cml_data_types:CML_STRING_T {
                    length "0..255";
                }
            } // END of homePhyPropertiesDigest definition.

            leaf homeMemIfState  {
                type  cml_data_types:CML_UINT8_T;  
            } // END of homeMemIfState definition.

            leaf homeStpState  {
                type  cml_data_types:CML_UINT8_T;  
            } // END of homeStpState definition.

            leaf homeMlagSync  {
                type  cml_data_types:CML_UINT8_T;  
            } // END of homeMlagSync definition.

            leaf idlToMlagFloodEnabled  {
                type  cml_data_types:CML_UINT8_T;  
            } // END of idlToMlagFloodEnabled definition.

            leaf mlagPortState  {
                type  cml_data_types:CML_UINT8_T;  
            } // END of mlagPortState definition.

            leaf mlagIfState  {
                type  cml_data_types:CML_UINT8_T;  
            } // END of mlagIfState definition.

            leaf isAggMapped  {
                type  cml_data_types:CML_UINT8_T;  
            } // END of isAggMapped definition.

            leaf nttinfopdu  {
                type  cml_data_types:CML_UINT8_T;  
            } // END of nttinfopdu definition.

            leaf mlagInfoUpdate  {
                type  cml_data_types:CML_UINT8_T;  
            } // END of mlagInfoUpdate definition.

            leaf differMlagInfo  {
                type  cml_data_types:CML_UINT8_T;  
            } // END of differMlagInfo definition.

            leaf neighAdminAggKey  {
                type  cml_data_types:CML_UINT16_T;  
            } // END of neighAdminAggKey definition.

            leaf neighOperPartnerAggKey  {
                type  cml_data_types:CML_UINT16_T;  
            } // END of neighOperPartnerAggKey definition.

            leaf neighPartnerSystem  {
                type  cml_data_types:CML_STRING_T {
                    length "0..255";
                }
            } // END of neighPartnerSystem definition.

            leaf neighPartnerSystemPriority  {
                type  cml_data_types:CML_UINT16_T;  
            } // END of neighPartnerSystemPriority definition.

            leaf neighMemberIfBandwidth  {
                type  cml_data_types:CML_UINT64_T;  
            } // END of neighMemberIfBandwidth definition.

            leaf neighPhyPropertiesDigest  {
                type  cml_data_types:CML_STRING_T {
                    length "0..255";
                }
            } // END of neighPhyPropertiesDigest definition.

            leaf neighMemIfState  {
                type  cml_data_types:CML_UINT8_T;  
            } // END of neighMemIfState definition.

            leaf neighStpState  {
                type  cml_data_types:CML_UINT8_T;  
            } // END of neighStpState definition.

            leaf neighMlagSync  {
                type  cml_data_types:CML_UINT8_T;  
            } // END of neighMlagSync definition.

            leaf mlagBandwidth  {
                type  cml_data_types:CML_UINT64_T;  
            } // END of mlagBandwidth definition.

            leaf mcecInfoRcvState  {
                type  cml_data_types:CML_UINT8_T;  
            } // END of mcecInfoRcvState definition.

            leaf mcecInfoPeriodicTxState  {
                type  cml_data_types:CML_UINT8_T;  
            } // END of mcecInfoPeriodicTxState definition.

            leaf infoPeriodicTxTimerExpired  {
                type  cml_data_types:CML_UINT8_T;  
            } // END of infoPeriodicTxTimerExpired definition.

            leaf mcecValidInfoPduRx  {
                type  cml_data_types:CML_UINT32_T;  
            } // END of mcecValidInfoPduRx definition.

            leaf mcecValidInfoPduTx  {
                type  cml_data_types:CML_UINT32_T;  
            } // END of mcecValidInfoPduTx definition.

        } // End of portal-list
        container mcecDomain {
                        config true;

            description
                "mcec domain";

            leaf homeDomainSysNumber  {
                type  cml_data_types:CML_UINT8_T {
                     range "1..2";
                }
                description "domain system number";
            } // END of homeDomainSysNumber definition.

            leaf confNeighDomainSysNumber  {
                type  cml_data_types:CML_UINT8_T;  
                config false;
            } // END of confNeighDomainSysNumber definition.

            leaf domainAddress  {
                type  cml_data_types:CML_STRING_T {
                    length "0..255";
                }
                description "domain-address";
            } // END of domainAddress definition.

            leaf domainPriority  {
                type  cml_data_types:CML_UINT16_T {
                     range "1..65535";
                }
                default "32768";
                description "domain priority";
            } // END of domainPriority definition.

            leaf homeHelloTimeout  {
                type  cml_data_types:CML_MCEC_HELLO_T;  
                default "short";
                description "domain hello timeout";
            } // END of homeHelloTimeout definition.

            leaf domainSync  {
                type  cml_data_types:CML_UINT8_T;  
                config false;
            } // END of domainSync definition.

            leaf domainAdjacency  {
                type  cml_data_types:CML_UINT8_T;  
                config false;
            } // END of domainAdjacency definition.

            leaf domainConfigured  {
                type  cml_data_types:CML_UINT8_T;  
                config false;
            } // END of domainConfigured definition.

            leaf mcecBegin  {
                type  cml_data_types:CML_UINT8_T;  
                config false;
            } // END of mcecBegin definition.

            leaf nsmImiSyncUpDone  {
                type  cml_data_types:CML_UINT8_T;  
                config false;
            } // END of nsmImiSyncUpDone definition.

            leaf portalCount  {
                type  cml_data_types:CML_UINT16_T;  
                config false;
            } // END of portalCount definition.

            leaf mcecInvalidPduRx  {
                type  cml_data_types:CML_UINT32_T;  
                config false;
            } // END of mcecInvalidPduRx definition.

        } // END of mcecDomain-container definition.
        container idp {
                        config true;

            description
                "mcec_idp";

            leaf intraDomainLink  {
                type  cml_data_types:CML_STRING_T {
                    length "0..255";
                }
                description "intra-domain-link";
            } // END of intraDomainLink definition.

            leaf neighDomainAddr  {
                type  cml_data_types:CML_STRING_T {
                    length "0..255";
                }
                config false;
            } // END of neighDomainAddr definition.

            leaf neighDomainPriority  {
                type  cml_data_types:CML_UINT32_T;  
                config false;
            } // END of neighDomainPriority definition.

            leaf neighDomainSysNumber  {
                type  cml_data_types:CML_UINT16_T;  
                config false;
            } // END of neighDomainSysNumber definition.

            leaf neighDomainSync  {
                type  cml_data_types:CML_UINT16_T;  
                config false;
            } // END of neighDomainSync definition.

            leaf neighHelloTimeout  {
                type  cml_data_types:CML_UINT16_T;  
                config false;
            } // END of neighHelloTimeout definition.

            leaf differDomain  {
                type  cml_data_types:CML_UINT16_T;  
                config false;
            } // END of differDomain definition.

            leaf ntthellopdu  {
                type  cml_data_types:CML_UINT16_T;  
                config false;
            } // END of ntthellopdu definition.

            leaf portEnabled  {
                type  cml_data_types:CML_UINT16_T;  
                config false;
            } // END of portEnabled definition.

            leaf stpState  {
                type  cml_data_types:CML_UINT16_T;  
                config false;
            } // END of stpState definition.

            leaf helloPeriodicTxTimerExpired  {
                type  cml_data_types:CML_UINT8_T;  
                config false;
            } // END of helloPeriodicTxTimerExpired definition.

            leaf currentWhileTimerExpired  {
                type  cml_data_types:CML_UINT8_T;  
                config false;
            } // END of currentWhileTimerExpired definition.

            leaf mcecHelloRcvState  {
                type  cml_data_types:CML_UINT8_T;  
                config false;
            } // END of mcecHelloRcvState definition.

            leaf mcecHelloPeriodicTxState  {
                type  cml_data_types:CML_UINT8_T;  
                config false;
            } // END of mcecHelloPeriodicTxState definition.

            leaf mcecValidHelloPduTx  {
                type  cml_data_types:CML_UINT32_T;  
                config false;
            } // END of mcecValidHelloPduTx definition.

            leaf mcecValidInfoPduTx  {
                type  cml_data_types:CML_UINT32_T;  
                config false;
            } // END of mcecValidInfoPduTx definition.

            leaf mcecValidMacSyncPduTx  {
                type  cml_data_types:CML_UINT32_T;  
                config false;
            } // END of mcecValidMacSyncPduTx definition.

            leaf mcecValidHelloPduRx  {
                type  cml_data_types:CML_UINT32_T;  
                config false;
            } // END of mcecValidHelloPduRx definition.

            leaf mcecValidInfoPduRx  {
                type  cml_data_types:CML_UINT32_T;  
                config false;
            } // END of mcecValidInfoPduRx definition.

            leaf mcecValidMacSyncPduRx  {
                type  cml_data_types:CML_UINT32_T;  
                config false;
            } // END of mcecValidMacSyncPduRx definition.

        } // END of idp-container definition.
        container macSync {
                        config false;

            description
                "mac_sync *msyncp : mac synchronization structure";

            leaf numberOfEntry  {
                type  cml_data_types:CML_UINT16_T;  
            } // END of numberOfEntry definition.


            list lmt {
                 
                description
                    "Local MAC Table";

                config false;
                key "lmtMacAddr";

                
                leaf lmtIsAddEntry  {
                    type  cml_data_types:CML_UINT8_T;  
                } // END of lmtIsAddEntry definition.

                leaf lmtIsStaticEntry  {
                    type  cml_data_types:CML_UINT8_T;  
                } // END of lmtIsStaticEntry definition.

                leaf lmtVid  {
                    type  cml_data_types:CML_UINT16_T;  
                } // END of lmtVid definition.

                leaf lmtMacAddr  {
                    type  cml_data_types:CML_STRING_T {
                        length "0..255";
                    }
                } // END of lmtMacAddr definition.

                leaf lmtOifName  {
                    type  cml_data_types:CML_STRING_T {
                        length "0..255";
                    }
                } // END of lmtOifName definition.

            } // End of lmt-list

            list rmt {
                 
                description
                    "Remote MAC Table";

                config false;
                key "rmtMacAddr";

                
                leaf rmtIsAddEntry  {
                    type  cml_data_types:CML_UINT8_T;  
                } // END of rmtIsAddEntry definition.

                leaf rmtIsStaticEntry  {
                    type  cml_data_types:CML_UINT8_T;  
                } // END of rmtIsStaticEntry definition.

                leaf rmtVid  {
                    type  cml_data_types:CML_UINT16_T;  
                } // END of rmtVid definition.

                leaf rmtMacAddr  {
                    type  cml_data_types:CML_STRING_T {
                        length "0..255";
                    }
                } // END of rmtMacAddr definition.

                leaf rmtOifName  {
                    type  cml_data_types:CML_STRING_T {
                        length "0..255";
                    }
                } // END of rmtOifName definition.

            } // End of rmt-list
        } // END of macSync-container definition.
        container mcecStpSync {
                        config false;

            description
                "stp synchronization structure";

            leaf mcecStpSyncFlags  {
                type  cml_data_types:CML_UINT8_T;  
            } // END of mcecStpSyncFlags definition.

            leaf bridgePriority  {
                type  cml_data_types:CML_UINT16_T;  
            } // END of bridgePriority definition.

            leaf pathcostMethod  {
                type  cml_data_types:CML_UINT8_T;  
            } // END of pathcostMethod definition.

            leaf domainDigest  {
                type  cml_data_types:CML_STRING_T {
                    length "0..255";
                }
            } // END of domainDigest definition.

            leaf neighDomainDigest  {
                type  cml_data_types:CML_STRING_T {
                    length "0..255";
                }
            } // END of neighDomainDigest definition.

            leaf stpSyncNumberOfEntries  {
                type  cml_data_types:CML_UINT8_T;  
            } // END of stpSyncNumberOfEntries definition.

            leaf tcnMlagId  {
                type  cml_data_types:CML_UINT16_T;  
            } // END of tcnMlagId definition.


            list mcecStpMlagIfSyncEntry {
                 
                description
                    "mcecStpMlagIfSyncEntry";

                config false;
                key "mlagId";

                
                leaf mlagId  {
                    type  cml_data_types:CML_UINT16_T;  
                } // END of mlagId definition.

                leaf portPriority  {
                    type  cml_data_types:CML_UINT16_T;  
                } // END of portPriority definition.

                leaf pathCost  {
                    type  cml_data_types:CML_UINT32_T;  
                } // END of pathCost definition.

                leaf interfaceDigest  {
                    type  cml_data_types:CML_STRING_T {
                        length "0..255";
                    }
                } // END of interfaceDigest definition.

                leaf neighInterfaceDigest  {
                    type  cml_data_types:CML_STRING_T {
                        length "0..255";
                    }
                } // END of neighInterfaceDigest definition.

            } // End of mcecStpMlagIfSyncEntry-list
        } // END of mcecStpSync-container definition.
    } // END of mcecMaster-container definition.
    } // END of mcecMaster-container definition.


}
