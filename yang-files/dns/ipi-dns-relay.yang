/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-dns-relay.yang
*
*/

module ipi-dns-relay {

    yang-version 1.1;

    namespace   "http://www.ipinfusion.com/yang/ocnos/ipi-dns-relay";

    prefix "ipi-dns-relay";

    import ietf-inet-types {
        prefix inet;
        revision-date 2013-07-15;
    }

    import ipi-interface {
        prefix ipi-interface;
        revision-date 2022-08-24;
    }

    import ipi-network-instance {
        prefix ipi-network-instance;
        revision-date 2022-06-01;
    }

    import ipi-vrf {
        prefix ipi-vrf;
        revision-date 2022-07-13;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module provides support for users to configure DNS Relay through
                CLI";


    revision "2022-06-01" {
        description "Updated the yang file with feature";
        reference " 0.2.0.";
    }

    revision "2021-07-21" {
        description "Initial Version";
        reference " 0.1.0.";
    }

    grouping relay-dns-global-config {
        description
            "DNS relay attributes in configuration mode";
        leaf enable-dns-feature  {
            type  empty;
            description "Use this attribute to enable the DNS relay agent feature.";
        } // END of enable-dns-feature definition.

        leaf enable-dnsv4-relay  {
            type  empty;
            description "Use this attribute to enable the IPv4 DNS relay agent.";
        } // END of enable-dnsv4-relay definition.

        leaf enable-dnsv6-relay  {
            if-feature feature-list:HAVE_IPV6;
            type  empty;
            description "Use this attribute to enable the IPv6 DNS relay agent.";
        } // END of enable-dnsv6-relay definition.

        leaf-list dns-server-v4-addr  {
            type  inet:ipv4-address;
            description "Use this attribute to set the IPv4 address";
        } // END of dns-server-v4-addr definition.

        leaf-list dns-server-v6-addr  {
            if-feature feature-list:HAVE_IPV6;
            type  inet:ipv6-address;
            description "Use this attribute to set the IPv6 address";
        } // END of dns-server-v6-addr definition.

    } // END of relay-dns-global-config definition.
    grouping relay-dns-interface-config {
        description
            "DNS relay attributes in interface mode";
        leaf name  {
            type  leafref {
                path  "/ipi-interface:interfaces/ipi-interface:interface/ipi-interface:name";
            }
            description "DNS relay Interface name";
        } // END of name definition.

        leaf enable-dnsv4-relay  {
            type  empty;
            description "Use this attribute to enable the IPv4 DNS relay agent.";
        } // END of enable-dnsv4-relay definition.

        leaf enable-dnsv6-relay  {
            if-feature feature-list:HAVE_IPV6;
            type  empty;
            description "Use this attribute to enable the IPv6 DNS relay agent.";
        } // END of enable-dnsv6-relay definition.

        leaf dns-relay-uplink  {
            type  empty;
            description "Use this attribute to set the uplink IPv4 DNS relay agent.";
        } // END of dns-relay-uplink definition.

        leaf dns-relay-v6-uplink  {
            if-feature feature-list:HAVE_IPV6;
            type  empty;
            description "Use this attribute to set the uplink IPv6 DNS relay agent.";
        } // END of dns-relay-v6-uplink definition.

    } // END of relay-dns-interface-config definition.
    grouping relay-dns-vrf-config {
        description
            "DNS relay attributes in VRF mode";
        leaf-list dns-server-v4-addr  {
            type  inet:ipv4-address;
            description "Use this attribute to set the IPv4 address";
        } // END of dns-server-v4-addr definition.

        leaf-list dns-server-v6-addr  {
            if-feature feature-list:HAVE_IPV6;
            type  inet:ipv6-address;
            description "Use this attribute to set the IPv4 address";
        } // END of dns-server-v6-addr definition.

    } // END of relay-dns-vrf-config definition.

    grouping  dns-relay-grouping {
    description
        "DNS Relay";
    container dns-relay {
        if-feature feature-list:HAVE_HOSTPD;
        description
            "DNS Relay";
        container config {
            description
                "DNS Global Configuration";
            uses relay-dns-global-config;
        } // END of config-container definition.
        container state {
            config false;
            description
                "DNS dump state";
            uses relay-dns-global-config;
        } // END of state-container definition.
        container interfaces {
            description
                "DNS Relay Interface";

            list interface {
                key "name";
                description
                    "List of interfaces on which Ethernet OAM available";
                leaf name  {
                    type  leafref {
                        path  "../config/name";
                    }
                    description "DNS relay interface name.";
                } // END of name definition.

                container config {
                    description
                        "DNS Interface Configuration";
                    uses relay-dns-interface-config;
                } // END of config-container definition.
                container state {
                    config false;
                    description
                        "DNS dump state";
                    uses relay-dns-interface-config;
                } // END of state-container definition.
            } // End of interface-list
        } // END of interfaces-container definition.
        container vrfs {
            if-feature feature-list:HAVE_VRF;
            description
                "VRF's List on which DNS relay can be configured";

            list vrf {
                key "vrf-name";
                description
                    "VRF for DNS configuration";
                leaf vrf-name  {
                    type  leafref {
                        path  "/ipi-network-instance:network-instances/ipi-network-instance:network-instance/ipi-vrf:vrf/ipi-vrf:config/ipi-vrf:vrf-name";
                    }
                    description "VRF name on which DNS relay is configured";
                } // END of vrf-name definition.

                container config {
                    description
                        "DNS Relay configuration in VRF";
                    uses relay-dns-vrf-config;
                } // END of config-container definition.
                container state {
                    config false;
                    description
                        "DNS dump state";
                    uses relay-dns-vrf-config;
                } // END of state-container definition.
            } // End of vrf-list
        } // END of vrfs-container definition.
    } // END of dns-relay-container definition.
    } // END of dns-relay-grouping definition.

    uses dns-relay-grouping;

}
