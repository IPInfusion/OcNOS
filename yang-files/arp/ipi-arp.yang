/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-arp.yang
*
*/

module ipi-arp {

    yang-version 1.1;

    namespace   "http://www.ipinfusion.com/yang/ocnos/ipi-arp";

    prefix "ipi-arp";

    import ipi-network-instance {
        prefix ipi-network-instance;
        revision-date 2022-06-01;
    }

    import ipi-vrf {
        prefix ipi-vrf;
        revision-date 2022-07-13;
    }

    import cml-data-types {
        prefix cml-data-types;
        revision-date 2022-09-30;
    }

    import ipi-arp-types {
        prefix ipi-arp-types;
        revision-date 2022-06-01;
    }

    import ipi-interface {
        prefix ipi-interface;
        revision-date 2022-08-24;
    }

    import ietf-inet-types {
        prefix inet;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Address Resolution Protocol";


    revision "2022-06-01" {
        description "Updated the yang file with feature";
        reference " 0.5.0.";
    }

    revision "2021-09-27" {
        description "Changed the clear arp ipaddr data type from CML_IPV4_ADDR_PREFIX_T to CML_IPV4_ADDR_T";
        reference " 0.4.0.";
    }

    revision "2021-09-01" {
        description "Changed base interface module's switchport attribute name and the datatype from bool to empty";
        reference " 0.3.0.";
    }

    revision "2020-12-15" {
        description "Change to have data-types in lower case instead of camel case";
        reference " 0.2.0.";
    }

    revision "2020-08-30" {
        description "Initial Version";
        reference " 0.1.0.";
    }

    grouping global-icmp-redirect {
        description
            "Arp global level icmp redirect information";
        container global {
            if-feature feature-list:HAVE_CUSTOM2_NDD;
            description
                "Arp global level icmp redirect information";
            container config {
                if-feature feature-list:HAVE_CUSTOM2_NDD;
                description
                    "Configuration data for icmp redirect global level";
                uses arp-icmp-redirect;
            } // END of config-container definition.
            container state {
                if-feature feature-list:HAVE_CUSTOM2_NDD;
                config false;
                description
                    "Operation state data for icmp redirect global level";
                uses arp-icmp-redirect;
            } // END of state-container definition.
        } // END of global-container definition.
    } // END of global-icmp-redirect definition.
    grouping arp-icmp-redirect {
        description
            "Top level icmp redirect information";
        leaf icmp-redirect  {
            type  empty;
            description "Use this attribute to trap ICMP redirect packets to the CPU";
        } // END of icmp-redirect definition.

    } // END of arp-icmp-redirect definition.
    grouping common-state-arp {
        description
            "ARP state information";
        leaf arp-age  {
            type  string {
                length "1..1965";
                pattern "[^?' =,>|]+";
            }
            description "The number of minutes before the ARP entry was refreshed. If this
                        value reaches the ARP aging period, the entry is removed from the
                        table. Static entries do not age out.  ARP entry IP address in the
                        device.";
        } // END of arp-age definition.

        leaf interface-name  {
            type  string {
                length "1..1965";
                pattern "[^?' =,>|]+";
            }
            description "Logical address to connect the device over network";
        } // END of interface-name definition.

        leaf physical-interface-name  {
            type  string {
                length "1..1965";
                pattern "[^?' =,>|]+";
            }
            description "Logical address to connect the device over network";
        } // END of physical-interface-name definition.

        leaf arp-state  {
            type  ipi-arp-types:ndd_arp_state_t;
            description "INCOMPLETE/FAILED state entries are only cleared if the total number
                        of ARP entries is more than 2048. It might take up to 60 seconds to
                        clear the entries. This is an optimization to improve ND performanc";
        } // END of arp-state definition.

        leaf interface-state  {
            type  ipi-arp-types:ndd_arp_if_type_t;
            description "State (up or down) of the logical address";
        } // END of interface-state definition.

    } // END of common-state-arp definition.
    grouping link-layer-top {
        description
            "ARP mac address information";
        leaf ip-address  {
            type  inet:ipv4-address;
            description "Use this attribute to create a static ARP entry";
        } // END of ip-address definition.

        leaf mac-address  {
            type  cml-data-types:cml_mac_addr_t {
                length "1..1965";
            }
            mandatory true;
            description "Use this attribute to set the MAC (hardware) address of the ARP entry.";
        } // END of mac-address definition.

        leaf respond-to-arp-request  {
            type  empty;
            description "Use this attribute to set  the response to ARP requests for the IP
                        address";
        } // END of respond-to-arp-request definition.

    } // END of link-layer-top definition.
    grouping arp-summary-info {
        description
            "Summary information";
        leaf resolved-arp  {
            type  uint32;
            description "Count of working/known adjacencies";
        } // END of resolved-arp definition.

        leaf incomplete-arp  {
            type  uint32;
            description "Count of yet to be established adjacencies";
        } // END of incomplete-arp definition.

        leaf unknown-arp  {
            type  uint32;
            description "Count of adjacencies not currently in ARP table";
        } // END of unknown-arp definition.

        leaf total-arp  {
            type  uint32;
            description "Total count of all adjacencies";
        } // END of total-arp definition.

    } // END of arp-summary-info definition.
    grouping dynamic-ip-arp {
        description
            "Dyanmic ARP entry information";

        list dynamic-arp {
            key "vrf-name";
            config false;
            description
                "Dyanmic arp information";
            leaf vrf-name  {
                type  string {
                    length "1..1965";
                    pattern "[^?' =,>|]+";
                }
                description "ARP entry associated vrf";
            } // END of vrf-name definition.


            list entry {
                key "ipv4-address";
                config false;
                description
                    "Dynamic ARP entry information";
                leaf ipv4-address  {
                    type  inet:ipv4-address;
                    description "ARP entry IP address in the device.";
                } // END of ipv4-address definition.

                leaf mac-address  {
                    type  cml-data-types:cml_mac_addr_t {
                        length "1..1965";
                    }
                    description "Physical address of the host";
                } // END of mac-address definition.

                uses common-state-arp;
            } // End of entry-list
            container adjacency-summary {
                config false;
                description
                    "ARP adjacency summary information";
                uses arp-summary-info;
            } // END of adjacency-summary-container definition.
        } // End of dynamic-arp-list
    } // END of dynamic-ip-arp definition.
    grouping global-ip-arp {
        description
            "static ARP entry information";

        list entry {
        when " /ipi-arp:arp/ipi-arp:entry/ipi-arp:config/ipi-arp:mac-address ";
        // when " ipi-vrf:vrf/config/vrf-name ";
            key "vrf-name ip-address";
            description
                "static ARP entry information";
            leaf vrf-name  {
                type  leafref {
                    path  "/ipi-network-instance:network-instances/ipi-network-instance:network-instance/ipi-vrf:vrf/ipi-vrf:config/ipi-vrf:vrf-name";
                }
                description "Use this attribute to create a static ARP entry with default and
                            non-default vrf's";
            } // END of vrf-name definition.

            leaf ip-address  {
                type  leafref {
                    path  "../config/ip-address";
                }
                description "Use this attribute to create a static ARP entry";
            } // END of ip-address definition.

            container config {
                when " /ipi-arp:arp/ipi-arp:entry/ipi-arp:config/ipi-arp:mac-address ";
                description
                    "static ARP entry information";
                uses link-layer-top;
            } // END of config-container definition.
            container state {
                config false;
                description
                    "Operational state data";
                uses link-layer-top;
                uses common-state-arp;
            } // END of state-container definition.
        } // End of entry-list
    } // END of global-ip-arp definition.
    grouping arp-debug-config {
        description
            "arpCMLSEPdebugCMLSEPconfig";
        leaf debug-arp-event  {
            type  empty;
            description "Enable/Disable arp event debug";
        } // END of debug-arp-event definition.

    } // END of arp-debug-config definition.
    grouping arp-debug-terminal {
        description
            "arpCMLSEPdebugCMLSEPterminal";
        leaf debug-arp-terminal-event  {
            type  empty;
            description "Enable/Disable arp event debug";
        } // END of debug-arp-terminal-event definition.

    } // END of arp-debug-terminal definition.
    grouping arp-interface-config {
        description
            "Configuration data for arp on each interface";
        leaf enable-proxy-arp  {
            type  empty;
            description "Use this attribute to enable the proxy ARP feature";
        } // END of enable-proxy-arp definition.

        leaf enable-local-proxy-arp  {
            type  empty;
            description "Use this attribute to enable the local proxy ARP feature";
        } // END of enable-local-proxy-arp definition.

        leaf enable-ip-redirects  {
            type  empty;
            description "Use this attribute to enable ICMP redirects in kernel";
        } // END of enable-ip-redirects definition.

        leaf arp-ageing-timeout  {
            type  uint16 {
                 range "60..28800"  {
                    description "60..28800: Supported range 60 - 28800";
                 }
            }
            default "1500";
            description "Use this attribute to set the ARP aging timeout. The bridge aging time
                        affects the ARP entries which are dependent upon the MAC addresses in
                        hardware. If a MAC address ages out, it causes the corresponding ARP
                        entry to refresh.";
        } // END of arp-ageing-timeout definition.

        leaf arp-reachable-time  {
            type  uint16 {
                 range "10..3600"  {
                    description "10..3600: Supported range 10 - 3600";
                 }
            }
            default "60";
            description "Use this attribute to set the ARP reachable time.";
        } // END of arp-reachable-time definition.

    } // END of arp-interface-config definition.
    grouping arp-interface-top {
        description
            "Top level container for arp on each interface";
        container interfaces {
            description
                "Top level container for arp on each interface";

            list interface {
            when " not(/ipi-interface:interfaces/ipi-interface:interface/ipi-interface:config/ipi-interface:enable-switchport) ";
                key "name";
                description
                    "List of interfaces on which arp is enabled/available";
                leaf name  {
                    type  leafref {
                        path  "/ipi-interface:interfaces/ipi-interface:interface/ipi-interface:name";
                    }
                    description "The textual name of the interface. The value of this object should be
                                the name of the interface as assigned by the local device and should
                                be suitable for use in commands entered at the device's `console'.
                                This might be a text name, such as `le0' or a simple port number, such
                                as `1', depending on the interface naming syntax of the device. If
                                several entries in the ifTable together represent a single interface
                                as named by the device, then each will have the same value of name.
                                Note that for an agent which responds to SNMP queries concerning an
                                interface on some other (proxied) device, then the value of name for
                                such an interface is the proxied device's local name for it. If there
                                is no local name, or this object is otherwise not applicable, then
                                this object contains a zero-length string.";
                } // END of name definition.

                container config {
                    description
                        "Configuration data for ndd on each interface";
                    uses arp-interface-config;
                } // END of config-container definition.
                container state {
                    config false;
                    description
                        "Operational state data";
                    uses arp-interface-config;
                } // END of state-container definition.
            } // End of interface-list
        } // END of interfaces-container definition.
    } // END of arp-interface-top definition.
    grouping arp-debug-top {
        description
            "arp debug grouping";
        container debug {
            description
                "arp debug information";
            container config {
                description
                    "Configuration for arp-debug";
                uses arp-debug-config;
            } // END of config-container definition.
            container state {
                config false;
                description
                    "Configuration for arp-ebug";
                uses arp-debug-config;
                uses arp-debug-terminal;
            } // END of state-container definition.
        } // END of debug-container definition.
    } // END of arp-debug-top definition.

    grouping  arp-grouping {
    description
        "arp global level information";
    container arp {
        if-feature feature-list:HAVE_L3;
        if-feature feature-list:HAVE_NDD;
        description
            "arp global level information";
        uses global-ip-arp;
        uses global-icmp-redirect;
        uses arp-debug-top;
        uses arp-interface-top;
        uses dynamic-ip-arp;
    } // END of arp-container definition.
    } // END of arp-grouping definition.

    uses arp-grouping;

    rpc arp-terminal-debug-on {
        if-feature feature-list:HAVE_L3;
        if-feature feature-list:HAVE_NDD;
        description "Enable arp event debug";
    }

    rpc arp-terminal-debug-off {
        if-feature feature-list:HAVE_L3;
        if-feature feature-list:HAVE_NDD;
        description "Disable arp event debug";
    }

    rpc clear-arp-entry {
        if-feature feature-list:HAVE_L3;
        if-feature feature-list:HAVE_NDD;
        description "clear arp ip";
        input  {
            leaf ip-address  {
                type inet:ipv4-address;
                description "Use this RPC to  clear dynamic ARP entries.";
            }
            leaf vrf-name  {
                type string;
                description "Use this RPC to  clear dynamic ARP entries.";
            }
        }
    }

    rpc clear-arp-entry-per-interface {
        if-feature feature-list:HAVE_L3;
        if-feature feature-list:HAVE_NDD;
        description "clear arp interface";
        input  {
            leaf if-name  {
                type string;
                mandatory true;
                description "Use this RPC to  clear dynamic ARP entries.";
            }
            leaf vrf-name  {
                type string;
                description "Use this RPC to  clear dynamic ARP entries.";
            }
        }
    }

}
