/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-isis-types.yang
*
*/

module ipi-isis-types {

    yang-version 1.1;

    namespace   "http://www.ipinfusion.com/yang/ocnos/ipi-isis-types";

    prefix "ipi-isis-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-isis-types";


    revision "2022-06-01" {
        description "Updated the yang file with feature";
        reference " 0.6.0.";
    }

    revision "2022-04-27" {
        description "Get API changes for ISIS-TILFA";
        reference " 0.5.0.";
    }

    revision "2022-02-07" {
        description "Updated Help Strings for OL bit attributes";
        reference " 0.4.0.";
    }

    revision "2021-09-03" {
        description "Update descriptions of attribute";
        reference " 0.3.0.";
    }

    revision "2020-12-15" {
        description "Change to have data-types in lower case instead of camel case";
        reference " 0.2.0.";
    }

    revision "2020-05-06" {
        description "Datamodel restructuring";
        reference " 0.1.0.";
    }



    typedef  isis_systemid_t {
        type string {
            pattern "[0-9a-fA-F]{4}\\.[0-9a-f]{4}\\.[0-9a-f]{4}";
        }
        description "type definition for ISIS_SYSTEMID_T";
    }

    typedef  isis_level_t {
        type enumeration {
            enum level-1 {
                value 1;
                description "Set interval for level 1 only";
            }
            enum level-2 {
                value 2;
                description "Set interval for level 2 only";
            }
            enum level-1-2 {
                value 3;
                description "Set interval for both level 1 and level 2";
            }
        }
        description "type definition for ISIS_LEVEL_T";
    }

    typedef  isis_level2_t {
        type enumeration {
            enum level-1 {
                value 1;
                description "Level-1";
            }
            enum level-2 {
                value 2;
                description "Level-2";
            }
        }
        description "type definition for ISIS_LEVEL2_T";
    }

    typedef  isis_level_proto_t {
        type enumeration {
            enum ipv4 {
                value 0;
                description "IPv4 address family";
            }
            enum ipv6 {
                value 1;
                description "IPv6 address family";
            }
        }
        description "type definition for ISIS_LEVEL_PROTO_T";
    }

    typedef  isis_cspf_debug_t {
        type bits {
            bit events {
                position 0;
                description "None";
            }
            bit hexdump {
                position 1;
                description "None";
            }
        }
        description "type definition for ISIS_CSPF_DEBUG_T";
    }

    typedef  isis_lfa_level_proto_t {
        type enumeration {
            enum ipv4 {
                value 1;
                description "IPv4 address family";
            }
        }
        description "type definition for ISIS_LFA_LEVEL_PROTO_T";
    }

    typedef  isis_lfa_nexthop_type_t {
        type enumeration {
            enum lfa {
                value 1;
                description "LFA Next-hop";
            }
            enum remote-lfa {
                value 2;
                description "Remote-LFA Next-hop";
            }
        }
        description "type definition for ISIS_LFA_NEXTHOP_TYPE_T";
    }

    typedef  isis_frr_enum_t {
        type enumeration {
            enum all {
                value 1;
                description "On all prefixes";
            }
        }
        description "type definition for ISIS_FRR_ENUM_T";
    }

    typedef  isis_tilfa_protection_type_t {
        type enumeration {
            enum link-protection {
                value 1;
                description "Link Protection";
            }
            enum node-protection {
                value 2;
                description "Node Protection";
            }
            enum protection-error {
                value 3;
                description "Protection Error";
            }
        }
        description "type definition for ISIS_TILFA_PROTECTION_TYPE_T";
    }

    typedef  isis_path_type_t {
        type enumeration {
            enum L1 {
                value 1;
                description "Level-1";
            }
            enum L2 {
                value 2;
                description "Level-2";
            }
        }
        description "type definition for ISIS_PATH_TYPE_T";
    }

    typedef  isis_frr_tie_break_val_t {
        type enumeration {
            enum primary-path {
                value 1;
                description "Primary Path";
            }
            enum node-protecting {
                value 2;
                description "broadcast-interface-disjoint";
            }
            enum interface-disjoint {
                value 3;
                description "Link Protecting";
            }
            enum broadcast-interface-disjoint {
                value 4;
                description "Broadcast Link Protecting";
            }
            enum downstream-path {
                value 5;
                description "Downstream path";
            }
            enum secondary-path {
                value 6;
                description "Secondary path";
            }
        }
        description "type definition for ISIS_FRR_TIE_BREAK_VAL_T";
    }

    typedef  isis_iflevel_t {
        type enumeration {
            enum level-1 {
                value 1;
                description "Act as a station router only";
            }
            enum level-2 {
                value 2;
                description "Act as an area router only";
            }
            enum p2p {
                value 3;
                description "P2p index";
            }
        }
        description "type definition for ISIS_IFLEVEL_T";
    }

    typedef  isis_nbr_adj_t {
        type enumeration {
            enum Suppress {
                value 1;
                description "show Adjacency Suppress";
            }
            enum Advertise {
                value 2;
                description "show Adjacency Advertisement";
            }
        }
        description "type definition for ISIS_NBR_ADJ_T";
    }

    typedef  isis_origin_type_t {
        type enumeration {
            enum originate {
                value 4;
                description "Distribute a default route";
            }
            enum originate-level-1 {
                value 5;
                description "Distribute a default route,Distribute in level-1";
            }
            enum originate-always {
                value 32;
                description "Distribute a default route,Always advertise default route";
            }
        }
        description "type definition for ISIS_ORIGIN_TYPE_T";
    }

    typedef  isis_network_t {
        type enumeration {
            enum broadcast {
                value 1;
                description "Specify IS-IS broadcast multi-access network";
            }
            enum point-to-point {
                value 2;
                description "Specify IS-IS point-to-point network";
            }
        }
        description "type definition for ISIS_NETWORK_T";
    }

    typedef  isis_dynamic_hostanme_t {
        type enumeration {
            enum dynamic-hostname {
                value 0;
                description "Enable dynamic hostname";
            }
            enum area-tag {
                value 1;
                description "Use area-tag as hostname";
            }
        }
        description "type definition for ISIS_DYNAMIC_HOSTANME_T";
    }

    typedef  isis_overload_state_t {
        type enumeration {
            enum off {
                value 0;
                description "Indicates IS-IS instance has left overload state";
            }
            enum on {
                value 1;
                description "Indicates IS-IS instance has entered overload state";
            }
        }
        description "type definition for ISIS_OVERLOAD_STATE_T";
    }

    typedef  isis_state_t {
        type enumeration {
            enum Down {
                value 0;
                description "LAN Neighbor Down";
            }
            enum Init {
                value 1;
                description "LAN Neighbor Init";
            }
            enum Up {
                value 2;
                description "LAN Neighbor Up";
            }
        }
        description "type definition for ISIS_STATE_T";
    }

    typedef  isis_metric_style_t {
        type enumeration {
            enum narrow {
                value 1;
                description "Use old style of TLVs with narrow metric";
            }
            enum wide {
                value 2;
                description "Use new style of TLVs to carry wider metric";
            }
            enum transition {
                value 3;
                description "Send and accept both styles of TLVs during transition";
            }
            enum narrow-transition {
                value 4;
                description "Use old style of TLVs with narrow metric,Send and accept both styles of TLVs during transition";
            }
            enum wide-transition {
                value 5;
                description "Use old style of TLVs with wide metric, Send and accept both styles of TLVs during transition";
            }
        }
        description "type definition for ISIS_METRIC_STYLE_T";
    }

    typedef  isis_multi_topology_level_type_t {
        type enumeration {
            enum level-1 {
                value 1;
                description "IS-IS level-1";
            }
            enum level-2 {
                value 2;
                description "IS-IS level-2";
            }
            enum level-1-2 {
                value 3;
                description "IS-IS level-1 and level-2";
            }
            enum level-1-transition {
                value 4;
                description "Use Level-1 transition";
            }
            enum level-1-2-transition {
                value 5;
                description "Use Level-1-2 transition";
            }
            enum level-2-transition {
                value 6;
                description "Use Level-2 transition";
            }
        }
        description "type definition for ISIS_MULTI_TOPOLOGY_LEVEL_TYPE_T";
    }

    typedef  isis_auth_mode_t {
        type enumeration {
            enum md5 {
                value 1;
                description "Keyed message digest";
            }
            enum text {
                value 2;
                description "Text mode";
            }
        }
        description "type definition for ISIS_AUTH_MODE_T";
    }

    typedef  isis_is_type_t {
        type enumeration {
            enum level-1 {
                value 1;
                description "Act as a station router only";
            }
            enum level-2-only {
                value 2;
                description "Act as an area router only";
            }
            enum level-1-2 {
                value 3;
                description "Act as both a station router and an area router";
            }
        }
        description "type definition for ISIS_IS_TYPE_T";
    }

    typedef  isis_is_type3_t {
        type enumeration {
            enum level-1 {
                value 1;
                description "Redistribute routes into level-1 only";
            }
            enum level-2 {
                value 2;
                description "Redistribute routes into level-2 only";
            }
            enum level-1-2 {
                value 3;
                description "Redistribute routes into both level-1 and level-2";
            }
        }
        description "type definition for ISIS_IS_TYPE3_T";
    }

    typedef  isis_route_t {
        type enumeration {
            enum redistribution {
                value 0;
                description "Clear ISIS IP local redistribution routes";
            }
            enum all {
                value 1;
                description "all of the IS-IS routing table";
            }
        }
        description "type definition for ISIS_ROUTE_T";
    }

    typedef  isis_snp_t {
        type enumeration {
            enum send-only {
                value 1;
                description "Keyed message digest";
            }
            enum validate {
                value 2;
                description "Text mode";
            }
        }
        description "type definition for ISIS_SNP_T";
    }

    typedef  isis_redistribute_t {
        type enumeration {
            enum kernel {
                value 1;
                description "Kernel routes";
            }
            enum connected {
                value 2;
                description "Connected";
            }
            enum static {
                value 3;
                description "Static routes";
            }
            enum rip {
                value 4;
                description "Routing Information Protocol(RIP)";
            }
            enum ospf {
                value 5;
                description "Open Shortest Path First (OSPF)";
            }
            enum bgp {
                value 6;
                description "Border Gateway Protocol (BGP)";
            }
        }
        description "type definition for ISIS_REDISTRIBUTE_T";
    }

    typedef  isis_debug_t {
        type bits {
            bit ifsm {
                position 0;
                description "IS-IS Interface Finite State Machine";
            }
            bit nfsm {
                position 1;
                description "IS-IS Neighbor Finite State Machine";
            }
            bit pdu {
                position 2;
                description "IS-IS Protocol Data Unit";
            }
            bit lsp {
                position 3;
                description "IS-IS Link State PDU";
            }
            bit spf {
                position 4;
                description "IS-IS SPF Calculation";
            }
            bit events {
                position 5;
                description "IS-IS Events";
            }
            bit nsm {
                position 6;
                description "IS-IS NSM information";
            }
            bit checksum {
                position 7;
                description "IS-IS Check-Sum";
            }
            bit authentication {
                position 8;
                description "IS-IS Authentication";
            }
            bit local-updates {
                position 9;
                description "IS-IS Local Updates";
            }
            bit protocol-errors {
                position 10;
                description "IS-IS Protocol Errors";
            }
            bit bfd {
                position 12;
                if-feature feature-list:HAVE_BFD;
                description "Bidirectional Forwarding Detection (BFD)";
            }
            bit mpls {
                position 13;
                if-feature feature-list:HAVE_MPLS;
                description "Multi-Protocol Label Switching (MPLS)";
            }
            bit rib {
                position 14;
                if-feature feature-list:HAVE_RIBD;
                description "IS-IS RIB information";
            }
            bit sr {
                position 15;
                if-feature feature-list:HAVE_SR_MPLS;
                description "Segment Routing";
            }
            bit lfa {
                position 16;
                if-feature feature-list:HAVE_ISIS_LFA;
                description "Loop Free Alternate";
            }
            bit dist-ls {
                position 17;
                if-feature feature-list:HAVE_BGP_LS;
                description "ISIS-LS message";
            }
            bit tilfa {
                position 19;
                if-feature feature-list:HAVE_ISIS_TI_LFA;
                description "Topology Independent Loop Free Alternate";
            }
        }
        description "type definition for ISIS_DEBUG_T";
    }

    typedef  isis_metric_t {
        type enumeration {
            enum internal {
                value 0;
                description "Set IS-IS Internal metric type";
            }
            enum external {
                value 1;
                description "Set IS-IS External metric type";
            }
        }
        description "type definition for ISIS_METRIC_T";
    }

    typedef  isis_summary_level_t {
        type enumeration {
            enum level-1 {
                value 1;
                description "Summarize into level-1 area";
            }
            enum level-2 {
                value 2;
                description "Summarize into level-2 sub-domain";
            }
            enum level-1-2 {
                value 3;
                description "Summarize into both area and sub-domain";
            }
        }
        description "type definition for ISIS_SUMMARY_LEVEL_T";
    }

    typedef  isis_level3_t {
        type enumeration {
            enum level-1 {
                value 1;
                description "Level-1 only";
            }
            enum level-2 {
                value 2;
                description "Level-2 only";
            }
            enum level-1-2 {
                value 3;
                description "Level-1-2";
            }
        }
        description "type definition for ISIS_LEVEL3_T";
    }

    typedef  isis_level_igp_sync_t {
        type enumeration {
            enum level-1 {
                value 1;
                description "Enable LDP ISIS synchronization for level-1 only";
            }
            enum level-2 {
                value 2;
                description "Enable LDP ISIS synchronization for level-2 only";
            }
            enum level-1-2 {
                value 3;
                description "Enable LDP ISIS synchronization for level-1 and level-2";
            }
        }
        description "type definition for ISIS_LEVEL_IGP_SYNC_T";
    }

    typedef  isis_circuit_type_t {
        type enumeration {
            enum level-1 {
                value 1;
                description "Level-1 only adjacencies are formed";
            }
            enum level-2-only {
                value 2;
                description "Level-2 only adjacencies are formed";
            }
            enum level-1-2 {
                value 3;
                description "Level-1-2 adjacencies are formed";
            }
        }
        description "type definition for ISIS_CIRCUIT_TYPE_T";
    }

    typedef  isis_suppress_t {
        type enumeration {
            enum default {
                value 0;
                description "Only for set-overload bit value";
            }
            enum external {
                value 1;
                description "If overload-bit set do not advertise IP prefixes learned from other protocols";
            }
            enum interlevel {
                value 2;
                description "If overload-bit set do not advertise IP prefixes learned from another ISIS level";
            }
            enum external-interlevel {
                value 3;
                description "If overload-bit set donot advertise IP prefixes learned from other protocols,If overload-bit set do not advertise IP prefixes learned from another ISIS level";
            }
            enum interlevel-external {
                value 4;
                description "If overload-bit set donot advertise IP prefixes learned from another ISIS level,If overload-bit set donot advertise IP prefixes learned from other protocols";
            }
        }
        description "type definition for ISIS_SUPPRESS_T";
    }

    typedef  isis_waitforbgp_t {
        type enumeration {
            enum default {
                value 0;
                description "Only for set-overload bit value";
            }
            enum wait-for-bgp {
                value 1;
                description "Let BGP decide when to unset the overload bit";
            }
        }
        description "type definition for ISIS_WAITFORBGP_T";
    }

    typedef  isis_onstartup_t {
        type union {
            type isis_waitforbgp_t {

            }
            type uint32 {
                range "5..86400";

            }
        }
        description "type definition for ISIS_ONSTARTUP_T";
    }

    typedef  isis_mesh_blocked_t {
        type enumeration {
            enum blocked {
                value 0;
                description "Block LSPs on this interface";
            }
        }
        description "type definition for ISIS_MESH_BLOCKED_T";
    }

    typedef  isis_mesh_type_t {
        type union {
            type isis_mesh_blocked_t {

            }
            type uint32 {
                range "1..4294967295";

            }
        }
        description "type definition for ISIS_MESH_TYPE_T";
    }

    typedef  isis_bgp_ls_t {
        type enumeration {
            enum bgpls {
                value 0;
                description "Link State distribution to BGP";
            }
        }
        description "type definition for ISIS_BGP_LS_T";
    }

    typedef  isis_bgp_ls_type_t {
        type union {
            type isis_bgp_ls_t {

            }
            type uint32 {
                range "5..20";

            }
        }
        description "type definition for ISIS_BGP_LS_TYPE_T";
    }

    typedef  isis_address_ipv6_t {
        type enumeration {
            enum ipv6 {
                value 1;
                description "Address family";
            }
        }
        description "type definition for ISIS_ADDRESS_IPV6_T";
    }

    typedef  isis_auth_level_type_t {
        type enumeration {
            enum level-1-only {
                value 1;
                description "Act as a station router only";
            }
            enum level-2-only {
                value 2;
                description "Act as an area router only";
            }
            enum level-1-2 {
                value 3;
                description "Act as both a station router and an area router";
            }
        }
        description "type definition for ISIS_AUTH_LEVEL_TYPE_T";
    }

    typedef  isis_ieee_float32_t {
        type string;
        description "type definition for ISIS_IEEE_FLOAT32_T";
    }

    typedef  isis_spf_t {
        type enumeration {
            enum spf {
                value 0;
                description "spf";
            }
            enum strict-spf {
                value 1;
                description "strict spf";
            }
        }
        description "type definition for ISIS_SPF_T";
    }

    typedef  isis_cspf_path_type_t {
        type enumeration {
            enum strict {
                value 0;
                description "Strict";
            }
            enum loose {
                value 1;
                description "Loose";
            }
        }
        description "type definition for ISIS_CSPF_PATH_TYPE_T";
    }

    typedef  isis_cspf_lsp_type_t {
        type enumeration {
            enum primary {
                value 0;
                description "Primary LSP";
            }
            enum backup {
                value 1;
                description "Backup LSP";
            }
            enum bypass {
                value 2;
                description "Bypass LSP";
            }
        }
        description "type definition for ISIS_CSPF_LSP_TYPE_T";
    }

    typedef  isis_cspf_constraint_type_t {
        type enumeration {
            enum exclude-node {
                value 0;
                description "Exclude Node";
            }
            enum exclude-link {
                value 1;
                description "Exclude Link";
            }
            enum exclude-any {
                value 2;
                description "Exclude Any";
            }
        }
        description "type definition for ISIS_CSPF_CONSTRAINT_TYPE_T";
    }

    typedef  isis_igp_shortcut_lsp_status_t {
        type enumeration {
            enum active {
                value 0;
                description "Active";
            }
            enum inactive {
                value 1;
                description "Inactive";
            }
        }
        description "type definition for ISIS_IGP_SHORTCUT_LSP_STATUS_T";
    }

    typedef  isis_srms_type_t {
        type enumeration {
            enum INACTIVE {
                value 0;
                description "Inactive";
            }
            enum ACTIVE {
                value 1;
                description "Active";
            }
        }
        description "type definition for ISIS_SRMS_TYPE_T";
    }

    typedef  isis_neighbour_protocol_t {
        type enumeration {
            enum IS-IS {
                value 0;
                description "IS-IS";
            }
            enum M-ISIS {
                value 1;
                description "M-ISIS";
            }
        }
        description "type definition for ISIS_NEIGHBOUR_PROTOCOL_T";
    }

    typedef  isis_multi_topology_types_t {
        type bits {
            bit IPv4 {
                position 1;
                description "IPv4";
            }
            bit IPv6 {
                position 2;
                description "IPv6";
            }
        }
        description "Multi Topology Types";
    }

}
