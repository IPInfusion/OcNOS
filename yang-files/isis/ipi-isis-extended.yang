/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-isis-extended.yang
*
*/

submodule ipi-isis-extended {

    yang-version 1.1;

    belongs-to  ipi-isis { prefix ipi-isis; }

    import feature-list {
        prefix feature-list;
        revision-date 2023-02-21;
    }

    import ipi-isis-types {
        prefix ipi-isis-types;
        revision-date 2022-06-01;
    }

    import cml-data-types {
        prefix cml-data-types;
        revision-date 2022-09-30;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Model for managing IS-IS Extended Parameters";


    revision "2022-06-13" {
        description "Update attribute name of ISIS-TILFA";
        reference " 0.5.1.";
    }

    revision "2022-06-01" {
        description "Updated the yang file with feature";
        reference " 0.5.0.";
    }

    revision "2022-04-27" {
        description "Get Api changes for ISIS-TILFA";
        reference " 0.4.0.";
    }

    revision "2021-09-03" {
        description "Update descriptions of attribute";
        reference " 0.3.0.";
    }

    revision "2020-12-15" {
        description "Change to have data-types in lower case instead of camel case";
        reference " 0.2.0.";
    }

    revision "2020-05-06" {
        description "Datamodel restructuring";
        reference " 0.1.0.";
    }



    grouping ipv4-lfa-route-grouping {
    description
        "This objectlist defines the ISIS LFA Route";
        list ipv4-lfa-route {
            if-feature feature-list:HAVE_ISISD;
            key "destination-prefix";
            config false;
            description
                "This objectlist defines the ISIS LFA Route";
            leaf destination-prefix  {
                type  leafref {
                    path  "../state/destination-prefix";
                }
                description "Destination Prefix for the LFA route";
            } // END of destination-prefix definition.


            list route-nexthop {
                key "primary-nexthop nexthop-type";
                config false;
                description
                    "This objectlist defines the ISIS LFA Route Next Hop, LFA node can be a
                                direct neighbor node or in case of Remote-LFA it can be a remote node,
                                In case a direct neighbor nexthop-type is lfa and in case of remote
                                node it'll be remote-lfa";
                leaf primary-nexthop  {
                    type  leafref {
                        path  "../state/primary-nexthop";
                    }
                    description "Primary Nexthop address of LFA route";
                } // END of primary-nexthop definition.

                leaf nexthop-type  {
                    type  leafref {
                        path  "../state/nexthop-type";
                    }
                    description "Nexthop type of LFA route";
                } // END of nexthop-type definition.

                container state {
                    config false;
                    description
                        "This container defines the ISIS LFA Route Next Hop State";
                    uses isis-lfa-route-nh-state;
                } // END of state-container definition.
            } // End of route-nexthop-list
            container state {
                config false;
                description
                    "This container defines the ISIS LFA Route State";
                uses isis-lfa-route-state;
            } // END of state-container definition.
        } // End of ipv4-lfa-route-list
    } // END of ipv4-lfa-route-grouping definition.


    grouping ipv6-lfa-route-grouping {
    description
        "This objectlist defines the ISIS IPv6 LFA Route";
        list ipv6-lfa-route {
            if-feature feature-list:HAVE_ISISD;
            key "destination-prefix";
            config false;
            description
                "This objectlist defines the ISIS IPv6 LFA Route";
            leaf destination-prefix  {
                type  leafref {
                    path  "../state/destination-prefix";
                }
                description "Destination Prefix of LFA route";
            } // END of destination-prefix definition.


            list route-nexthop {
                key "primary-nexthop";
                config false;
                description
                    "This objectlist defines the ISIS IPv6 LFA Route Next Hop";
                leaf primary-nexthop  {
                    type  leafref {
                        path  "../state/primary-nexthop";
                    }
                    description "Primary Nexthop address of LFA route";
                } // END of primary-nexthop definition.

                container state {
                    config false;
                    description
                        "This container defines the ISIS IPv6 LFA Route Next Hop State";
                    uses isis-ipv6-lfa-route-nh-state;
                } // END of state-container definition.
            } // End of route-nexthop-list
            container state {
                config false;
                description
                    "This container defines the ISIS IPv6 LFA Route State";
                uses isis-ipv6-lfa-route-state;
            } // END of state-container definition.
        } // End of ipv6-lfa-route-list
    } // END of ipv6-lfa-route-grouping definition.


    grouping fast-reroute-grouping {
    description
        "This objectlist defines the Fast Reroute";
        list fast-reroute {
            if-feature feature-list:HAVE_ISISD;
            key "level-type";
            description
                "This objectlist defines the Fast Reroute";
            leaf level-type  {
                type  leafref {
                    path  "../config/level-type";
                }
                description "IS-IS instance level,(1|2)";
            } // END of level-type definition.


            list route-map {
                if-feature feature-list:HAVE_ISIS_LFA;
                key "protocol";
                description
                    "This objectlist defines the Fast Reroute list";
                leaf protocol  {
                    type  leafref {
                        path  "../config/protocol";
                    }
                    description "Protocol Address Family";
                } // END of protocol definition.

                container config {
                    description
                        "This container defines the ISIS FRR Routemap Configurations";
                    uses isis-frr-routemap-config;
                } // END of config-container definition.
                container state {
                    config false;
                    description
                        "This container defines the ISIS FRR Routemap state information";
                    uses isis-frr-routemap-config;
                } // END of state-container definition.
            } // End of route-map-list

            list ti-lfa {
                if-feature feature-list:HAVE_ISIS_TI_LFA;
                key "protocol";
                description
                    "Topology Independent LFA protocol information";
                leaf protocol  {
                    type  leafref {
                        path  "../config/protocol";
                    }
                    description "Protocol Address Family";
                } // END of protocol definition.

                container config {
                    description
                        "This container defines the ISIS TI-LFA Configurations";
                    uses isis-ti-lfa-config;
                } // END of config-container definition.
                container state {
                    config false;
                    description
                        "This container defines the ISIS TI-LFA State information";
                    uses isis-ti-lfa-config;
                } // END of state-container definition.
            } // End of ti-lfa-list

            list protocol {
                if-feature feature-list:HAVE_ISIS_LFA;
                key "lfa-protocol preference-value";
                description
                    "This objectlist defines the Fast Protocol List";
                leaf lfa-protocol  {
                    type  leafref {
                        path  "../config/lfa-protocol";
                    }
                    description "LFA Protocol (ipv4 | ipv6)";
                } // END of lfa-protocol definition.

                leaf preference-value  {
                    type  leafref {
                        path  "../config/preference-value";
                    }
                    description "Indicates which tie-break option to use.";
                } // END of preference-value definition.

                container config {
                    description
                        "This container defines the ISIS FRR Routemap Configurations";
                    uses isis-frr-proto-config;
                } // END of config-container definition.
                container state {
                    config false;
                    description
                        "This container defines the ISIS FRR Routemap state information";
                    uses isis-frr-proto-config;
                } // END of state-container definition.
            } // End of protocol-list
            container config {
                description
                    "This container defines the ISIS FRR level type Configurations";
                uses isis-frr-level-type-config;
                uses isis-remote-lfa-config;
            } // END of config-container definition.
            container state {
                config false;
                description
                    "This container defines the ISIS FRR level type State information";
                uses isis-frr-level-type-config;
                uses isis-remote-lfa-config;
            } // END of state-container definition.
            container ipv4-tilfa-routes {
                description
                    "This container defines the ISIS TI-LFA routes";

                list ipv4-tilfa-route {
                    key "destination-prefix";
                    config false;
                    description
                        "This ObjectList defines the ISIS TI-LFA route information";
                    leaf destination-prefix  {
                        type  leafref {
                            path  "../state/destination-prefix";
                        }
                        description "Destination Prefix for the TI-LFA route";
                    } // END of destination-prefix definition.

                    container state {
                        config false;
                        description
                            "This container defines the ISIS TI-LFA Route State";
                        uses ipv4-tilfa-route-state;
                    } // END of state-container definition.
                    container nexthops {
                        config false;
                        description
                            "This container defines the ISIS TI-LFA route Next Hops information";

                        list nexthop {
                            key "primary-nexthop";
                            config false;
                            description
                                "This ObjectList defines the ISIS TI-LFA Route Next Hop information";
                            leaf primary-nexthop  {
                                type  leafref {
                                    path  "../state/primary-nexthop";
                                }
                                description "Primary Nexthop address of TI-LFA route";
                            } // END of primary-nexthop definition.

                            container state {
                                config false;
                                description
                                    "This container defines the ISIS TI-LFA Route Next Hop State";
                                uses ipv4-tilfa-route-nexthop-state;
                            } // END of state-container definition.
                        } // End of nexthop-list
                    } // END of nexthops-container definition.
                    container pq-trunks {
                        config false;
                        description
                            "This container defines the ISIS TI-LFA route PQ Trunk Information";

                        list pq-trunk {
                            key "trunk-id";
                            config false;
                            description
                                "This ObjectList defines the ISIS TI-LFA Route PQ Trunk Information";
                            leaf trunk-id  {
                                type  leafref {
                                    path  "../state/trunk-id";
                                }
                                description "PQ Trunk Id of TI-LFA Route";
                            } // END of trunk-id definition.

                            container state {
                                config false;
                                description
                                    "This container defines the ISIS TI-LFA Route PQ Trunk state";
                                uses tilfa-pq-trunk-state;
                            } // END of state-container definition.
                        } // End of pq-trunk-list
                    } // END of pq-trunks-container definition.
                } // End of ipv4-tilfa-route-list
            } // END of ipv4-tilfa-routes-container definition.
            container tilfa-pq-nodes {
                description
                    "This container defines ISIS TI-LFA pq nodes";
                container circuit-levels {
                    description
                        "This container defines ISIS TI-LFA circuit levels";

                    list circuit-level {
                        key "level";
                        config false;
                        description
                            "This ObjectList defines the ISIS TI-LFA circuit level";
                        leaf level  {
                            type  leafref {
                                path  "../state/level";
                            }
                            description "ISIS level of TI-LFA PQ Nodes";
                        } // END of level definition.

                        container state {
                            config false;
                            description
                                "This container defines ISIS TI-LFA circuit level state";
                            uses tilfa-pq-state;
                        } // END of state-container definition.
                        container vertices {
                            config false;
                            description
                                "This container defines ISIS TILFA PQ Node vertices";

                            list vertex {
                                key "destination-vertex";
                                config false;
                                description
                                    "This ObjectList defines ISIS TILFA PQ Node vertex";
                                leaf destination-vertex  {
                                    type  leafref {
                                        path  "../state/destination-vertex";
                                    }
                                    description "ISIS destination vertex of TI-LFA PQ Nodes";
                                } // END of destination-vertex definition.

                                container state {
                                    config false;
                                    description
                                        "This container defines ISIS TILFA PQ Node vertex state";
                                    uses tilfa-pq-vertex-state;
                                } // END of state-container definition.
                                container interfaces {
                                    config false;
                                    description
                                        "This container defines ISIS TILFA PQ Node interfaces";

                                    list interface {
                                        key "name";
                                        config false;
                                        description
                                            "This ObjectList defines ISIS TI-LFA PQ node interface";
                                        leaf name  {
                                            type  leafref {
                                                path  "../state/name";
                                            }
                                            description "";
                                        } // END of name definition.

                                        container state {
                                            config false;
                                            description
                                                "This container defines ISIS TILFA PQ Node interface state";
                                            uses tilfa-pq-interface-state;
                                        } // END of state-container definition.
                                        container link-protection {
                                            config false;
                                            description
                                                "This container defines ISIS TI-LFA Link protecting PQ Nodes";
                                            container state {
                                                config false;
                                                description
                                                    "This container defines ISIS TI-LFA Link protecting PQ Node state";
                                                uses tilfa-pq-link-protection-state;
                                            } // END of state-container definition.
                                        } // END of link-protection-container definition.
                                        container node-protection {
                                            config false;
                                            description
                                                "This container defines ISIS TI-LFA Node  protecting PQ Nodes";
                                            container state {
                                                config false;
                                                description
                                                    "This container defines ISIS TI-LFA Node protecting PQ Node state";
                                                uses tilfa-pq-node-protection-state;
                                            } // END of state-container definition.
                                        } // END of node-protection-container definition.
                                    } // End of interface-list
                                } // END of interfaces-container definition.
                            } // End of vertex-list
                        } // END of vertices-container definition.
                    } // End of circuit-level-list
                } // END of circuit-levels-container definition.
            } // END of tilfa-pq-nodes-container definition.
        } // End of fast-reroute-list
    } // END of fast-reroute-grouping definition.
    grouping isis-lfa-route-state {
        description
            "State items for ISIS LFA Route";
        leaf destination-prefix  {
            type  inet:ipv4-prefix;
            description "Destination Prefix of LFA route";
        } // END of destination-prefix definition.

        leaf destination-path-type  {
            type  string {
                length "1..1965";
                pattern "[^?' =,>|]+";
            }
            description "Destination Path Type of LFA route";
        } // END of destination-path-type definition.

    } // END of isis-lfa-route-state definition.
    grouping isis-lfa-route-nh-state {
        description
            "State items for ISIS LFA Route Next Hop";
        leaf primary-nexthop  {
            type  inet:ipv4-address;
            description "Primary Nexthop address of LFA route";
        } // END of primary-nexthop definition.

        leaf nexthop-type  {
            type  ipi-isis-types:isis_lfa_nexthop_type_t;
            description "Nexthop type of LFA route";
        } // END of nexthop-type definition.

        leaf primary-nexthop-interface-name  {
            type  string {
                length "1..1965";
                pattern "[^?' =,>|]+";
            }
            description "Primary Nexthop Interface Name of LFA route";
        } // END of primary-nexthop-interface-name definition.

        leaf remote-router-id  {
            type  inet:ipv4-address;
            description "Router-ID of Remote LFA node";
        } // END of remote-router-id definition.

        leaf lfa-nexthop  {
            type  inet:ipv4-address;
            description "LFA Nexthop Prefix of LFA route";
        } // END of lfa-nexthop definition.

        leaf lfa-nexthop-interface-name  {
            type  string {
                length "1..1965";
                pattern "[^?' =,>|]+";
            }
            description "LFA Nexthop Interface Name of LFA route";
        } // END of lfa-nexthop-interface-name definition.

        leaf lfa-path-metric  {
            type  uint32;
            description "LFA Path Metric of LFA route";
        } // END of lfa-path-metric definition.

        leaf protection-provided  {
            type  cml-data-types:cml_line_t {
                length "1..1965";
            }
            description "Protection Provided for LFA route";
        } // END of protection-provided definition.

    } // END of isis-lfa-route-nh-state definition.
    grouping isis-ipv6-lfa-route-state {
        description
            "State items for ISIS IPv6 LFA Route";
        leaf destination-prefix  {
            type  inet:ipv6-prefix;
            description "Destination Prefix of LFA route";
        } // END of destination-prefix definition.

        leaf destination-path-type  {
            type  string {
                length "1..1965";
                pattern "[^?' =,>|]+";
            }
            description "Destination Path Type of LFA route";
        } // END of destination-path-type definition.

    } // END of isis-ipv6-lfa-route-state definition.
    grouping isis-ipv6-lfa-route-nh-state {
        description
            "State items for ISIS IPv6 LFA Route Next Hop";
        leaf primary-nexthop  {
            type  inet:ipv6-address;
            description "Primary Nexthop address of LFA route";
        } // END of primary-nexthop definition.

        leaf primary-nexthop-interface-name  {
            type  string {
                length "1..1965";
                pattern "[^?' =,>|]+";
            }
            description "Primary Nexthop Interface Name of LFA route";
        } // END of primary-nexthop-interface-name definition.

        leaf lfa-nexthop  {
            type  inet:ipv6-address;
            description "Nexthop Prefix of LFA route";
        } // END of lfa-nexthop definition.

        leaf lfa-nexthop-interface-name  {
            type  string {
                length "1..1965";
                pattern "[^?' =,>|]+";
            }
            description "Nexthop Interface Name of LFA route";
        } // END of lfa-nexthop-interface-name definition.

        leaf lfa-path-metric  {
            type  uint32;
            description "Path Metric of LFA route";
        } // END of lfa-path-metric definition.

        leaf protection-provided  {
            type  string {
                length "1..1965";
                pattern "[^?' =,>|]+";
            }
            description "Protection Provided for LFA route";
        } // END of protection-provided definition.

    } // END of isis-ipv6-lfa-route-nh-state definition.
    grouping isis-ti-lfa-config {
        description
            "Config items for ISIS TI-LFA";
        leaf protocol  {
            type  ipi-isis-types:isis_lfa_level_proto_t;
            description "Protocol Address Family";
        } // END of protocol definition.

    } // END of isis-ti-lfa-config definition.
    grouping isis-remote-lfa-config {
        description
            "Config items for ISIS TI-LFA";
        leaf-list remote-lfa-protocol  {
            if-feature feature-list:HAVE_LDPD;
            if-feature feature-list:HAVE_ISIS_LFA;
            type  ipi-isis-types:isis_lfa_level_proto_t;
            description "Protocol Address Family";
        } // END of remote-lfa-protocol definition.

    } // END of isis-remote-lfa-config definition.
    grouping isis-frr-level-type-config {
        description
            "Configuration items for ISIS FRR Routemap";
        leaf level-type  {
            type  ipi-isis-types:isis_level2_t;
            description "IS-IS instance level,(1|2)";
        } // END of level-type definition.

    } // END of isis-frr-level-type-config definition.
    grouping isis-frr-routemap-config {
        description
            "Configuration items for ISIS FRR Routemap";
        leaf protocol  {
            type  ipi-isis-types:isis_lfa_level_proto_t;
            description "Protocol Address Family";
        } // END of protocol definition.

        leaf name  {
            when " not(/isis/isis-instance/fast-reroute/route-map/config/enable-all-prefixes) ";
            type  string {
                length "1..1965";
                pattern "[^?' =,>|]+";
            }
            description "Specific prefixex allowed using this route map";
        } // END of name definition.

        leaf enable-all-prefixes  {
            when " not(/isis/isis-instance/fast-reroute/route-map/config/name) ";
            type  ipi-isis-types:isis_frr_enum_t;
            description "Apply on all prefixes";
        } // END of enable-all-prefixes definition.

    } // END of isis-frr-routemap-config definition.
    grouping isis-frr-proto-config {
        description
            "Configuration items for ISIS FRR Protocol";
        leaf lfa-protocol  {
            type  ipi-isis-types:isis_lfa_level_proto_t;
            description "Protocol Address Family";
        } // END of lfa-protocol definition.

        leaf preference-value  {
            type  ipi-isis-types:isis_frr_tie_break_val_t;
            description "Indicates which tie-break option to use.";
        } // END of preference-value definition.

        leaf preference-index  {
            type  uint32 {
                 range "1..255"  {
                    description "1..255: Supported range 1 - 255";
                 }
            }
            mandatory true;
            description "this index indicates which tie-break option to be given preference";
        } // END of preference-index definition.

    } // END of isis-frr-proto-config definition.
    grouping isis-gr-config {
        description
            "Configuration items for ISIS  GR Configurations";
        leaf grace-period  {
            type  uint16 {
                 range "1..65535"  {
                    description "1..65535: Supported range 1 - 65535";
                 }
            }
            description "The period within which ISIS should come up";
        } // END of grace-period definition.

        leaf enable-helper-only  {
            type  empty;
            description "Attribute to configure helper mode";
        } // END of enable-helper-only definition.

        leaf suppress-adjacency  {
            type  empty;
            description "When set to true, adjacency is not advertised. The SA bit is used by a
                        starting router to  request that its neighbor suppress advertisement
                        of the adjacency  to the starting router in the neighbor's LSPs.";
        } // END of suppress-adjacency definition.

    } // END of isis-gr-config definition.
    grouping ipv4-tilfa-route-state {
        description
            "State items for ISIS TI-LFA Route";
        leaf destination-prefix  {
            type  inet:ipv4-address;
            description "Destination Prefix of TI-LFA route";
        } // END of destination-prefix definition.

        leaf path-type  {
            type  ipi-isis-types:isis_path_type_t;
            description "Destination Path Type of TI-LFA route";
        } // END of path-type definition.

    } // END of ipv4-tilfa-route-state definition.
    grouping ipv4-tilfa-route-nexthop-state {
        description
            "State items for ISIS TI-LFA Route Next Hop";
        leaf primary-nexthop  {
            type  inet:ipv4-address;
            description "Primary Nexthop address of TI-LFA route";
        } // END of primary-nexthop definition.

        leaf protection-type  {
            type  ipi-isis-types:isis_tilfa_protection_type_t;
            description "Nexthop protection type of TI-LFA route";
        } // END of protection-type definition.

        leaf backup-nexthop  {
            type  inet:ipv4-address;
            description "Backup Nexthop of TI-LFA route";
        } // END of backup-nexthop definition.

        leaf pq-node-router-id  {
            type  inet:ipv4-address;
            description "PQ Router-ID of TI-LFA route";
        } // END of pq-node-router-id definition.

        leaf pq-trunk-id  {
            type  uint32;
            description "PQ Trunk-id of TI-LFA route";
        } // END of pq-trunk-id definition.

        leaf primary-outgoing-label  {
            type  uint32;
            description "Primary Out-going Label of TI-LFA route";
        } // END of primary-outgoing-label definition.

        leaf primary-incoming-label  {
            type  uint32;
            description "Primary In-coming Label of TI-LFA route";
        } // END of primary-incoming-label definition.

        leaf backup-outgoing-label  {
            type  uint32;
            description "Backup Out-coming Label of TI-LFA route";
        } // END of backup-outgoing-label definition.

        leaf backup-outgoing-interface  {
            type  string {
                length "1..1965";
                pattern "[^?' =,>|]+";
            }
            description "Backup Out-going Interface of TI-LFA route";
        } // END of backup-outgoing-interface definition.

    } // END of ipv4-tilfa-route-nexthop-state definition.
    grouping tilfa-pq-trunk-state {
        description
            "State items for IPV4 ISIS TI-LFA pq trunk";
        leaf trunk-id  {
            type  uint32;
            description "Tilfa PQ Trunk Id";
        } // END of trunk-id definition.

        leaf trunk-name  {
            type  string {
                length "1..1965";
                pattern "[^?' =,>|]+";
            }
            description "Tilfa PQ Trunk name";
        } // END of trunk-name definition.

        leaf nexthop  {
            type  inet:ipv4-address;
            description "PQ Trunk Nexthop Address";
        } // END of nexthop definition.

        leaf outgoing-label  {
            type  uint32;
            description "PQ Trunk Outgoing Label";
        } // END of outgoing-label definition.

    } // END of tilfa-pq-trunk-state definition.
    grouping tilfa-pq-state {
        description
            "State items for TI-LFA PQ Nodes";
        leaf level  {
            type  ipi-isis-types:isis_level2_t;
            description "TI-LFA PQ Nodes level";
        } // END of level definition.

    } // END of tilfa-pq-state definition.
    grouping tilfa-pq-vertex-state {
        description
            "State items for TI-LFA PQ Nodes vertex";
        leaf destination-vertex  {
            type  string {
                length "1..1965";
                pattern "[^?' =,>|]+";
            }
            description "TI-LFA PQ Node destination vertex";
        } // END of destination-vertex definition.

    } // END of tilfa-pq-vertex-state definition.
    grouping tilfa-pq-interface-state {
        description
            "State items for TI-LFA PQ Nodes interface state";
        leaf name  {
            type  string {
                length "1..1965";
                pattern "[^?' =,>|]+";
            }
            description "TI-LFA PQ Node interface name";
        } // END of name definition.

    } // END of tilfa-pq-interface-state definition.
    grouping tilfa-pq-link-protection-state {
        description
            "State items for TI-LFA PQ Nodes link protection state";
        leaf-list pnodes  {
            type  string {
                length "1..1965";
                pattern "[^?' =,>|]+";
            }
            description "ISIS TI-LFA P nodes";
        } // END of pnodes definition.

        leaf-list qnodes  {
            type  string {
                length "1..1965";
                pattern "[^?' =,>|]+";
            }
            description "ISIS TI-LFA Q nodes";
        } // END of qnodes definition.

        leaf pq-node  {
            type  string {
                length "1..1965";
                pattern "[^?' =,>|]+";
            }
            description "ISIS TI-LFA PQ node";
        } // END of pq-node definition.

        leaf q-node-disjoint  {
            type  string {
                length "1..1965";
                pattern "[^?' =,>|]+";
            }
            description "ISIS TI-LFA  Q node disjoint";
        } // END of q-node-disjoint definition.

    } // END of tilfa-pq-link-protection-state definition.
    grouping tilfa-pq-node-protection-state {
        description
            "State items for TI-LFA PQ Nodes Node  protection state";
        leaf-list pnodes  {
            type  string {
                length "1..1965";
                pattern "[^?' =,>|]+";
            }
            description "ISIS TI-LFA P nodes";
        } // END of pnodes definition.

        leaf-list qnodes  {
            type  string {
                length "1..1965";
                pattern "[^?' =,>|]+";
            }
            description "ISIS TI-LFA Q nodes";
        } // END of qnodes definition.

        leaf pq-node  {
            type  string {
                length "1..1965";
                pattern "[^?' =,>|]+";
            }
            description "ISIS TI-LFA PQ node";
        } // END of pq-node definition.

        leaf q-node-disjoint  {
            type  string {
                length "1..1965";
                pattern "[^?' =,>|]+";
            }
            description "ISIS TI-LFA  Q node disjoint";
        } // END of q-node-disjoint definition.

    } // END of tilfa-pq-node-protection-state definition.

    grouping  graceful-restart-grouping {
    description
        "This container defines the ISIS Graceful Restart";
    container graceful-restart {
        if-feature feature-list:HAVE_ISISD;
        description
            "This container defines the ISIS Graceful Restart";
        container config {
            description
                "This container defines the ISIS Graceful Restart config parameters";
            uses isis-gr-config;
        } // END of config-container definition.
        container state {
            config false;
            description
                "This container defines the ISIS Graceful Restart state information";
            uses isis-gr-config;
        } // END of state-container definition.
    } // END of graceful-restart-container definition.
    } // END of graceful-restart-grouping definition.


}
