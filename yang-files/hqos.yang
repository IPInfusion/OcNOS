/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : hqos.yang
*
*/

submodule hqos {

    belongs-to  ZebOS { prefix ZebOS; }
    include interface;


    import cml_data_types {
        prefix cml_data_types;
    }

    import feature_list {
        prefix feature_list;
    }

    description
        "Hierarchical quality of service";


    revision "2017-01-30" {
        description "datamodel adding for HQOS.";
    }

    grouping aclFilter {
                leaf filterType  {
            type  cml_data_types:CML_FILTER_TYPE_T;  
        } // END of filterType definition.

        leaf common  {
            type  cml_data_types:CML_INT32_T;  
        } // END of common definition.

        container mfilter {
                        config true;

            description
                "mfilter structure in Hierarchical quality of service";

            leaf extended  {
                type  cml_data_types:CML_INT32_T;  
            } // END of extended definition.

            leaf pktFormat  {
                type  cml_data_types:CML_INT32_T;  
            } // END of pktFormat definition.

            leaf-list filterA  {
                type  cml_data_types:CML_INT8_T;  
            } // END of filterA definition.

            leaf-list Amask  {
                type  cml_data_types:CML_INT8_T;  
            } // END of Amask definition.

            leaf-list filterM  {
                type  cml_data_types:CML_INT8_T;  
            } // END of filterM definition.

            leaf-list Mmask  {
                type  cml_data_types:CML_INT8_T;  
            } // END of Mmask definition.

            leaf priority  {
                type  cml_data_types:CML_INT32_T;  
            } // END of priority definition.

        } // END of mfilter-container definition.
        container ifilter {
                        config true;

            description
                "ipv4 filter structure in Hierarchical quality of service";

            leaf flag  {
                type  cml_data_types:CML_INT32_T;  
            } // END of flag definition.

            leaf addr  {
                type  cml_data_types:CML_IPV4_ADDR_T;  
            } // END of addr definition.

            leaf addrMask  {
                type  cml_data_types:CML_IPV4_ADDR_T;  
            } // END of addrMask definition.

            leaf mask  {
                type  cml_data_types:CML_IPV4_ADDR_T;  
            } // END of mask definition.

            leaf maskMask  {
                type  cml_data_types:CML_IPV4_ADDR_T;  
            } // END of maskMask definition.

            leaf addrConfig  {
                type  cml_data_types:CML_IPV4_ADDR_T;  
            } // END of addrConfig definition.

            leaf maskConfig  {
                type  cml_data_types:CML_IPV4_ADDR_T;  
            } // END of maskConfig definition.

            leaf proto  {
                type  cml_data_types:CML_INT16_T;  
            } // END of proto definition.

            leaf isIanaValue  {
                type  cml_data_types:CML_INT8_T;  
            } // END of isIanaValue definition.

        } // END of ifilter-container definition.
        container ip6filter {
                        config true;

            description
                "ipv6 filter structure in Hierarchical quality of service";

            leaf flag  {
                type  cml_data_types:CML_INT32_T;  
            } // END of flag definition.

            leaf saddr  {
                type  cml_data_types:CML_IPV6_ADDR_T;  
            } // END of saddr definition.

            leaf saddrMask  {
                type  cml_data_types:CML_IPV6_ADDR_T;  
            } // END of saddrMask definition.

            leaf daddr  {
                type  cml_data_types:CML_IPV6_ADDR_T;  
            } // END of daddr definition.

            leaf daddrMask  {
                type  cml_data_types:CML_IPV6_ADDR_T;  
            } // END of daddrMask definition.

            leaf saddrConfig  {
                type  cml_data_types:CML_IPV6_ADDR_T;  
            } // END of saddrConfig definition.

            leaf daddrConfig  {
                type  cml_data_types:CML_IPV4_ADDR_T;  
            } // END of daddrConfig definition.

            leaf proto  {
                type  cml_data_types:CML_INT16_T;  
            } // END of proto definition.

            leaf isIanaValue  {
                type  cml_data_types:CML_INT8_T;  
            } // END of isIanaValue definition.

        } // END of ip6filter-container definition.
        container zfilter {
                        config true;

            description
                "zfilter structure in Hierarchical quality of service";

            leaf exact  {
                type  cml_data_types:CML_INT32_T;  
            } // END of exact definition.

            leaf prefix  {
                type  cml_data_types:CML_STRING_T {
                    length "0..255";
                }
            } // END of prefix definition.

        } // END of zfilter-container definition.
        container zextfilter {
                        config true;

            description
                "qos zebos ext structure in Hierarchical quality of service";

            leaf extProtocol  {
                type  cml_data_types:CML_INT32_T;  
            } // END of extProtocol definition.

            leaf sprefix  {
                type  cml_data_types:CML_STRING_T {
                    length "0..255";
                }
            } // END of sprefix definition.

            leaf sportOp  {
                type  cml_data_types:CML_QOS_OPERATION_T;  
            } // END of sportOp definition.

            leaf sport  {
                type  cml_data_types:CML_INT32_T;  
            } // END of sport definition.

            leaf dprefix  {
                type  cml_data_types:CML_STRING_T {
                    length "0..255";
                }
            } // END of dprefix definition.

            leaf dportOp  {
                type  cml_data_types:CML_QOS_OPERATION_T;  
            } // END of dportOp definition.

            leaf dport  {
                type  cml_data_types:CML_INT32_T;  
            } // END of dport definition.

        } // END of zextfilter-container definition.
    } // END of aclFilter definition.

    grouping  qos-grouping {
    container qos {
                config true;

        description
            "nsm master structure having Hierarchical quality of service";


        list cosQueueProfileTree {
             
            description
                "cos_queue_profile_tree having Hierarchical quality of service";

            config true;
            key "cosQueueProfile";

            
            leaf cosQueueProfile  {
                type  cml_data_types:CML_UINT32_T {
                     range "1..64";
                }
            } // END of cosQueueProfile definition.


            list nsmQosProfileUpdate {
                 
                description
                    "nsm_qos_profile_update of Hierarchical quality of service";

                config true;
                key "profileCos";

                
                leaf profileCos  {
                    type  cml_data_types:CML_INT8_T {
                         range "0..7";
                    }
                } // END of profileCos definition.

                leaf profileQueue  {
                    mandatory true;
                    type  cml_data_types:CML_INT8_T {
                         range "0..7";
                    }
                } // END of profileQueue definition.

            } // End of nsmQosProfileUpdate-list
        } // End of cosQueueProfileTree-list

        list qifList {
             
            description
                "interface qif list in Hierarchical quality of service";

            config true;
            key "ifName";

            
            leaf ifName  {
                type  cml_data_types:CML_STRING_T {
                    length "0..255";
                }
            } // END of ifName definition.

            leaf-list serviceInput  {
                type  cml_data_types:CML_STRING_T {
                    length "0..255";
                }
            } // END of serviceInput definition.

            leaf-list serviceOutput  {
                type  cml_data_types:CML_STRING_T {
                    length "0..255";
                }
            } // END of serviceOutput definition.

            leaf-list serviceQueuing  {
                type  cml_data_types:CML_STRING_T {
                    length "0..255";
                }
            } // END of serviceQueuing definition.

            leaf trustType  {
                type  cml_data_types:CML_BOOL_T;  
            } // END of trustType definition.


            list cosQueue {
                 
                description
                    "cos queue values mapping at interface level";

                config true;
                key "CosTblSize";

                
                leaf CosTblSize  {
                    type  cml_data_types:CML_INT8_T {
                         range "0..7";
                    }
                } // END of CosTblSize definition.

                leaf InterfaceCosQueueId  {
                    mandatory true;
                    type  cml_data_types:CML_INT32_T {
                         range "0..7";
                    }
                } // END of InterfaceCosQueueId definition.

            } // End of cosQueue-list

            list dscpQueue {
                 
                description
                    "dscp queue mapping structure in Hierarchical quality of service";

                config true;
                key "DscpTblSize";

                
                leaf DscpTblSize  {
                    type  cml_data_types:CML_INT32_T {
                         range "0..63";
                    }
                } // END of DscpTblSize definition.

                leaf dscpQueueMapTbl  {
                    mandatory true;
                    type  cml_data_types:CML_INT32_T {
                         range "0..7";
                    }
                } // END of dscpQueueMapTbl definition.

            } // End of dscpQueue-list
        } // End of qifList-list

        list classQosMap {
             
            description
                "class queue mapping structure in Hierarchical quality of service";

            config true;
            key "name";

            
            leaf name  {
                type  cml_data_types:CML_STRING_T {
                    length "0..255";
                }
            } // END of name definition.

            leaf cmapType  {
                type  cml_data_types:CML_QOS_CMAP_TYPE_T;  
            } // END of cmapType definition.

            leaf cmapMatchCriteria  {
                type  cml_data_types:CML_CMAP_MATCH_CRITERIA_T;  
            } // END of cmapMatchCriteria definition.

            leaf priority  {
                type  cml_data_types:CML_UINT8_T;  
            } // END of priority definition.

            leaf cmapMatchId  {
                type  cml_data_types:CML_UINT16_T;  
            } // END of cmapMatchId definition.

            leaf matchCount  {
                type  cml_data_types:CML_UINT16_T;  
            } // END of matchCount definition.

            leaf cmapMatchSet  {
                type  cml_data_types:CML_UINT8_T;  
            } // END of cmapMatchSet definition.

            leaf matchAclCount  {
                type  cml_data_types:CML_UINT16_T;  
            } // END of matchAclCount definition.

            leaf aclNameSet  {
                type  cml_data_types:CML_STRING_T {
                    length "0..255";
                }
            } // END of aclNameSet definition.

            leaf srcAddr  {
                type  cml_data_types:CML_STRING_T {
                    length "0..255";
                }
            } // END of srcAddr definition.

            leaf dstAddr  {
                type  cml_data_types:CML_STRING_T {
                    length "0..255";
                }
            } // END of dstAddr definition.

            leaf aclName  {
                type  cml_data_types:CML_STRING_T {
                    length "0..255";
                }
            } // END of aclName definition.

            leaf negate  {
                type  cml_data_types:CML_HQOS_TRAFFIC_TYPE_NOT_T;  
            } // END of negate definition.

            leaf trafficType  {
                type  cml_data_types:CML_HQOS_TRAFFIC_TYPE_T;  
            } // END of trafficType definition.

            leaf-list ethertypeList  {
                type  cml_data_types:CML_STRING_T {
                    length "0..255";
                }
            } // END of ethertypeList definition.

            container qosGrp {
                                config true;

                description
                    "qos group match structure in Hierarchical quality of service";

                leaf flag  {
                    type  cml_data_types:CML_UINT32_T;  
                } // END of flag definition.

                leaf num  {
                    type  cml_data_types:CML_UINT32_T {
                         range "1..2000";
                    }
                } // END of num definition.

                leaf-list cmapQosGroup  {
                    type  cml_data_types:CML_UINT8_T;  
                } // END of cmapQosGroup definition.

            } // END of qosGrp-container definition.
            container cos {
                                config true;

                description
                    "cos structure in Hierarchical quality of service";

                leaf num  {
                    type  cml_data_types:CML_UINT32_T;  
                } // END of num definition.

                leaf matchType  {
                    type  cml_data_types:CML_HQOS_MATCH_NOT_T;  
                } // END of matchType definition.

                leaf cos  {
                    type  cml_data_types:CML_STRING_T;  
                } // END of cos definition.

            } // END of cos-container definition.
            container cosInner {
                                config true;

                description
                    "cos inner structure in Hierarchical quality of service";

                leaf num  {
                    type  cml_data_types:CML_UINT32_T;  
                } // END of num definition.

                leaf innerType  {
                    type  cml_data_types:CML_HQOS_MATCH_NOT_T;  
                } // END of innerType definition.

                leaf cos  {
                    type  cml_data_types:CML_STRING_T;  
                } // END of cos definition.

            } // END of cosInner-container definition.
            container cmapDscp {
                                config true;

                description
                    "cmap dscp structure in Hierarchical quality of service";

                leaf ver  {
                    type  cml_data_types:CML_INT8_T;  
                } // END of ver definition.

                leaf num  {
                    type  cml_data_types:CML_INT8_T;  
                } // END of num definition.

                leaf dscpType  {
                    type  cml_data_types:CML_HQOS_MATCH_NOT_DSCP_T;  
                } // END of dscpType definition.

                leaf dscp  {
                    type  cml_data_types:CML_QOS_DSCP_VAL_T;  
                } // END of dscp definition.

                leaf ipv6Num  {
                    type  cml_data_types:CML_INT8_T;  
                } // END of ipv6Num definition.

            } // END of cmapDscp-container definition.
            container cmapIpPrec {
                                config true;

                description
                    "ip precedence structure in Hierarchical quality of service";

                leaf precedenceType  {
                    type  cml_data_types:CML_HQOS_MATCH_NOT_PRECEDENCE_T;  
                } // END of precedenceType definition.

                leaf precedence  {
                    type  cml_data_types:CML_QOS_PREC_VAL_T;  
                } // END of precedence definition.

            } // END of cmapIpPrec-container definition.
            container cmapRtp {
                                config true;

                description
                    "match rtp structure in Hierarchical quality of service";

                leaf rtpType  {
                    type  cml_data_types:CML_HQOS_MATCH_NOT_RTP_T;  
                } // END of rtpType definition.

                leaf rtp  {
                    type  cml_data_types:CML_STRING_T;  
                } // END of rtp definition.

            } // END of cmapRtp-container definition.
            container cmapProto {
                                config true;

                description
                    "cmap proto structure in Hierarchical quality of service";

                leaf protocolType  {
                    type  cml_data_types:CML_HQOS_MATCH_NOT_PROTOCOL_T;  
                } // END of protocolType definition.

                leaf protocol  {
                    type  cml_data_types:CML_PROTO_TYPE_T;  
                } // END of protocol definition.

            } // END of cmapProto-container definition.
            container vlan {
                                config true;

                description
                    "vlan configuration in Hierarchical quality of service";

                leaf vlanType  {
                    type  cml_data_types:CML_HQOS_MATCH_NOT_VLAN_T;  
                } // END of vlanType definition.

                leaf vlan  {
                    type  cml_data_types:CML_STRING_T;  
                } // END of vlan definition.

            } // END of vlan-container definition.
            container vlanInner {
                                config true;

                description
                    "inner vlan structure in Hierarchical quality of service";

                leaf vlanInnerType  {
                    type  cml_data_types:CML_HQOS_MATCH_NOT_VLAN_T;  
                } // END of vlanInnerType definition.

                leaf-list vlanInner  {
                    type  cml_data_types:CML_STRING_T;  
                } // END of vlanInner definition.

            } // END of vlanInner-container definition.
            container cmapExp {
                if-feature feature_list:HAVE_DIFFSERV;
                                config true;

                description
                    "mpls exp structure in Hierarchical quality of service";

                leaf expType  {
                    type  cml_data_types:CML_HQOS_MATCH_NOT_MPLS_EXP_T;  
                } // END of expType definition.

                leaf exp  {
                    type  cml_data_types:CML_STRING_T {
                        length "0..255";
                    }
                } // END of exp definition.

            } // END of cmapExp-container definition.
        } // End of classQosMap-list

        list pmap {
             
            description
                "pmap list in Hierarchical quality of service";

            config true;
            key "pmapName";

            
            leaf pmapName  {
                type  cml_data_types:CML_STRING_T {
                    length "0..255";
                }
            } // END of pmapName definition.

            leaf pmapType  {
                type  cml_data_types:CML_PMAP_TYPE_T;  
            } // END of pmapType definition.

            leaf aclName  {
                type  cml_data_types:CML_STRING_T {
                    length "0..255";
                }
            } // END of aclName definition.

            leaf aclAttached  {
                type  cml_data_types:CML_UINT8_T;  
            } // END of aclAttached definition.

            leaf numAclsAttached  {
                type  cml_data_types:CML_INT32_T;  
            } // END of numAclsAttached definition.

            leaf defaultClassAttach  {
                type  cml_data_types:CML_INT8_T;  
            } // END of defaultClassAttach definition.

            leaf seqNum  {
                type  cml_data_types:CML_INT16_T;  
            } // END of seqNum definition.

            leaf cmapCount  {
                type  cml_data_types:CML_INT16_T;  
            } // END of cmapCount definition.

            leaf attached  {
                type  cml_data_types:CML_INT32_T;  
            } // END of attached definition.

            leaf-list clName  {
                type  cml_data_types:CML_STRING_T {
                    length "0..255";
                }
            } // END of clName definition.

            leaf queuingFlag  {
                type  cml_data_types:CML_INT8_T;  
            } // END of queuingFlag definition.

            leaf bandwidthMax  {
                type  cml_data_types:CML_INT32_T;  
            } // END of bandwidthMax definition.

            leaf shapeMax  {
                type  cml_data_types:CML_INT32_T;  
            } // END of shapeMax definition.

            leaf bandwidthRemaining  {
                type  cml_data_types:CML_INT32_T;  
            } // END of bandwidthRemaining definition.

            leaf bandwidthRemFlag  {
                type  cml_data_types:CML_INT8_T;  
            } // END of bandwidthRemFlag definition.

            leaf bandwidthRateType  {
                type  cml_data_types:CML_INT8_T;  
            } // END of bandwidthRateType definition.

            leaf shapeRateType  {
                type  cml_data_types:CML_INT8_T;  
            } // END of shapeRateType definition.

            leaf bandwidthRefCount  {
                type  cml_data_types:CML_INT8_T;  
            } // END of bandwidthRefCount definition.

            leaf shapeRefCount  {
                type  cml_data_types:CML_INT8_T;  
            } // END of shapeRefCount definition.

            leaf bandwidthTotal  {
                type  cml_data_types:CML_INT32_T;  
            } // END of bandwidthTotal definition.

            leaf thresholdRefCount  {
                type  cml_data_types:CML_INT8_T;  
            } // END of thresholdRefCount definition.

            leaf thresholdType  {
                type  cml_data_types:CML_INT8_T;  
            } // END of thresholdType definition.

            leaf matchNotProto  {
                type  cml_data_types:CML_INT8_T;  
            } // END of matchNotProto definition.

            leaf priorityCount  {
                type  cml_data_types:CML_INT8_T;  
            } // END of priorityCount definition.

            leaf servicePolicyAttach  {
                type  cml_data_types:CML_INT8_T;  
            } // END of servicePolicyAttach definition.

            leaf schedQueBmp  {
                type  cml_data_types:CML_INT8_T;  
            } // END of schedQueBmp definition.

            leaf servicePolicyCount  {
                type  cml_data_types:CML_INT32_T;  
            } // END of servicePolicyCount definition.

            leaf policerCount  {
                type  cml_data_types:CML_INT8_T;  
            } // END of policerCount definition.

            leaf noUpdate  {
                type  cml_data_types:CML_INT8_T;  
            } // END of noUpdate definition.


            list cmapTree {
                 
                description
                    "Applying class on policy structure in Hierarchical quality of service";

                config true;
                key "cmapName";

                
                leaf cmapName  {
                    type  cml_data_types:CML_STRING_T {
                        length "0..255";
                    }
                } // END of cmapName definition.

                leaf cmapId  {
                    type  cml_data_types:CML_PMAP_TYPE_T;  
                } // END of cmapId definition.

                leaf userCfgPriority  {
                    type  cml_data_types:CML_INT16_T {
                         range "1..1000";
                    }
                } // END of userCfgPriority definition.

                container police {
                                        config true;

                    description
                        "police structure of Hierarchical quality of service";

                    leaf policeType  {
                        type  cml_data_types:CML_UINT32_T;  
                    } // END of policeType definition.

                    leaf avg  {
                        type  cml_data_types:CML_UINT32_T;  
                    } // END of avg definition.

                    leaf cirType  {
                        type  cml_data_types:CML_QOS_RATE_T;  
                    } // END of cirType definition.

                    leaf pir  {
                        type  cml_data_types:CML_UINT32_T;  
                    } // END of pir definition.

                    leaf pirType  {
                        type  cml_data_types:CML_QOS_RATE_T;  
                    } // END of pirType definition.

                    leaf burst  {
                        type  cml_data_types:CML_UINT32_T;  
                    } // END of burst definition.

                    leaf bcType  {
                        type  cml_data_types:CML_BURST_TYPE_T;  
                    } // END of bcType definition.

                    leaf excessBurst  {
                        type  cml_data_types:CML_UINT32_T;  
                    } // END of excessBurst definition.

                    leaf beType  {
                        type  cml_data_types:CML_BURST_TYPE_T;  
                    } // END of beType definition.

                    leaf confPoliceVal  {
                        type  cml_data_types:CML_UINT8_T;  
                    } // END of confPoliceVal definition.

                    leaf confAct  {
                        type  cml_data_types:CML_CONFORM_ACTION_T;  
                    } // END of confAct definition.

                    leaf policeDscp  {
                        type  cml_data_types:CML_UINT8_T;  
                    } // END of policeDscp definition.

                    leaf exdAct  {
                        type  cml_data_types:CML_EXCEED_ACTION_T;  
                    } // END of exdAct definition.

                    leaf votPoliceVal  {
                        type  cml_data_types:CML_UINT8_T;  
                    } // END of votPoliceVal definition.

                    leaf votAct  {
                        type  cml_data_types:CML_VIOLATE_ACTION_T;  
                    } // END of votAct definition.

                    leaf policerId  {
                        type  cml_data_types:CML_UINT32_T;  
                    } // END of policerId definition.

                    leaf fcMode  {
                        type  cml_data_types:CML_FLOW_CONTROL_MODE_T;  
                    } // END of fcMode definition.

                    leaf mode  {
                        type  cml_data_types:CML_UINT8_T;  
                    } // END of mode definition.

                    leaf policeTos  {
                        type  cml_data_types:CML_UINT8_T;  
                    } // END of policeTos definition.

                    leaf policeCos  {
                        type  cml_data_types:CML_UINT8_T;  
                    } // END of policeCos definition.

                    leaf policeExp  {
                        if-feature feature_list:HAVE_DIFFSERV;
                        type  cml_data_types:CML_UINT8_T;  
                    } // END of policeExp definition.

                } // END of police-container definition.
                container setS {
                                        config true;

                    description
                        "setting class on policy structure in Hierarchical quality of service";

                    leaf level  {
                        type  cml_data_types:CML_EMPTY_T;  
                    } // END of level definition.

                    leaf Type  {
                        type  cml_data_types:CML_INT32_T;  
                    } // END of Type definition.

                    leaf value  {
                        type  cml_data_types:CML_QOS_SET_VAL_T;  
                    } // END of value definition.

                } // END of setS-container definition.
                container nsmQosShape {
                                        config true;

                    description
                        "qos shape structure in Hierarchical quality of service";

                    leaf rate  {
                        type  cml_data_types:CML_INT32_T;  
                    } // END of rate definition.

                    leaf rateType  {
                        type  cml_data_types:CML_HQOS_SHAPE_TYPE_T;  
                    } // END of rateType definition.

                    leaf inputRate  {
                        type  cml_data_types:CML_INT32_T;  
                    } // END of inputRate definition.

                    leaf netShapeRate  {
                        type  cml_data_types:CML_INT32_T;  
                    } // END of netShapeRate definition.

                } // END of nsmQosShape-container definition.
                container qosQueuing {
                                        config true;

                    description
                        "qos queuing structure in Hierarchical quality of service";

                    leaf flag  {
                        type  cml_data_types:CML_INT32_T;  
                    } // END of flag definition.

                    leaf pqueueFlag  {
                        type  cml_data_types:CML_INT8_T;  
                    } // END of pqueueFlag definition.

                    leaf bandwidthRemainingPer  {
                        type  cml_data_types:CML_INT8_T {
                             range "1..100";
                        }
                    } // END of bandwidthRemainingPer definition.

                    leaf wrrWeight  {
                        type  cml_data_types:CML_INT32_T {
                             range "1..127";
                        }
                    } // END of wrrWeight definition.

                    leaf servicePolicy  {
                        type  cml_data_types:CML_STRING_T {
                            length "0..255";
                        }
                    } // END of servicePolicy definition.

                    container qosWred {
                                                config true;

                        description
                            "qos wred structure in Hierarchical quality of service";

                        leaf minThreshold  {
                            type  cml_data_types:CML_INT32_T;  
                        } // END of minThreshold definition.

                        leaf maxThreshold  {
                            type  cml_data_types:CML_INT32_T;  
                        } // END of maxThreshold definition.

                        leaf minThresholdYp  {
                            type  cml_data_types:CML_INT32_T;  
                        } // END of minThresholdYp definition.

                        leaf maxThresholdYp  {
                            type  cml_data_types:CML_INT32_T;  
                        } // END of maxThresholdYp definition.

                        leaf minThresholdRp  {
                            type  cml_data_types:CML_INT32_T;  
                        } // END of minThresholdRp definition.

                        leaf maxThresholdRp  {
                            type  cml_data_types:CML_INT32_T;  
                        } // END of maxThresholdRp definition.

                        leaf minType  {
                            type  cml_data_types:CML_INT8_T;  
                        } // END of minType definition.

                        leaf maxType  {
                            type  cml_data_types:CML_INT8_T;  
                        } // END of maxType definition.

                        leaf-list cos  {
                            type  cml_data_types:CML_INT8_T;  
                        } // END of cos definition.

                    } // END of qosWred-container definition.
                    container tailDrop {
                                                config true;

                        description
                            "tail drop structure in Hierarchical quality of service";

                        leaf cos  {
                            type  cml_data_types:CML_INT32_T;  
                        } // END of cos definition.

                        leaf maxThreshold  {
                            type  cml_data_types:CML_INT32_T;  
                        } // END of maxThreshold definition.

                        leaf maxType  {
                            type  cml_data_types:CML_UINT8_T;  
                        } // END of maxType definition.

                    } // END of tailDrop-container definition.
                    container qosBandwidth {
                                                config true;

                        description
                            "qos bandwidth structure in Hierarchical quality of service";

                        leaf inputRate  {
                            type  cml_data_types:CML_INT32_T;  
                        } // END of inputRate definition.

                        leaf rate  {
                            type  cml_data_types:CML_INT32_T;  
                        } // END of rate definition.

                        leaf rateType  {
                            type  cml_data_types:CML_HQOS_SHAPE_TYPE_T;  
                            default "kbps";
                        } // END of rateType definition.

                    } // END of qosBandwidth-container definition.
                } // END of qosQueuing-container definition.
                container qoswrrSp {
                                        config true;

                    description
                        "wrr structure in Hierarchical quality of service";

                    leaf wrrSpFlag  {
                        type  cml_data_types:CML_INT32_T;  
                    } // END of wrrSpFlag definition.

                } // END of qoswrrSp-container definition.
            } // End of cmapTree-list

            list protoCmapl {
                 
                description
                    "nsm cmap list in Hierarchical quality of service";

                config true;
                key "name";

                
                leaf name  {
                    type  cml_data_types:CML_STRING_T {
                        length "0..255";
                    }
                } // END of name definition.

            } // End of protoCmapl-list
        } // End of pmap-list
        container acl {
                        config true;

            description
                "acl master of Hierarchical quality of service";

            leaf name  {
                type  cml_data_types:CML_STRING_T {
                    length "0..255";
                }
            } // END of name definition.

            leaf remark  {
                type  cml_data_types:CML_STRING_T {
                    length "0..255";
                }
            } // END of remark definition.

            leaf aclType  {
                type  cml_data_types:CML_INT32_T;  
            } // END of aclType definition.

            leaf attached  {
                type  cml_data_types:CML_INT32_T;  
            } // END of attached definition.


            list accessNum {
                 
                description
                    "access list structure in Hierarchical quality of service";

                config true;
                key "aclType";

                
                leaf aclType  {
                    type  cml_data_types:CML_INT32_T;  
                } // END of aclType definition.

                uses aclFilter;
            } // End of accessNum-list

            list accessString {
                 
                description
                    "access list structure in Hierarchical quality of service";

                config true;
                key "aclType";

                
                leaf aclType  {
                    type  cml_data_types:CML_INT32_T;  
                } // END of aclType definition.

                uses aclFilter;
            } // End of accessString-list
        } // END of acl-container definition.
        container qosGlobal {
                        config true;

            description
                "global structure of Hierarchical quality of service";

            leaf state  {
                type  cml_data_types:CML_HQOS_ENABLE_DISABLE_T;  
                description "Enabled(1)/Disabled(0) state";
            } // END of state definition.

            leaf remarkDei  {
                type  cml_data_types:CML_BOOL_T;  
            } // END of remarkDei definition.

            leaf-list dscpQueueMapTbl  {
                type  cml_data_types:CML_INT8_T;  
            } // END of dscpQueueMapTbl definition.

            leaf-list dscpDscpMapTbl  {
                type  cml_data_types:CML_INT8_T;  
            } // END of dscpDscpMapTbl definition.

            leaf-list cosQueueMapTblModified  {
                type  cml_data_types:CML_INT8_T;  
            } // END of cosQueueMapTblModified definition.

            leaf-list cosCosMapTbl  {
                type  cml_data_types:CML_INT8_T;  
            } // END of cosCosMapTbl definition.

            leaf statistics  {
                type  cml_data_types:CML_BOOL_T;  
            } // END of statistics definition.


            list dscpml {
                 
                description
                    "nsm dscp mut list structure in Hierarchical quality of service";

                config true;
                key "name";

                
                leaf name  {
                    type  cml_data_types:CML_STRING_T {
                        length "0..255";
                    }
                } // END of name definition.

                leaf aclName  {
                    type  cml_data_types:CML_STRING_T {
                        length "0..255";
                    }
                } // END of aclName definition.

                leaf-list dscpMutD  {
                    type  cml_data_types:CML_INT8_T;  
                } // END of dscpMutD definition.

            } // End of dscpml-list

            list dcosl {
                 
                description
                    "nsm dscp cos list in Hierarchical quality of service";

                config true;
                key "name";

                
                leaf name  {
                    type  cml_data_types:CML_STRING_T {
                        length "0..255";
                    }
                } // END of name definition.

                leaf aclName  {
                    type  cml_data_types:CML_STRING_T {
                        length "0..255";
                    }
                } // END of aclName definition.

                leaf-list dscpMutD  {
                    type  cml_data_types:CML_INT8_T;  
                } // END of dscpMutD definition.

            } // End of dcosl-list

            list cos {
                 
                description
                    "nsm agp list in Hierarchical quality of service";

                config true;
                key "name";

                
                leaf name  {
                    type  cml_data_types:CML_STRING_T {
                        length "0..255";
                    }
                } // END of name definition.

                leaf aclName  {
                    type  cml_data_types:CML_STRING_T {
                        length "0..255";
                    }
                } // END of aclName definition.

                container police {
                                        config true;

                    description
                        "police structure of Hierarchical quality of service";

                    leaf policeType  {
                        type  cml_data_types:CML_UINT32_T;  
                    } // END of policeType definition.

                    leaf avg  {
                        type  cml_data_types:CML_UINT32_T;  
                    } // END of avg definition.

                    leaf cirType  {
                        type  cml_data_types:CML_QOS_RATE_T;  
                    } // END of cirType definition.

                    leaf pir  {
                        type  cml_data_types:CML_UINT32_T;  
                    } // END of pir definition.

                    leaf pirType  {
                        type  cml_data_types:CML_QOS_RATE_T;  
                    } // END of pirType definition.

                    leaf burst  {
                        type  cml_data_types:CML_UINT32_T;  
                    } // END of burst definition.

                    leaf bcType  {
                        type  cml_data_types:CML_BURST_TYPE_T;  
                    } // END of bcType definition.

                    leaf excessBurst  {
                        type  cml_data_types:CML_UINT32_T;  
                    } // END of excessBurst definition.

                    leaf beType  {
                        type  cml_data_types:CML_BURST_TYPE_T;  
                    } // END of beType definition.

                    leaf confPoliceVal  {
                        type  cml_data_types:CML_UINT8_T;  
                    } // END of confPoliceVal definition.

                    leaf confAct  {
                        type  cml_data_types:CML_CONFORM_ACTION_T;  
                    } // END of confAct definition.

                    leaf policeDscp  {
                        type  cml_data_types:CML_UINT8_T;  
                    } // END of policeDscp definition.

                    leaf exdAct  {
                        type  cml_data_types:CML_EXCEED_ACTION_T;  
                    } // END of exdAct definition.

                    leaf votPoliceVal  {
                        type  cml_data_types:CML_UINT8_T;  
                    } // END of votPoliceVal definition.

                    leaf votAct  {
                        type  cml_data_types:CML_VIOLATE_ACTION_T;  
                    } // END of votAct definition.

                } // END of police-container definition.
            } // End of cos-list

            list cosQueue {
                 
                description
                    "cos queue values mapping structure in Hierarchical quality of service";

                config true;
                key "CosTblSize";

                
                leaf CosTblSize  {
                    type  cml_data_types:CML_INT8_T {
                         range "0..7";
                    }
                } // END of CosTblSize definition.

                leaf cosQueueMapTbl  {
                    mandatory true;
                    type  cml_data_types:CML_INT32_T {
                         range "0..7";
                    }
                } // END of cosQueueMapTbl definition.

            } // End of cosQueue-list

            list dscpQueue {
                 
                description
                    "dscp queue values mapping structure in Hierarchical quality of service";

                config true;
                key "DscpTblSize";

                
                leaf DscpTblSize  {
                    type  cml_data_types:CML_INT32_T {
                         range "0..63";
                    }
                } // END of DscpTblSize definition.

                leaf dscpQueueMapTbl  {
                    mandatory true;
                    type  cml_data_types:CML_INT32_T {
                         range "0..7";
                    }
                } // END of dscpQueueMapTbl definition.

            } // End of dscpQueue-list

            list expClass {
                                 if-feature feature_list:HAVE_DIFFSERV;

                description
                    "mpls exp values mapping structure in Hierarchical quality of service";

                config true;
                key "ExpTblSize";

                
                leaf ExpTblSize  {
                    type  cml_data_types:CML_INT32_T {
                         range "0..7";
                    }
                } // END of ExpTblSize definition.

                leaf expQueueMapTbl  {
                    mandatory true;
                    type  cml_data_types:CML_INT32_T {
                         range "0..7";
                    }
                } // END of expQueueMapTbl definition.

            } // End of expClass-list

            list classExp {
                                 if-feature feature_list:HAVE_DIFFSERV;

                description
                    "mpls class to exp values mapping structure in Hierarchical quality of service";

                config true;
                key "queueExpTblSize";

                
                leaf queueExpTblSize  {
                    type  cml_data_types:CML_INT32_T {
                         range "0..7";
                    }
                } // END of queueExpTblSize definition.

                leaf queueExpMapTbl  {
                    mandatory true;
                    type  cml_data_types:CML_INT32_T {
                         range "0..7";
                    }
                } // END of queueExpMapTbl definition.

            } // End of classExp-list
            container wrrMode {
                                config true;

                description
                    "Weighted Round Robin Mode";

                leaf weightedRound  {
                    type  cml_data_types:CML_INT32_T {
                         range "1..127";
                    }
                } // END of weightedRound definition.

                leaf nonUnicastQueues  {
                    type  cml_data_types:CML_INT32_T {
                         range "1..127";
                    }
                } // END of nonUnicastQueues definition.

            } // END of wrrMode-container definition.
            container spMode {
                                config true;

                description
                    "Strict Priority Mode";

                leaf unicastQueues  {
                    type  cml_data_types:CML_INT32_T {
                         range "0..1";
                    }
                } // END of unicastQueues definition.

                leaf spNonUnicastQueues  {
                    type  cml_data_types:CML_INT32_T {
                         range "0..1";
                    }
                } // END of spNonUnicastQueues definition.

            } // END of spMode-container definition.
        } // END of qosGlobal-container definition.
    } // END of qos-container definition.
    } // END of qos-container definition.


}
