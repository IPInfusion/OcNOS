/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-profile.yang
*
*/

submodule ipi-platform-profile {

    yang-version 1.1;

    belongs-to  ipi-platform { prefix ipi-platform; }

    import feature-list {
        prefix feature-list;
        revision-date 2023-02-21;
    }

    import cml-data-types {
        prefix cml-data-types;
        revision-date 2022-09-30;
    }

    import ipi-platform-types {
        prefix ipi-platform-types;
        revision-date 2022-06-01;
    }

    include ipi-platform-profile-extended { revision-date 2022-07-22;}
    organization
        "IP Infusion Inc.";

    contact
        "Address: 3965 Freedom Circle, Suite 200, Santa Clara, CA 95054
         Phone: +1 408-400-1900
         E-mail: support@ipinfusion.com
         Web: http://www.ipinfusion.com/";

    description
        "Datamodel for Platform profile object";


    revision "2022-07-22" {
        description "Enabling RTAG7 MPLS option";
        reference " 0.11.3.";
    }

    revision "2022-07-20" {
        description "Added implicit_delete on hardware load-balance";
        reference " 0.11.2.";
    }

    revision "2022-07-05" {
        description "Added attribute ingress-ipv4-custom2";
        reference " 0.11.1.";
    }

    revision "2022-06-27" {
        description "Added new attribute for hardware-profile seamless-bfd (enable|disable)";
        reference " 0.11.1.";
    }

    revision "2022-06-01" {
        description "Updated the yang file with feature";
        reference " 0.11.0.";
    }

    revision "2022-05-02" {
        description "Added new attribute for hardware-profile port mode for UFIS9600-64X and UFIS9600-32X mode";
        reference " 0.10.3.";
    }

    revision "2022-01-07" {
        description "Changed cpu-q-default from attribute to rpc";
        reference " 0.10.3.";
    }

    revision "2022-01-06" {
        description "Added new Attribute hardware-profile port-config";
        reference " 0.10.2.";
    }

    revision "2021-12-27" {
        description "Added implicit-delete to load-balance config";
        reference " 0.10.1.";
    }

    revision "2021-11-22" {
        description "Updated with changes for DNX Broadcom platform hardware profiles";
        reference " 0.10.0.";
    }

    revision "2021-10-12" {
        description "Updated attribute ingress-ipv4 and egress-ipv6 datatype from CML_EMPTY_T to CML_ENABLE_DISABLE_T";
        reference " 0.9.0.";
    }

    revision "2021-09-06" {
        description "Updated description for attribute group-id,Removed enable-status attribute";
        reference " 0.8.0.";
    }

    revision "2021-07-29" {
        description "Added new filter type ipsg and ipsg-ipv6 group";
        reference " 0.7.0.";
    }

    revision "2021-07-28" {
        description "Added new attributes for forwarding profile, cpu-queue and load-balance";
        reference " 0.6.0.";
    }

    revision "2021-06-29" {
        description "Added attribute ingress-ipv6-acl";
        reference " 0.5.0.";
    }

    revision "2021-06-25" {
        description "Added new filter type dhcp-snoop and dhcp-snoop-ipv6 group";
        reference " 0.4.0.";
    }

    revision "2021-06-23" {
        description "Updated attribute ingress-bfd datatype from CML_EMPTY_T to CML_ENABLE_DISABLE_T";
        reference " 0.3.0.";
    }

    revision "2021-06-17" {
        description "Updated with changes for non-DNX Broadcom platform hardware profiles";
        reference " 0.2.0.";
    }

    revision "2021-04-27" {
        description "Added Get API support for TCAM Utilization filter group";
        reference " 0.2.0.";
    }

    revision "2021-03-29" {
        description "Initial Version";
        reference " 0.1.0.";
    }

    grouping hardware-profile-config {
        description
            "Grouping for hardware-profile config objects.";
        leaf flow-control  {
            if-feature feature-list:HAVE_BCM_UFT;
            if-feature feature-list:HAVE_DUNE;
            type  empty;
            description "Use this attribute to enable or disable hardware profile flowcontrol.";
        } // END of flow-control definition.

        leaf micro-bfd  {
            if-feature feature-list:HAVE_CUSTOM1_HW_BFD;
            type  empty;
            description "Use this attribute to enable or disable hardware profile micro-bfd.";
        } // END of micro-bfd definition.

        leaf seamless-bfd  {
            if-feature feature-list:HAVE_CUSTOM1_HW_BFD;
            if-feature feature-list:HAVE_SBFD;
            type  empty;
            description "Use this attribute to enable or disable hardware profile seamless-bfd.";
        } // END of seamless-bfd definition.

        leaf ufis9510-28dc-port-mode  {
            if-feature feature-list:HAVE_DUNE;
            type  ipi-platform-types:platform_ufis9510_28dc_port_mode_type_t;
            default "mode2";
            description "use this attribute to configure or unconfigure hardware profile port
                        modes";
        } // END of ufis9510-28dc-port-mode definition.

        leaf ufis9600-64x-port-mode  {
            if-feature feature-list:HAVE_DUNE;
            type  ipi-platform-types:platform_ufis9600_64x_port_mode_type_t;
            default "mode2";
            description "use this attribute to configure or unconfigure hardware profile port
                        modes";
        } // END of ufis9600-64x-port-mode definition.

        leaf ufis9600-32x-port-mode  {
            if-feature feature-list:HAVE_DUNE;
            type  ipi-platform-types:platform_ufis9600_32x_port_mode_type_t;
            default "mode2";
            description "use this attribute to configure or unconfigure hardware profile port
                        modes";
        } // END of ufis9600-32x-port-mode definition.

        leaf custom-service-queue-profile  {
            if-feature feature-list:HAVE_DUNE;
            type  ipi-platform-types:platform_qos_queue_profile_type_t;
            default "profile1";
            description "Use this attribute to configure or unconfigure hardware profile
                        service-queue profile support.";
        } // END of custom-service-queue-profile definition.

    } // END of hardware-profile-config definition.
    grouping hardware-profile-filters-config {
        description
            "Grouping for hardware-profile filter config objects.";
        leaf egress-ipv6  {
            if-feature feature-list:HAVE_ACL;
            if-feature feature-list:NOT_HAVE_DUNE;
            type  cml-data-types:cml_enable_disable_t;
            description "Use this attribute to enable or disable Egress IPv6 filter groups.
                        Disabling filter groups increases the configurable filter entries.";
        } // END of egress-ipv6 definition.

        leaf egress-dst-ipv6  {
            if-feature feature-list:HAVE_ACL;
            if-feature feature-list:HAVE_CUSTOM3_ACL;
            type  empty;
            description "Use this attribute to enable or disable Egress Dst IPv6 filter groups.
                        Disabling filter groups increases the configurable filter entries.";
        } // END of egress-dst-ipv6 definition.

        leaf egress-src-ipv6  {
            if-feature feature-list:HAVE_ACL;
            if-feature feature-list:HAVE_CUSTOM3_ACL;
            type  empty;
            description "Use this attribute to enable or disable Egress Src IPv6 filter groups.
                        Disabling filter groups increases the configurable filter entries.";
        } // END of egress-src-ipv6 definition.

        leaf egress-ipv6-dnx  {
            if-feature feature-list:HAVE_ACL;
            if-feature feature-list:HAVE_DNX;
            type  cml-data-types:cml_enable_disable_t;
            default "enable";
            description "Use this command to enable or disable egress IPv6 filter groups.
                        Disabling filter groups increases the configurable filter entries.";
        } // END of egress-ipv6-dnx definition.

        leaf ingress-ipv6  {
            if-feature feature-list:HAVE_ACL;
            if-feature feature-list:HAVE_DUNE;
            type  empty;
            description "Use this attribute to enable or disable Ingress IPv6 filter groups.
                        Disabling filter groups increases the configurable filter entries.";
        } // END of ingress-ipv6 definition.

        leaf ingress-ipv6-acl  {
            if-feature feature-list:HAVE_ACL;
            if-feature feature-list:NOT_HAVE_DUNE;
            type  cml-data-types:cml_enable_disable_t;
            description "Use this attribute to enable or disable Ingress IPv6 filter groups.
                        Disabling filter groups increases the configurable filter entries.";
        } // END of ingress-ipv6-acl definition.

        leaf ingress-ipv4  {
            if-feature feature-list:HAVE_ACL;
            if-feature feature-list:NOT_HAVE_DUNE;
            type  cml-data-types:cml_enable_disable_t;
            description "Use this attribute to enable or disable Ingress IPv4 filter groups.
                        Disabling filter groups increases the configurable filter entries.";
        } // END of ingress-ipv4 definition.

        leaf ingress-ipv4-custom2  {
            if-feature feature-list:HAVE_ACL;
            if-feature feature-list:HAVE_DUNE;
            type  empty;
            description "Use this attribute to enable or disable Ingress IPv4 filter groups.
                        Disabling filter groups increases the configurable filter entries.";
        } // END of ingress-ipv4-custom2 definition.

        leaf ingress-ipv4-extended  {
            if-feature feature-list:HAVE_ACL;
            if-feature feature-list:HAVE_DUNE;
            type  empty;
            description "Use this attribute to enable or disable Ingress IPv4 extended filter
                        groups. Disabling filter groups increases the configurable filter
                        entries.";
        } // END of ingress-ipv4-extended definition.

        leaf ingress-ipv4-qos  {
            if-feature feature-list:HAVE_ACL;
            if-feature feature-list:HAVE_DUNE;
            type  empty;
            description "Use this attribute to enable or disable Ingress IPv4 QoS filter
                        groups. Disabling filter groups increases the configurable filter
                        entries.";
        } // END of ingress-ipv4-qos definition.

        leaf ingress-arp  {
            if-feature feature-list:HAVE_ACL;
            type  empty;
            description "Use this attribute to enable or disable Ingress ARP filter groups.";
        } // END of ingress-arp definition.

        leaf ingress-ipv6-qos  {
            if-feature feature-list:HAVE_ACL;
            if-feature feature-list:HAVE_DUNE;
            type  empty;
            description "Use this attribute to enable or disable Ingress IPv6 QoS filter
                        groups. Disabling filter groups increases the configurable filter
                        entries.";
        } // END of ingress-ipv6-qos definition.

        leaf qos  {
            when " not(/profiles/hardware-profile/filters/config/qos-extended) and not(/profiles/hardware-profile/filters/config/qos-policer) ";
            if-feature feature-list:HAVE_ACL;
            if-feature feature-list:HAVE_DUNE;
            type  empty;
            description "Use this attribute to enable or disable QoS filter groups. Disabling
                        filter groups increases the configurable filter entries.";
        } // END of qos definition.

        leaf qos-extended  {
            when " not(/profiles/hardware-profile/filters/config/qos) and not(/profiles/hardware-profile/filters/config/qos-policer) ";
            if-feature feature-list:HAVE_ACL;
            if-feature feature-list:HAVE_DUNE;
            type  empty;
            description "Use this attribute to enable or disable QoS extended filter groups.
                        Disabling filter groups increases the configurable filter entries.";
        } // END of qos-extended definition.

        leaf qos-policer  {
            when " not(/profiles/hardware-profile/filters/config/qos) and not(/profiles/hardware-profile/filters/config/qos-extended) ";
            if-feature feature-list:HAVE_ACL;
            if-feature feature-list:HAVE_DUNE;
            type  empty;
            description "Use this attribute to enable or disable QoS policer filter groups.
                        Disabling filter groups increases the configurable filter entries.";
        } // END of qos-policer definition.

        leaf egress-qos-policer  {
            if-feature feature-list:HAVE_ACL;
            if-feature feature-list:HAVE_DUNE;
            if-feature feature-list:HAVE_DNX;
            type  empty;
            description "Use this attribute to enable or disable Egress QoS policer filter
                        groups. Disabling filter groups increases the configurable filter
                        entries.";
        } // END of egress-qos-policer definition.

        leaf egress-qos-policer-ext  {
            if-feature feature-list:HAVE_ACL;
            if-feature feature-list:HAVE_CUSTOM3_ACL;
            type  empty;
            description "Use this attribute to enable or disable Egress QoS policer filter
                        groups. Disabling filter groups increases the configurable filter
                        entries.";
        } // END of egress-qos-policer-ext definition.

        leaf qos-ipv6  {
            if-feature feature-list:HAVE_ACL;
            if-feature feature-list:HAVE_DUNE;
            type  empty;
            description "Use this attribute to enable or disable QoS filter group for IPv6
                        traffic. Disabling filter groups increases the configurable filter
                        entries.";
        } // END of qos-ipv6 definition.

        leaf egress-ipv4  {
            if-feature feature-list:HAVE_ACL;
            if-feature feature-list:HAVE_DUNE;
            if-feature feature-list:NOT_HAVE_CUSTOM3_ACL;
            type  empty;
            description "Use this attribute to enable or disable Egress IPv4 filter groups.
                        Disabling filter groups increases the configurable filter entries.";
        } // END of egress-ipv4 definition.

        leaf egress-ipv4-dnx  {
            if-feature feature-list:HAVE_ACL;
            if-feature feature-list:HAVE_DUNE;
            if-feature feature-list:HAVE_CUSTOM3_ACL;
            type  empty;
            description "Use this attribute to enable or disable Egress IPv4 filter groups.
                        Disabling filter groups increases the configurable filter entries.";
        } // END of egress-ipv4-dnx definition.

        leaf egress-ipv4-ext  {
            if-feature feature-list:HAVE_ACL;
            if-feature feature-list:HAVE_DNX;
            type  empty;
            description "Use this attribute to enable or disable Egress IPv4 ext filter groups.
                        Disabling filter groups increases the configurable filter entries.";
        } // END of egress-ipv4-ext definition.

        leaf egress-layer2  {
            if-feature feature-list:HAVE_ACL;
            if-feature feature-list:HAVE_DUNE;
            if-feature feature-list:NOT_HAVE_CUSTOM3_ACL;
            type  empty;
            description "Use this attribute to enable or disable Egress L2 filter groups.
                        Disabling filter groups increases the configurable filter entries.";
        } // END of egress-layer2 definition.

        leaf egress-layer2-dnx  {
            if-feature feature-list:HAVE_ACL;
            if-feature feature-list:HAVE_CUSTOM3_ACL;
            type  empty;
            description "Use this attribute to enable or disable Egress L2 filter groups.
                        Disabling filter groups increases the configurable filter entries.";
        } // END of egress-layer2-dnx definition.

        leaf egress-layer2-ext  {
            if-feature feature-list:HAVE_ACL;
            if-feature feature-list:HAVE_DNX;
            type  empty;
            description "Use this attribute to enable or disable Egress L2 ext filter groups.
                        Disabling filter groups increases the configurable filter entries.";
        } // END of egress-layer2-ext definition.

        leaf ingress-layer2  {
            when " not(/profiles/hardware-profile/filters/config/ingress-layer2-extended) ";
            if-feature feature-list:HAVE_ACL;
            if-feature feature-list:HAVE_DUNE;
            type  empty;
            description "Use this attribute to enable or disable Ingress L2 filter groups.
                        Disabling filter groups increases the configurable filter entries.";
        } // END of ingress-layer2 definition.

        leaf ingress-layer2-extended  {
            when " not(/profiles/hardware-profile/filters/config/ingress-layer2) ";
            if-feature feature-list:HAVE_ACL;
            if-feature feature-list:HAVE_DUNE;
            type  empty;
            description "Use this attribute to enable or disable Ingress L2 extended filter
                        groups. Disabling filter groups increases the configurable filter
                        entries.";
        } // END of ingress-layer2-extended definition.

        leaf forwarding-ipv4  {
            if-feature feature-list:HAVE_ACL;
            if-feature feature-list:HAVE_DUNE;
            type  empty;
            description "Use this attribute to enable or disable forwarding-ipv4 filter groups.
                        Disabling filter groups increases the configurable filter entries.";
        } // END of forwarding-ipv4 definition.

        leaf cfm-domain-name-string  {
            if-feature feature-list:HAVE_CFM;
            if-feature feature-list:HAVE_DUNE;
            if-feature feature-list:NOT_HAVE_DNX;
            type  empty;
            description "Use this attribute to enable or disable CFM domain name filter groups.
                        Disabling filter groups increases the configurable filter entries.";
        } // END of cfm-domain-name-string definition.

        leaf twamp-ipv4  {
            if-feature feature-list:HAVE_TWAMP_HW_OFFLOAD;
            if-feature feature-list:HAVE_TWAMP;
            if-feature feature-list:HAVE_DUNE;
            type  empty;
            description "Use this attribute to enable or disable TWAMP IPv4 Forwarding filter
                        groups. Disabling filter groups increases the configurable filter
                        entries.";
        } // END of twamp-ipv4 definition.

        leaf twamp-ipv6  {
            if-feature feature-list:HAVE_TWAMP_HW_OFFLOAD;
            if-feature feature-list:HAVE_TWAMP;
            if-feature feature-list:HAVE_DUNE;
            type  empty;
            description "Use this attribute to enable or disable TWAMP IPv6 Forwarding filter
                        groups. Disabling filter groups increases the configurable filter
                        entries.";
        } // END of twamp-ipv6 definition.

        leaf vxlan-arp-nd  {
            if-feature feature-list:HAVE_VXLAN;
            if-feature feature-list:HAVE_DUNE;
            type  empty;
            description "Use this attribute to enable or disable VxLAN Forwarding filter
                        groups. Disabling filter groups increases the configurable filter
                        entries.";
        } // END of vxlan-arp-nd definition.

        leaf vxlan-multi-homing  {
            if-feature feature-list:HAVE_VXLAN;
            if-feature feature-list:HAVE_DUNE;
            type  empty;
            description "Use this attribute to enable or disable VxLAN Multi Homing Forwarding
                        filter groups. Disabling filter groups increases the configurable
                        filter entries.";
        } // END of vxlan-multi-homing definition.

        leaf evpn-mpls-multi-homing  {
            if-feature feature-list:HAVE_NVO;
            if-feature feature-list:HAVE_MPLS;
            if-feature feature-list:HAVE_DUNE;
            type  empty;
            description "Use this attribute to enable or disable EVPN-MPLS Multi Homing
                        Forwarding filter groups. Disabling filter groups increases the
                        configurable filter entries.";
        } // END of evpn-mpls-multi-homing definition.

        leaf ingress-bfd  {
            if-feature feature-list:HAVE_BFD_HW_OFFLOAD;
            if-feature feature-list:NOT_HAVE_CUSTOM1_HW_BFD;
            type  cml-data-types:cml_enable_disable_t;
            description "Use this attribute to enable or disable Ingress BFD filter groups.
                        Disabling filter groups increases the configurable filter entries.";
        } // END of ingress-bfd definition.

        leaf dhcp-snoop  {
            if-feature feature-list:HAVE_DHCP_SNOOP;
            if-feature feature-list:HAVE_DUNE;
            type  empty;
            description "Use this attribute to enable or disable Dhcp snooping filter groups.
                        Disabling filter groups increases the configurable filter entries.";
        } // END of dhcp-snoop definition.

        leaf dhcp-snoop-ipv6  {
            if-feature feature-list:HAVE_DHCP_SNOOP;
            if-feature feature-list:HAVE_DUNE;
            type  empty;
            description "Use this attribute to enable or disable Dhcp snooping ipv6 filter
                        groups. Disabling filter groups increases the configurable filter
                        entries.";
        } // END of dhcp-snoop-ipv6 definition.

        leaf ipsg  {
            if-feature feature-list:HAVE_DHCP_SNOOP;
            if-feature feature-list:HAVE_DUNE;
            type  empty;
            description "Use this attribute to enable or disable IP Source Guard(IPSG) filter
                        groups. Disabling filter groups increases the configurable filter
                        entries.";
        } // END of ipsg definition.

        leaf ipsg-ipv6  {
            if-feature feature-list:HAVE_DHCP_SNOOP;
            if-feature feature-list:HAVE_DUNE;
            type  empty;
            description "Use this attribute to enable or disable IP Source Guard(IPSG) ipv6
                        filter groups. Disabling filter groups increases the configurable
                        filter entries.";
        } // END of ipsg-ipv6 definition.

    } // END of hardware-profile-filters-config definition.
    grouping hardware-profiles-statistics-config {
        description
            "Grouping for hardware-profile statistics config objects.";
        leaf ingress-acl  {
            if-feature feature-list:HAVE_DUNE;
            if-feature feature-list:NOT_HAVE_DNX;
            type  empty;
            description "Use this attribute to enable or disable Ingress ACL QoS and PBR filter
                        groups. Disabling filter groups increases the configurable filter
                        entries.";
        } // END of ingress-acl definition.

        leaf egress-acl  {
            if-feature feature-list:HAVE_DUNE;
            if-feature feature-list:NOT_HAVE_DNX;
            type  empty;
            description "Use this attribute to enable or disable Egress ACL filter groups.
                        Disabling filter groups increases the configurable filter entries.";
        } // END of egress-acl definition.

        leaf ingress-qos  {
            if-feature feature-list:HAVE_DUNE;
            if-feature feature-list:NOT_HAVE_DNX;
            type  empty;
            description "Use this attribute to enable or disable explicitly for QoS filter
                        groups. Disabling filter groups increases the configurable filter
                        entries.";
        } // END of ingress-qos definition.

        leaf attachment-circuit-logical-if  {
            if-feature feature-list:HAVE_DUNE;
            if-feature feature-list:NOT_HAVE_DNX;
            type  empty;
            description "Use this attribute to enable or disable attachment circuits logical
                        filter groups. Disabling filter groups increases the configurable
                        filter entries.";
        } // END of attachment-circuit-logical-if definition.

        leaf tunnel-logical-if  {
            if-feature feature-list:HAVE_DUNE;
            if-feature feature-list:NOT_HAVE_DNX;
            type  empty;
            description "Use this attribute to enable or disable tunnel logical filter groups.
                        Disabling filter groups increases the configurable filter entries.";
        } // END of tunnel-logical-if definition.

        leaf evpn-mpls-stats  {
            if-feature feature-list:HAVE_NVO;
            if-feature feature-list:HAVE_MPLS;
            if-feature feature-list:HAVE_DUNE;
            if-feature feature-list:NOT_HAVE_DNX;
            type  empty;
            description "Use this attribute to enable or disable hardware statistics for
                        evpn-mpls.";
        } // END of evpn-mpls-stats definition.

        leaf mpls-pseudowire  {
            if-feature feature-list:HAVE_DUNE;
            if-feature feature-list:HAVE_MPLS_STATS;
            if-feature feature-list:NOT_HAVE_DNX;
            type  empty;
            description "Use this attribute to enable or disable MPLS Pseudowire filter groups.
                        Disabling filter groups increases the configurable filter entries.";
        } // END of mpls-pseudowire definition.

        leaf cfm-frame-loss-measurements  {
            if-feature feature-list:HAVE_DUNE;
            if-feature feature-list:HAVE_CFM;
            type  empty;
            description "Use this attribute to enable or disable CFM Loss Measurements filter
                        groups. Disabling filter groups increases the configurable filter
                        entries.";
        } // END of cfm-frame-loss-measurements definition.

        leaf cfm-continuity-check-messages  {
            if-feature feature-list:HAVE_DUNE;
            if-feature feature-list:CCM_HW_OFFLOAD;
            if-feature feature-list:NOT_HAVE_DNX;
            type  empty;
            description "Use this attribute to enable or disable CFM Continuity Check Messages
                        filter groups. Disabling filter groups increases the configurable
                        filter entries.";
        } // END of cfm-continuity-check-messages definition.

        leaf virtual-output-queue-full-color  {
            when " not(/profiles/hardware-profile/statistics/config/virtual-output-queue-forward-drop) ";
            if-feature feature-list:HAVE_DUNE;
            type  empty;
            description "Use this attribute to enable or disable Virtual Output Queue Full
                        Color filter groups. Disabling filter groups increases the
                        configurable filter entries.";
        } // END of virtual-output-queue-full-color definition.

        leaf virtual-output-queue-forward-drop  {
            when " not(/profiles/hardware-profile/statistics/config/virtual-output-queue-full-color) ";
            if-feature feature-list:HAVE_DUNE;
            type  empty;
            description "Use this attribute to enable or disable Virtual Output Queue Forward
                        Drop filter groups. Disabling filter groups increases the configurable
                        filter entries.";
        } // END of virtual-output-queue-forward-drop definition.

    } // END of hardware-profiles-statistics-config definition.
    grouping hardware-tcam-state {
        description
            "Grouping for hardware tcam state objects.";
        leaf warning-threshold-level  {
            type  int32;
            description "Warning TCAM threshold level in percentage. Value of -1 means the
                        field is not applicable.";
        } // END of warning-threshold-level definition.

        leaf critical-alert-threshold-level  {
            type  int32;
            description "Alert TCAM threshold level in percentage. Value of -1 means the field
                        is not applicable.";
        } // END of critical-alert-threshold-level definition.

    } // END of hardware-tcam-state definition.
    grouping hardware-tcam-filter-group-state {
        description
            "Grouping for hardware tcam filter group state objects.";
        leaf group-id  {
            type  uint32;
            description "A unique number corresponding to each TCAM group. This attribute is
                        used solely for defining the key for the TCAM utilization filter
                        groups object list. It's value shouldn't be interpreted.";
        } // END of group-id definition.

        leaf group-name  {
            type  cml-data-types:cml_line_t {
                length "1..1965";
            }
            description "TCAM Utilization filter group name.";
        } // END of group-name definition.

        leaf free-entries  {
            type  int32;
            description "Count of free entries in the TCAM group. Value of -1 means the field
                        is not applicable.";
        } // END of free-entries definition.

        leaf used-entries  {
            type  int32;
            description "Percentage of entries used in the TCAM group.Value of -1 means the
                        field is not applicable.";
        } // END of used-entries definition.

        leaf used-percentage  {
            type  int32;
            description "Percentage of entries used in the TCAM group. Value of -1 means the
                        field is not applicable.";
        } // END of used-percentage definition.

        leaf total-entries  {
            type  int32;
            description "Count of total entries in the TCAM group.Total is summation of
                        dedicated entries and shared entries.Value of -1 means the field is
                        not applicable.";
        } // END of total-entries definition.

        leaf dedicated-entries  {
            type  int32;
            description "Count of total entries dedicated to TCAM group. Dedicated entries are
                        fixed to the TCAM group and are the minimum guaranteed number. Value
                        of -1 means the field is not applicable.";
        } // END of dedicated-entries definition.

        leaf shared-entries  {
            type  int32;
            description "Count of entries which are shared across TCAM groups. Value of -1
                        means the field is not applicable.";
        } // END of shared-entries definition.

    } // END of hardware-tcam-filter-group-state definition.
    grouping platform-kaps-config {
        description
            "Grouping for forwarding-profiles kaps config objects.";
        leaf profile-type  {
            type  ipi-platform-types:platform_kaps_profile_type_t;
            description "forwarding profile for KAPS";
        } // END of profile-type definition.

    } // END of platform-kaps-config definition.
    grouping platform-ext-tcam-config {
        description
            "Grouping for forwarding-profiles external-tcam config objects.";
        leaf profile-type  {
            type  ipi-platform-types:platform_ext_tcam_profile_type_t;
            default "profile-one";
            description "forwarding profile for external TCAM";
        } // END of profile-type definition.

    } // END of platform-ext-tcam-config definition.
    grouping platform-custom-tcam-config {
        description
            "Grouping for forwarding-profiles external-tcam config objects.";
        leaf profile-type  {
            type  ipi-platform-types:platform_tcam_custom_profile_t;
            mandatory true;
            description "forwarding profile for type for custom-TCAM";
        } // END of profile-type definition.

        leaf ipv4-percentage  {
            type  uint8 {
                 range "10..90"  {
                    description "10..90: Supported range 10 - 90";
                 }
            }
            units "%";
            mandatory true;
            description "Use this attribute to set Percentage of entries for ipv4 routes";
        } // END of ipv4-percentage definition.

        leaf ipv6-percentage  {
            type  uint8 {
                 range "10..90"  {
                    description "10..90: Supported range 10 - 90";
                 }
            }
            units "%";
            mandatory true;
            description "Use this attribute to set Percentage of entries for ipv6 routes";
        } // END of ipv6-percentage definition.

    } // END of platform-custom-tcam-config definition.
    grouping platform-kaps-state {
        description
            "Grouping for KAPS Forwarding Profile state objects.";
        leaf profile  {
            type  ipi-platform-types:platform_kaps_forwading_profile_t;
            description "Profile type";
        } // END of profile definition.

        leaf is-active  {
            type  boolean;
            description "Active in hardware";
        } // END of is-active definition.

        leaf public-db-size  {
            type  uint32;
            description "Public-db size";
        } // END of public-db-size definition.

        leaf private-db-size  {
            type  uint32;
            description "Private-db size";
        } // END of private-db-size definition.

    } // END of platform-kaps-state definition.
    grouping platform-elk-tcam-state {
        description
            "Grouping for External TCAM Forwarding Profile state objects.";
        leaf profile  {
            type  ipi-platform-types:platform_elk_tcam_forwading_profile_t;
            description "Profile type";
        } // END of profile definition.

        leaf is-active  {
            type  boolean;
            description "Active in hardware";
        } // END of is-active definition.

        leaf ipv4-db-size  {
            type  uint32;
            description "IPv4 DB size";
        } // END of ipv4-db-size definition.

        leaf ipv6-db-size  {
            type  uint32;
            description "IPv6 DB size";
        } // END of ipv6-db-size definition.

    } // END of platform-elk-tcam-state definition.
    grouping platform-rate-limit-config {
        description
            "Grouping for cpu-queue rate-limit config objects.";
        leaf queue-name  {
            type  ipi-platform-types:platform_cpu_queue_name_t;
            description "This attribute specifies CPU queue name for rate limiting config";
        } // END of queue-name definition.

        leaf rate  {
            type  int32 {
                 range "0..100000"  {
                    description "0..100000:Feature : HAVE_DUNE Supported range 0 - 100000Not Feature :
                            HAVE_DUNE  Supported range 0 - 100000";
                 }
            }
            description "CPU queue Rate";
        } // END of rate definition.

        leaf monitor-status  {
            if-feature feature-list:HAVE_DUNE;
            type  ipi-platform-types:platform_cpu_queue_monitor_t;
            description "monitor cpu queue usage";
        } // END of monitor-status definition.

    } // END of platform-rate-limit-config definition.
    grouping platform-load-balance-config {
        description
            "Grouping for load-balance config objects.";
        leaf enable  {
            type  empty;
            mandatory true;
            description "This Object is set loadBalance";
        } // END of enable definition.

        leaf mpls-label-based  {
            type  empty;
            description "This Object is set for load balancing based on mpls labels";
        } // END of mpls-label-based definition.

    } // END of platform-load-balance-config definition.
    grouping platform-load-balance-l2-config {
        description
            "Grouping for load-balance l2 config objects.";
        leaf dest-mac-based  {
            if-feature feature-list:NOT_HAVE_DNX;
            type  empty;
            description "This Object is set for Destination Mac address based load balancing";
        } // END of dest-mac-based definition.

        leaf src-mac-based  {
            if-feature feature-list:NOT_HAVE_DNX;
            type  empty;
            description "This Object is set for Source Mac address based load balancing";
        } // END of src-mac-based definition.

        leaf ether-type-based  {
            type  empty;
            description "This Object is set for Ether-type based load balancing";
        } // END of ether-type-based definition.

        leaf vlan-based  {
            type  empty;
            description "This Object is set for Vlan based load balancing";
        } // END of vlan-based definition.

    } // END of platform-load-balance-l2-config definition.
    grouping platform-load-balance-ipv4-config {
        description
            "Grouping for load-balance ipv4 config objects.";
        leaf src-ipv4-address-based  {
            if-feature feature-list:NOT_HAVE_DNX;
            type  empty;
            description "This Object is set for Source IPV4 based load balancing";
        } // END of src-ipv4-address-based definition.

        leaf dest-ipv4-address-based  {
            if-feature feature-list:NOT_HAVE_DNX;
            type  empty;
            description "This Object is set for Destination IPV4 based load balancing";
        } // END of dest-ipv4-address-based definition.

        leaf src-l4-port-based  {
            if-feature feature-list:NOT_HAVE_DNX;
            type  empty;
            description "This Object is set for Source L4 port based load balancing";
        } // END of src-l4-port-based definition.

        leaf dest-l4-port-based  {
            if-feature feature-list:NOT_HAVE_DNX;
            type  empty;
            description "This Object is set for Destination L4 port based load balancing";
        } // END of dest-l4-port-based definition.

        leaf protocol-id-based  {
            type  empty;
            description "This Object is set for Protocol Id based load balancing";
        } // END of protocol-id-based definition.

    } // END of platform-load-balance-ipv4-config definition.
    grouping platform-cpu-queue-top {
        description
            "Grouping for platform cpu-queue objects.";
        container cpu-queue {
            if-feature feature-list:HAVE_BROADCOM;
            description
                "This container defines cpu-queue configuration and state information.";
            container rate-limits {
                description
                    "This container defines rate-limits configuration and state
                            information.";

                list rate-limit {
                    key "queue-name";
                    description
                        "The list of rate-limit configuration.";
                    leaf queue-name  {
                        type  leafref {
                            path  "../config/queue-name";
                        }
                        description "This attribute specifies CPU queue name for rate limiting config";
                    } // END of queue-name definition.

                    container config {
                        description
                            "This container defines cpu-queue rate-limit configuration.";
                        uses platform-extended-rate-limit-config;
                        uses platform-rate-limit-config;
                    } // END of config-container definition.
                    container state {
                        config false;
                        description
                            "This container defines cpu-queue rate-limit information Operational
                                    states.";
                        uses platform-extended-rate-limit-config;
                        uses platform-rate-limit-config;
                    } // END of state-container definition.
                } // End of rate-limit-list
            } // END of rate-limits-container definition.
        } // END of cpu-queue-container definition.
    } // END of platform-cpu-queue-top definition.
    grouping platform-load-balance-ipv6-config {
        description
            "Grouping for load-balance ipv6 config objects.";
        leaf src-ipv6-address-based  {
            if-feature feature-list:NOT_HAVE_DNX;
            type  empty;
            description "This Object is set for Source IPV6 based load balancing";
        } // END of src-ipv6-address-based definition.

        leaf dest-ipv6-address-based  {
            if-feature feature-list:NOT_HAVE_DNX;
            type  empty;
            description "This Object is set for Destination IPV6 based load balancing";
        } // END of dest-ipv6-address-based definition.

        leaf src-l4-port-based  {
            if-feature feature-list:NOT_HAVE_DNX;
            type  empty;
            description "This Object is set for Source L4 port based load balancing";
        } // END of src-l4-port-based definition.

        leaf dest-l4-port-based  {
            if-feature feature-list:NOT_HAVE_DNX;
            type  empty;
            description "This Object is set for Destination L4 port based load balancing";
        } // END of dest-l4-port-based definition.

        leaf next-header-based  {
            type  empty;
            description "This Object is set for Next Header Field for IPV6";
        } // END of next-header-based definition.

    } // END of platform-load-balance-ipv6-config definition.

    grouping  profiles-grouping {
    description
        "Top level container for platform profiles, including configuration and
                state data";
    container profiles {
        if-feature feature-list:HAVE_BROADCOM;
        if-feature feature-list:HAVE_CMMD;
        description
            "Top level container for platform profiles, including configuration and
                    state data";
        container hardware-profile {
            description
                "This container defines hardware-profile configuration and state
                        information.";
            container config {
                description
                    "This container defines hardware-profile configuration.";
                uses hardware-profile-config;
            } // END of config-container definition.
            container state {
                config false;
                description
                    "This container defines hardware-profile Operational states.";
                uses hardware-profile-config;
            } // END of state-container definition.
            container filters {
                description
                    "This container defines hardware-profile filter configuration and state
                            information.";
                container config {
                    description
                        "This container defines hardware-profile filter configuration.";
                    uses hardware-profile-filters-config;
                } // END of config-container definition.
                container state {
                    config false;
                    description
                        "This container defines hardware-profile filter Operational states.";
                    uses hardware-profile-filters-config;
                } // END of state-container definition.
                container tcam-utilization {
                    if-feature feature-list:HAVE_ACL;
                    config false;
                    description
                        "This container defines TCAM Utilization information.";
                    container state {
                        config false;
                        description
                            "This container defines TCAM Utilization information Operational
                                    states.";
                        uses hardware-tcam-state;
                    } // END of state-container definition.
                    container filter-groups {
                        config false;
                        description
                            "This container defines TCAM Utilization filter-groups information.";

                        list filter-group {
                            key "group-id";
                            config false;
                            description
                                "The list of named filter-group.";
                            leaf group-id  {
                                type  leafref {
                                    path  "../state/group-id";
                                }
                                description "A unique number corresponding to each TCAM group. This attribute is
                                            used solely for defining the key for the TCAM utilization filter
                                            groups object list. It's value shouldn't be interpreted.";
                            } // END of group-id definition.

                            container state {
                                config false;
                                description
                                    "This container defines filter-group information Operational states.";
                                uses hardware-tcam-filter-group-state;
                            } // END of state-container definition.
                        } // End of filter-group-list
                    } // END of filter-groups-container definition.
                } // END of tcam-utilization-container definition.
            } // END of filters-container definition.
            container statistics {
                description
                    "This container defines hardware-profile statistics configuration and
                            state information.";
                container config {
                    description
                        "This container defines hardware-profile statistics configuration.";
                    uses hardware-profiles-statistics-config;
                } // END of config-container definition.
                container state {
                    config false;
                    description
                        "This container defines hardware-profile statistics Operational states.";
                    uses hardware-profiles-statistics-config;
                } // END of state-container definition.
            } // END of statistics-container definition.
        } // END of hardware-profile-container definition.
        container forwarding-profiles {
            description
                "This container defines forwarding-profiles configuration and state
                        information.";
            container config {
                if-feature feature-list:HAVE_BCM_UFT;
                if-feature feature-list:NOT_HAVE_DUNE;
                description
                    "This container defines forwarding-profiles configuration.";
                uses platform-extended-forwarding-profile-config;
            } // END of config-container definition.
            container state {
                if-feature feature-list:HAVE_BCM_UFT;
                if-feature feature-list:NOT_HAVE_DUNE;
                config false;
                description
                    "This container defines forwarding-profiles operational states.";
                uses platform-extended-forwarding-profile-config;
            } // END of state-container definition.
            container kaps {
                if-feature feature-list:HAVE_DUNE;
                if-feature feature-list:HAVE_BCM_UFT;
                if-feature feature-list:NOT_HAVE_DNX;
                description
                    "This container defines forwarding-profiles KAPS configuration and
                            state information.";
                container config {
                    description
                        "This container defines forwarding-profiles KAPS configuration.";
                    uses platform-kaps-config;
                } // END of config-container definition.
                container state {
                    config false;
                    description
                        "This container definesforwarding-profiles KAPS Operational states.";
                    uses platform-kaps-config;
                } // END of state-container definition.
            } // END of kaps-container definition.
            container external-tcam {
                if-feature feature-list:HAVE_DUNE;
                if-feature feature-list:HAVE_BCM_UFT;
                if-feature feature-list:NOT_HAVE_DNX;
                description
                    "This container defines forwarding-profiles external-TCAM configuration
                            and state information.";
                container config {
                    description
                        "This container defines forwarding-profiles external-TCAM
                                configuration.";
                    uses platform-ext-tcam-config;
                } // END of config-container definition.
                container state {
                    config false;
                    description
                        "This container definesforwarding-profiles external-TCAM Operational
                                states.";
                    uses platform-ext-tcam-config;
                } // END of state-container definition.
            } // END of external-tcam-container definition.
            container custom-tcam {
                if-feature feature-list:HAVE_DUNE;
                if-feature feature-list:HAVE_BCM_UFT;
                if-feature feature-list:NOT_HAVE_DNX;
                description
                    "This container defines forwarding-profiles custom-TCAM configuration
                            and state information.";
                container config {
                    presence "forwarding-profiles custom-tcam configuration";
                    description
                        "This container defines forwarding-profiles custom-TCAM configuration.";
                    uses platform-custom-tcam-config;
                } // END of config-container definition.
                container state {
                    config false;
                    description
                        "This container defines forwarding-profiles custom-TCAM Operational
                                states.";
                    uses platform-custom-tcam-config;
                } // END of state-container definition.
            } // END of custom-tcam-container definition.
            container table-limit {
                if-feature feature-list:HAVE_BCM_UFT;
                config false;
                description
                    "This container defines profile table maximum supported values state
                            information.";

                list kaps {
                    if-feature feature-list:HAVE_DUNE;
                    key "profile";
                    config false;
                    description
                        "The list of forwarding-profiles KAPS.";
                    leaf profile  {
                        type  leafref {
                            path  "../state/profile";
                        }
                        description "Forwarding Profile KAPS Profile type.";
                    } // END of profile definition.

                    container state {
                        config false;
                        description
                            "This container defines KAPS information Operational states.";
                        uses platform-kaps-state;
                    } // END of state-container definition.
                } // End of kaps-list

                list external-tcam {
                    if-feature feature-list:HAVE_DUNE;
                    if-feature feature-list:HAVE_ELK_TCAM;
                    key "profile";
                    config false;
                    description
                        "The list of forwarding-profiles external-TCAM.";
                    leaf profile  {
                        type  leafref {
                            path  "../state/profile";
                        }
                        description "Forwarding Profile External TCAM Profile type.";
                    } // END of profile definition.

                    container state {
                        config false;
                        description
                            "This container defines external-TCAM information Operational states.";
                        uses platform-elk-tcam-state;
                    } // END of state-container definition.
                } // End of external-tcam-list
                uses state-grouping;
                uses table-sizes-grouping;
            } // END of table-limit-container definition.
            uses mdb-grouping;
            uses custom-profile-grouping;
        } // END of forwarding-profiles-container definition.
    } // END of profiles-container definition.
    } // END of profiles-grouping definition.

    grouping  hardware-grouping {
    description
        "Top level container for hardware, including configuration and state
                data";
    container hardware {
        if-feature feature-list:HAVE_BROADCOM;
        if-feature feature-list:HAVE_CMMD;
        description
            "Top level container for hardware, including configuration and state
                    data";
        container load-balance {
            if-feature feature-list:HAVE_BROADCOM;
            description
                "This container defines hardware load-balance configuration and state
                        information.";
            container config {
                presence "hardware load-balance configuration";
                description
                    "This container defines hardware load-balance configuration.";
                uses platform-extended-load-balance-config;
                uses platform-load-balance-config;
            } // END of config-container definition.
            container state {
                config false;
                description
                    "This container defines hardware load-balance Operational states.";
                uses platform-extended-load-balance-config;
                uses platform-load-balance-config;
            } // END of state-container definition.
            container l2 {
                when " /hardware/load-balance/config/enable ";
                if-feature feature-list:HAVE_L2;
                description
                    "This container defines load-balance l2 configuration and state
                            information.";
                container config {
                    description
                        "This container defines load-balance l2 configuration.";
                    uses platform-extended-load-balance-l2-config;
                    uses platform-load-balance-l2-config;
                } // END of config-container definition.
                container state {
                    config false;
                    description
                        "This container defines load-balance l2 Operational states.";
                    uses platform-extended-load-balance-l2-config;
                    uses platform-load-balance-l2-config;
                } // END of state-container definition.
                uses inner-l2-grouping;
            } // END of l2-container definition.
            container ipv4 {
                when " /hardware/load-balance/config/enable ";
                if-feature feature-list:HAVE_L3;
                description
                    "This container defines load-balance ipv4 configuration and state
                            information.";
                container config {
                    description
                        "This container defines load-balance ipv4 configuration.";
                    uses platform-extended-load-balance-ipv4-config;
                    uses platform-load-balance-ipv4-config;
                } // END of config-container definition.
                container state {
                    config false;
                    description
                        "This container defines load-balance ipv4 Operational states.";
                    uses platform-extended-load-balance-ipv4-config;
                    uses platform-load-balance-ipv4-config;
                } // END of state-container definition.
                uses inner-ipv4-grouping;
            } // END of ipv4-container definition.
            container ipv6 {
                when " /hardware/load-balance/config/enable ";
                if-feature feature-list:HAVE_L3;
                description
                    "This container defines load-balance ipv6 configuration and state
                            information.";
                container config {
                    description
                        "This container defines load-balance ipv6 configuration.";
                    uses platform-extended-load-balance-ipv6-config;
                    uses platform-load-balance-ipv6-config;
                } // END of config-container definition.
                container state {
                    config false;
                    description
                        "This container defines load-balance ipv6 Operational states.";
                    uses platform-extended-load-balance-ipv6-config;
                    uses platform-load-balance-ipv6-config;
                } // END of state-container definition.
            } // END of ipv6-container definition.
            uses tunnel-grouping;
            uses vxlan-grouping;
            uses mpls-ler-grouping;
            uses l4-port-grouping;
            uses port-channel-grouping;
        } // END of load-balance-container definition.
        container dram-tune {
            if-feature feature-list:HAVE_BROADCOM;
            config false;
            description
                "This container defines dram-tuning-profiles information.";
            container state {
                config false;
                description
                    "This container defines operational data for dram-tune";
                leaf dram-tune-status  {
                    if-feature feature-list:HAVE_BROADCOM;
                    type  int32;
                    default "0";
                    description "Use this attribute to configure or unconfigure hardware profile
                                service-queue profile support.";
                } // END of dram-tune-status definition.

            } // END of state-container definition.
        } // END of dram-tune-container definition.
        uses platform-cpu-queue-top;
        uses mac-ageing-grouping;
        uses platform-grouping;
        uses cpu-control-grouping;
    } // END of hardware-container definition.
    } // END of hardware-grouping definition.


}
