/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-ceragon.yang
*
*/

submodule ipi-platform-ceragon {

    yang-version 1.1;

    belongs-to  ipi-platform { prefix ipi-platform; }

    import feature-list {
        prefix feature-list;
        revision-date 2023-02-21;
    }

    import ipi-platform-types {
        prefix ipi-platform-types;
        revision-date 2022-06-01;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for ceragon cpld components in platform
                datamodel";


    revision "2022-06-01" {
        description "Updated the yang file with feature";
        reference " 0.2.0.";
    }

    revision "2022-03-08" {
        description "Initial version for Ceragon board CPLD attributes and updated PoE Port state runtime attributes";
        reference " 0.1.0.";
    }

    grouping poe-state {
        description
            "Per PoE port current state";
        leaf port-index  {
            type  uint8;
            description "PoE port index";
        } // END of port-index definition.

        leaf port-name  {
            type  string {
                length "1..1965";
            }
            description "The PoE Port name";
        } // END of port-name definition.

        leaf port-state  {
            type  ipi-platform-types:cmm_poe_port_status_t;
            description "PoE Port state";
        } // END of port-state definition.

    } // END of poe-state definition.
    grouping cpld-attr-state {
        description
            "cpldCMLSEPattrCMLSEPstate";
        leaf usb-over-current-status  {
            type  uint8;
            description "USB Over Current Status";
        } // END of usb-over-current-status definition.

        leaf loss-of-input-clock-status  {
            type  uint8;
            description "CLU Input Clock loss Status";
        } // END of loss-of-input-clock-status definition.

    } // END of cpld-attr-state definition.

    grouping  ceragon-grouping {
    description
        "Container for Ceragon components";
    container ceragon {
        if-feature feature-list:HAVE_CMMD;
        config false;
        description
            "Container for Ceragon components";
        container cpld-attr {
            config false;
            description
                "Ceragon CPLD IO state Update notifications";
            container state {
                config false;
                description
                    "Ceragon CPLD IO state Update notifications";
                uses cpld-attr-state;
            } // END of state-container definition.
        } // END of cpld-attr-container definition.
        container poe {
            config false;
            description
                "Container for PoE component";
            container state {
                config false;
                description
                    "Operational state data for PoE component";
                uses poe-state;
            } // END of state-container definition.
        } // END of poe-container definition.
    } // END of ceragon-container definition.
    } // END of ceragon-grouping definition.


}
