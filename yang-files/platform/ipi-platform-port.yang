/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-port.yang
*
*/

module ipi-platform-port {

    yang-version 1.1;

    namespace   "http://www.ipinfusion.com/yang/ocnos/ipi-platform-port";

    prefix "ipi-platform-port";

    import ipi-platform {
        prefix ipi-platform;
        revision-date 2022-11-30;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for port component in platform datamodel";


    revision "2022-06-01" {
        description "Updated the yang file with feature";
        reference " 0.3.0.";
    }

    revision "2021-09-03" {
        description "Update descriptions of attribute";
        reference " 0.2.0.";
    }

    revision "2021-06-24" {
        description "Initial revision";
        reference " 0.1.0.";
    }


    grouping  port-grouping {
    description
        "Data for physical port components";
    container port {
        if-feature feature-list:HAVE_CMMD;
        config false;
        description
            "Data for physical port components";
    } // END of port-container definition.
    } // END of port-grouping definition.

    augment /ipi-platform:components/ipi-platform:component {
        if-feature feature-list:HAVE_CMMD;
        description
            "Data for physical port components";
        uses port-grouping;
    }


}
