/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-storage.yang
*
*/

submodule ipi-platform-storage {

    yang-version 1.1;

    belongs-to  ipi-platform { prefix ipi-platform; }

    import feature-list {
        prefix feature-list;
        revision-date 2023-02-21;
    }

    import ipi-platform-types {
        prefix ipi-platform-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "This module defines a schema for storage components in platform
                datamodel";


    revision "2022-06-01" {
        description "Updated the yang file with feature";
        reference " 0.5.4.";
    }

    revision "2022-01-26" {
        description "Moved disk activity monitoring state attributes to a separate container. Also changed some attribute names";
        reference " 0.5.3.";
    }

    revision "2021-09-03" {
        description "Update descriptions of attribute";
        reference " 0.5.2.";
    }

    revision "2021-08-05" {
        description "New notifications added for smart harddisk";
        reference " 0.5.1.";
    }

    revision "2021-06-24" {
        description "New attributes added for harddisk";
        reference " 0.5.0.";
    }

    revision "2021-05-31" {
        description "New attributes added for harddisk filesystem mount-points";
        reference " 0.4.0.";
    }

    revision "2021-03-18" {
        description "Removed pattern from string attributes";
        reference " 0.3.0.";
    }

    revision "2020-12-15" {
        description "Change to have data-types in lower case instead of camel case";
        reference " 0.2.0.";
    }

    revision "2018-06-21" {
        description "Initial Version";
        reference " 0.1.0.";
    }

    grouping storage-mounted-filesystem-state {
        description
            "storageCMLSEPmountedCMLSEPfilesystemCMLSEPstate";
        leaf mount-point  {
            type  string {
                length "1..1965";
            }
            description "Path of the mounted filesystem.";
        } // END of mount-point definition.

        leaf total  {
            type  uint64;
            units "MB";
            description "Total memory of the mounted filesystem.";
        } // END of total definition.

        leaf used  {
            type  uint64;
            units "MB";
            description "Used memory of the mounted filesystem.";
        } // END of used definition.

        leaf free  {
            type  uint64;
            units "MB";
            description "Free memory of the mounted filesystem.";
        } // END of free definition.

        leaf usage  {
            type  uint8;
            units "%";
            description "Mounted filesystem usage in %.";
        } // END of usage definition.

    } // END of storage-mounted-filesystem-state definition.
    grouping storage-mounted-filesystem-top {
        description
            "storageCMLSEPmountedCMLSEPfilesystemCMLSEPtop";

        list mounted-filesystem {
            key "mount-point";
            config false;
            description
                "List to store operational data related to mounted filesystems";
            leaf mount-point  {
                type  leafref {
                    path  "../state/mount-point";
                }
                description "A unique value for each mounted filesystem.";
            } // END of mount-point definition.

            container state {
                config false;
                description
                    "Operational state data for mounted filesystem";
                uses storage-mounted-filesystem-state;
            } // END of state-container definition.
        } // End of mounted-filesystem-list
    } // END of storage-mounted-filesystem-top definition.
    grouping storage-state {
        description
            "Operational state data for storage components";
        leaf serial-number  {
            type  string {
                length "1..1965";
            }
            description "Hard disk's serial number.";
        } // END of serial-number definition.

        leaf model-number  {
            type  string {
                length "1..1965";
            }
            description "Hard disk's model number";
        } // END of model-number definition.

        leaf firmware-revision  {
            type  string {
                length "1..1965";
            }
            description "Hard disk's firmware revision";
        } // END of firmware-revision definition.

        leaf cylinder-count  {
            type  uint16;
            description "Hard disk's cylinder count";
        } // END of cylinder-count definition.

        leaf head-count  {
            type  uint16;
            description "Hard disk's head count.";
        } // END of head-count definition.

        leaf sector-count  {
            type  uint32;
            description "Hard disk's sector count.";
        } // END of sector-count definition.

        leaf unformatted-bytes-or-track  {
            type  uint16;
            description "Hard disk's unformatted bytes or track.";
        } // END of unformatted-bytes-or-track definition.

        leaf unformatted-bytes-or-sector  {
            type  uint16;
            description "Hard disk's unformatted bytes or sector.";
        } // END of unformatted-bytes-or-sector definition.

        leaf revision-number  {
            type  string {
                length "1..1965";
            }
            description "Hard disk's Revision number. Blank indicates unavailable";
        } // END of revision-number definition.

        leaf total-memory  {
            type  uint64;
            description "Total memory of the Hard storage.";
        } // END of total-memory definition.

        leaf used-memory  {
            type  uint64;
            description "Used memory of the Hard storage.";
        } // END of used-memory definition.

        leaf free-memory  {
            type  uint64;
            description "Free memory of the Hard storage.";
        } // END of free-memory definition.

        leaf usage-critical-threshold  {
            type  int32;
            units "%";
            description "Hard disk's usage threshold %  for critical level.";
        } // END of usage-critical-threshold definition.

        leaf usage-alert-threshold  {
            type  int32;
            units "%";
            description "Hard disk's usage threshold %  for Alert Level.";
        } // END of usage-alert-threshold definition.

        leaf remaining-life  {
            type  int32;
            units "%";
            description "Hard disk's Remain life % Values.";
        } // END of remaining-life definition.

        leaf remain-life-critical-threshold  {
            type  int32;
            units "%";
            description "Hard disk's Remain Life threshold % for Critical Level.";
        } // END of remain-life-critical-threshold definition.

        leaf remain-life-alert-threshold  {
            type  int32;
            units "%";
            description "Hard disk's Remain Life threshold % for Alert Level.";
        } // END of remain-life-alert-threshold definition.

        leaf available-reserved-space  {
            type  int32;
            units "%";
            description "Hard disk's Available Reserved Space % values";
        } // END of available-reserved-space definition.

        leaf available-reserved-space-critical-threshold  {
            type  int32;
            units "%";
            description "Hard disk's Available Reserved Space threshold % values for critical
                        Level.";
        } // END of available-reserved-space-critical-threshold definition.

        leaf available-reserved-space-alert-threshold  {
            type  int32;
            units "%";
            description "Hard disk's Available Reserved Space threshold % values for Alert
                        Level.";
        } // END of available-reserved-space-alert-threshold definition.

        leaf reallocated-sector-count  {
            type  int32;
            units "sectors";
            description "Hard disk's Reallocated Sectors Count values.";
        } // END of reallocated-sector-count definition.

        leaf uncorrectable-sector-count  {
            type  int32;
            units "sectors";
            description "Hard disk's Uncorrectable Sectors Count.";
        } // END of uncorrectable-sector-count definition.

        leaf manufacturer-id  {
            type  string {
                length "1..1965";
            }
            description "Hard disk's manufacturer identification defined by JEDEC.";
        } // END of manufacturer-id definition.

        leaf manufacture-date  {
            type  string {
                length "1..1965";
            }
            description "Hard disk's manufacture date.";
        } // END of manufacture-date definition.

        leaf device-type  {
            type  string {
                length "1..1965";
            }
            description "Hard disk's type. Removable or Embedded.";
        } // END of device-type definition.

        leaf cache-size  {
            type  uint64;
            description "Hard disk's cache memory size.";
        } // END of cache-size definition.

        leaf storage-status  {
            type  ipi-platform-types:cml_cmm_storage_status_t;
            description "Hard disk's eol status.";
        } // END of storage-status definition.

    } // END of storage-state definition.
    grouping harddisk-monitoring-state-attributes {
        description
            "Operational state attributes for hard disk monitoring";
        leaf interval  {
            type  int32;
            units "seconds";
            description "Hard disk's activity monitoring interval in seconds.";
        } // END of interval definition.

        leaf read-average  {
            type  int32;
            units "KBps";
            description "Hard disk's average read activity in KBps.";
        } // END of read-average definition.

        leaf write-average  {
            type  int32;
            units "KBps";
            description "Hard disk's average write activity in KBps.";
        } // END of write-average definition.

        leaf read-current  {
            type  int32;
            units "KBps";
            description "Hard disk's current read activity in KBps.";
        } // END of read-current definition.

        leaf write-current  {
            type  int32;
            units "KBps";
            description "Hard disk's current write activity in KBps.";
        } // END of write-current definition.

        leaf read-threshold  {
            type  int32;
            units "KBps";
            description "Hard disk's read activity threshold in KBps.";
        } // END of read-threshold definition.

        leaf write-threshold  {
            type  int32;
            units "KBps";
            description "Hard disk's write activity threshold in KBps.";
        } // END of write-threshold definition.

    } // END of harddisk-monitoring-state-attributes definition.

    grouping  storage-grouping {
    description
        "Container for storage component";
    container storage {
        if-feature feature-list:HAVE_CMMD;
        config false;
        description
            "Container for storage component";
        container state {
            config false;
            description
                "Operational state data for storage component";
            uses storage-state;
        } // END of state-container definition.
        container harddisk-monitoring {
            config false;
            description
                "Container for hard disk monitoring state information";
            container state {
                config false;
                description
                    "Operational state data for hard disk monitoring";
                uses harddisk-monitoring-state-attributes;
            } // END of state-container definition.
        } // END of harddisk-monitoring-container definition.
        container mounted-filesystems {
            config false;
            description
                "Container for mounted filesystem state information";
            uses storage-mounted-filesystem-top;
        } // END of mounted-filesystems-container definition.
    } // END of storage-container definition.
    } // END of storage-grouping definition.


}
