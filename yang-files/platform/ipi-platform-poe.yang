/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-poe.yang
*
*/

submodule ipi-platform-poe {

    yang-version 1.1;

    belongs-to  ipi-platform { prefix ipi-platform; }

    import ipi-platform-types {
        prefix ipi-platform-types;
        revision-date 2022-02-17;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for PoE components in platform datamodel";


    revision "2021-12-20" {
        description "Initial version for PoE Port state runtime attributes";
        reference " 0.1.0.";
    }

    grouping poe-state {
        description
            "Per PoE port current state";
        leaf port-index  {
            type  uint8;
            description "PoE port index";
        } // END of port-index definition.

        leaf port-name  {
            type  string {
                length "1..1965";
            }
            description "The PoE Port name";
        } // END of port-name definition.

        leaf port-state  {
            type  ipi-platform-types:cmm_poe_port_status_t;
            description "PoE Port state";
        } // END of port-state definition.

    } // END of poe-state definition.

    grouping  poe-grouping {
    description
        "Container for PoE component";
    container poe {
        config false;
        description
            "Container for PoE component";
        container state {
            config false;
            description
                "Operational state data for PoE component";
            uses poe-state;
        } // END of state-container definition.
    } // END of poe-container definition.
    } // END of poe-grouping definition.


}
