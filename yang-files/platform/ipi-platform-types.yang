/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-types.yang
*
*/

module ipi-platform-types {

    yang-version 1.1;

    namespace   "http://www.ipinfusion.com/yang/ocnos/ipi-platform-types";

    prefix "ipi-platform-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-platform-types";


    revision "2022-06-01" {
        description "Updated the yang file with feature";
        reference " 0.10.5.";
    }

    revision "2022-05-02" {
        description "Added new datatype port mode config types for UFIS9600-64X / UFIS9600-32X mode";
        reference " 0.10.4.";
    }

    revision "2022-03-08" {
        description "Replace 'poe' by 'vendor-specific' in CMM_COMPONENT_TYPE_T datatype";
        reference " 0.10.3.";
    }

    revision "2022-02-17" {
        description "Removed invalid options from PLATFORM_FORWARDING_PROFILE_T";
        reference " 0.10.2.";
    }

    revision "2022-02-01" {
        description "Fixed PLATFORM_CPU_QUEUE_NAME_T mpls helpstring";
        reference " 0.10.1.";
    }

    revision "2022-01-06" {
        description "Added new datatype PLATFORM_PORT_CONFIG_TYPE_T";
        reference " 0.10.0.";
    }

    revision "2021-12-20" {
        description "Add 'poe' element to CMM_COMPONENT_TYPE_T datatype. Added CMM_POE_PORT_STATUS_T datatype.";
        reference " 0.9.0.";
    }

    revision "2021-12-10" {
        description "Add PLATFORM_SYSTEM_STATUS_TYPE_T datatype";
        reference " 0.8.0.";
    }

    revision "2021-11-22" {
        description "Added new datatypes for platform restructuring phase 2";
        reference " 0.7.0.";
    }

    revision "2021-09-03" {
        description "Update descriptions of attribute";
        reference " 0.6.0.";
    }

    revision "2021-07-19" {
        description "Added new datatypes for platform forwarding profiles and CPU queues.";
        reference " 0.5.0.";
    }

    revision "2021-06-24" {
        description "Added optical-channel to component type.";
        reference " 0.4.0.";
    }

    revision "2021-01-25" {
        description "Added new datatype for power-rail status. Fixed CMM_COMPONENT_TYPE_T:chassis typo and added fru, linecard, and port types.";
        reference " 0.3.0.";
    }

    revision "2020-12-15" {
        description "Change to have data-types in lower case instead of camel case";
        reference " 0.2.0.";
    }

    revision "2018-06-21" {
        description "Initial Version";
        reference " 0.1.0.";
    }



    typedef  cmm_component_type_t {
        type enumeration {
            enum NA {
                value 0;
                description "Not applicable";
            }
            enum software {
                value 1;
                description "software-related components in a managed device";
            }
            enum chassis {
                value 2;
                description "Chassis component, typically with multiple slots / shelves";
            }
            enum backplane {
                value 3;
                description "Backplane component for aggregating traffic, typically contained in a chassis component";
            }
            enum fabric {
                value 4;
                description "Interconnect between ingress and egress ports on the device (e.g., a crossbar switch).";
            }
            enum power-supply {
                value 5;
                description "Component that is supplying power to the device";
            }
            enum power-rail {
                value 6;
                description "Power rail component";
            }
            enum fan {
                value 7;
                description "Cooling fan, or could be some other heat-reduction component";
            }
            enum sensor {
                value 8;
                description "Physical sensor, e.g., a temperature sensor in a chassis";
            }
            enum fan-tray {
                value 9;
                description "Fan tray";
            }
            enum transceiver {
                value 10;
                description "Pluggable module present in a port";
            }
            enum cpu {
                value 11;
                description "Processing unit, e.g., a management processor";
            }
            enum storage {
                value 12;
                description "A storage subsystem on the device (disk, SSD, etc.)";
            }
            enum integrated-circuit {
                value 13;
                description "A special purpose processing unit, typically for traffic           switching/forwarding (e.g., switching ASIC, NPU, forwarding           chip, etc.)";
            }
            enum ram {
                value 14;
                description "RAM unit";
            }
            enum ptp-clock {
                value 15;
                description "Ptp-clock unit";
            }
            enum fru {
                value 16;
                description "Field Replaceable Unit";
            }
            enum linecard {
                value 17;
                description "Linecard component, typically inserted into a chassis slot";
            }
            enum port {
                value 18;
                description "Physical port, e.g., for attaching pluggables and networking cables";
            }
            enum optical-channel {
                value 19;
                description "Optical channels act as carriers for transport traffic           directed over a line system.  They are represented as           physical components in the physical inventory model";
            }
            enum vendor-specific {
                value 20;
                description "Vendor Specific components";
            }
        }
        description "type definition for CMM_COMPONENT_TYPE_T";
    }

    typedef  cmm_bmc_event_type_t {
        type enumeration {
            enum Deasserted {
                value 1;
                description "Deasserted event";
            }
            enum Asserted {
                value 2;
                description "Asserted event";
            }
        }
        description "type definition for CMM_BMC_EVENT_TYPE_T";
    }

    typedef  cmm_component_oper_status_t {
        type enumeration {
            enum NA {
                value 0;
                description "Not Applicable";
            }
            enum active {
                value 1;
                description "Component is enabled and active (i.e., up)";
            }
            enum inactive {
                value 2;
                description "Component is enabled but inactive (i.e., down)";
            }
            enum disabled {
                value 3;
                description "Component is administratively disabled.";
            }
        }
        description "type definition for CMM_COMPONENT_OPER_STATUS_T";
    }

    typedef  cmm_bmc_value_t {
        type union {
            type decimal64 {

             fraction-digits 6;
            }
            type string {

            }
        }
        description "type definition for CMM_BMC_VALUE_T";
    }

    typedef  cmm_monitor_state {
        type enumeration {
            enum disable {
                value 1;
                description "Disable";
            }
            enum enable {
                value 2;
                description "Enable";
            }
        }
        description "type definition for CMM_MONITOR_STATE";
    }

    typedef  cmm_videopiu_state {
        type enumeration {
            enum disable {
                value 0;
                description "Disable";
            }
            enum enable {
                value 1;
                description "Enable";
            }
        }
        description "type definition for CMM_VIDEOPIU_STATE";
    }

    typedef  cmm_raon_aodu_state {
        type enumeration {
            enum disable {
                value 0;
                description "Disable";
            }
            enum enable {
                value 1;
                description "Enable";
            }
        }
        description "type definition for CMM_RAON_AODU_STATE";
    }

    typedef  cmm_gps_monitor_type_t {
        type enumeration {
            enum stop {
                value 0;
                description "stop monitoring";
            }
            enum start {
                value 1;
                description "start monitoring";
            }
        }
        description "type definition for CMM_GPS_MONITOR_TYPE_T";
    }

    typedef  cml_wavelength_t {
        type union {
            type cml_wavelength_channel_t {

            }
            type cml_wavelength_update_t {

            }
        }
        description "type definition for CML_WAVELENGTH_T";
    }

    typedef  cml_wavelength_channel_t {
        type uint32 {
             range 1..96;
        }
        description "type definition for CML_WAVELENGTH_CHANNEL_T";
    }

    typedef  cml_wavelength_update_t {
        type uint32 {
             range 1528773..1566723;
        }
        description "type definition for CML_WAVELENGTH_UPDATE_T";
    }

    typedef  cml_cmm_power_rail_t {
        type enumeration {
            enum unknown {
                value 0;
                description "Power rail status unknown";
            }
            enum good {
                value 1;
                description "Power rail good";
            }
            enum fail {
                value 2;
                description "Power rail fail";
            }
        }
        description "type definition for CML_CMM_POWER_RAIL_T";
    }

    typedef  platform_ufis9510_28dc_port_mode_type_t {
        type enumeration {
            enum mode1 {
                value 1;
                description "2X400G + 2X100G + 24X25G (Default)";
            }
            enum mode2 {
                value 2;
                description "2X100G (port-0 and port-1 as 100G) + 2X100G + 24X25G";
            }
            enum mode3 {
                value 3;
                description "1X400G (port-0 as 400G) + 1X100G (port-1 as 100G) + 2X100G + 24X25G";
            }
        }
        description "type definition for PLATFORM_UFIS9510_28DC_PORT_MODE_TYPE_T";
    }

    typedef  platform_ufis9600_64x_port_mode_type_t {
        type enumeration {
            enum mode1 {
                value 1;
                description "64X100G (Default)";
            }
            enum mode2 {
                value 2;
                description "4X1G  + 63X100G (ce0 breakout to 4X1G)";
            }
            enum mode3 {
                value 3;
                description "4X10G + 63X100G (ce0 breakout to 4X10G)";
            }
            enum mode4 {
                value 4;
                description "4X25G + 63X100G (ce0 breakout to 4X25G)";
            }
        }
        description "type definition for PLATFORM_UFIS9600_64X_PORT_MODE_TYPE_T";
    }

    typedef  platform_ufis9600_32x_port_mode_type_t {
        type enumeration {
            enum mode1 {
                value 1;
                description "32X100G (Default)";
            }
            enum mode2 {
                value 2;
                description "4X1G  + 31X100G (ce0 breakout to 4X1G)";
            }
            enum mode3 {
                value 3;
                description "4X10G + 31X100G (ce0 breakout to 4X10G)";
            }
            enum mode4 {
                value 4;
                description "4X25G + 31X100G (ce0 breakout to 4X25G)";
            }
        }
        description "type definition for PLATFORM_UFIS9600_32X_PORT_MODE_TYPE_T";
    }

    typedef  platform_qos_queue_profile_type_t {
        type enumeration {
            enum profile1 {
                value 1;
                description "supported new 4 queue-bundle per service (default)";
            }
            enum profile2 {
                value 2;
                description "supported new 8 queue-bundle per service";
            }
        }
        description "type definition for PLATFORM_QOS_QUEUE_PROFILE_TYPE_T";
    }

    typedef  platform_kaps_profile_type_t {
        type enumeration {
            enum profile-one {
                value 1;
                description "select kaps profile one";
            }
            enum profile-two {
                value 2;
                description "select kaps profile two";
            }
        }
        description "type definition for PLATFORM_KAPS_PROFILE_TYPE_T";
    }

    typedef  platform_ext_tcam_profile_type_t {
        type enumeration {
            enum profile-one {
                value 3;
                description "select elk-tcam profile one";
            }
            enum profile-two {
                value 4;
                description "select elk-tcam profile two";
            }
            enum profile-three {
                value 5;
                description "select elk-tcam profile three";
            }
        }
        description "type definition for PLATFORM_EXT_TCAM_PROFILE_TYPE_T";
    }

    typedef  platform_tcam_custom_profile_t {
        type enumeration {
            enum custom-profile {
                value 6;
                description "define elk-tcam custom profile";
            }
        }
        description "type definition for PLATFORM_TCAM_CUSTOM_PROFILE_T";
    }

    typedef  platform_kaps_forwading_profile_t {
        type enumeration {
            enum kaps-profile-one {
                value 9;
                description "kaps profile one";
            }
            enum kaps-profile-two {
                value 10;
                description "kaps profile two";
            }
        }
        description "type definition for PLATFORM_KAPS_FORWADING_PROFILE_T";
    }

    typedef  platform_elk_tcam_forwading_profile_t {
        type enumeration {
            enum elk-tcam-profile-one {
                value 11;
                description "elk-tcam profile one";
            }
            enum elk-tcam-profile-two {
                value 12;
                description "elk-tcam profile two";
            }
            enum elk-tcam-profile-three {
                value 13;
                description "elk-tcam profile three";
            }
        }
        description "type definition for PLATFORM_ELK_TCAM_FORWADING_PROFILE_T";
    }

    typedef  platform_cpu_queue_name_t {
        type enumeration {
            enum cpu.q1 {
                value 1;
                if-feature feature-list:HAVE_DUNE;
                description "cpu.q1";
            }
            enum cpu.q2 {
                value 2;
                if-feature feature-list:HAVE_DUNE;
                description "cpu.q2";
            }
            enum cpu.q3 {
                value 3;
                if-feature feature-list:HAVE_DUNE;
                description "cpu.q3";
            }
            enum cpu.q6 {
                value 6;
                if-feature feature-list:HAVE_DUNE;
                description "cpu.q6";
            }
            enum cpu.q7 {
                value 7;
                if-feature feature-list:HAVE_DUNE;
                description "cpu.q7";
            }
            enum vrrp {
                value 11;
                if-feature feature-list:HAVE_VRRPD;
                if-feature feature-list:NOT_HAVE_DUNE;
                description "VRRP queue parameters";
            }
            enum ldp-rsvp {
                value 12;
                if-feature feature-list:HAVE_MPLS;
                if-feature feature-list:NOT_HAVE_DUNE;
                description "LDP-RSVP queue parameters";
            }
            enum rip {
                value 13;
                if-feature feature-list:HAVE_RIPD;
                if-feature feature-list:NOT_HAVE_DUNE;
                description "RIP queue parameters";
            }
            enum dhcp {
                value 15;
                if-feature feature-list:NOT_HAVE_DUNE;
                description "DHCP queue parameters";
            }
            enum oamp {
                value 28;
                if-feature feature-list:HAVE_DUNE;
                description "OAMP queue parameters";
            }
            enum nhop {
                value 32;
                if-feature feature-list:HAVE_DUNE;
                description "nhop queue parameters";
            }
            enum mgmt-route-leak {
                value 33;
                if-feature feature-list:HAVE_DUNE;
                description "nhop queue parameters";
            }
            enum icmp-redirect {
                value 34;
                if-feature feature-list:HAVE_DUNE;
                description "ICMP-redirect queue parameters";
            }
            enum guest {
                value 35;
                if-feature feature-list:HAVE_DUNE;
                if-feature feature-list:HAVE_GUEST_VM;
                description "Guest queue parameters";
            }
            enum cfm {
                value 36;
                if-feature feature-list:HAVE_DUNE;
                description "CFM Error queue parameters";
            }
            enum cpu.q0 {
                if-feature feature-list:HAVE_DUNE;
                description "cpu.q0";
            }
            enum best-effort {
                if-feature feature-list:NOT_HAVE_DUNE;
                description "Best-effort queue parameters";
            }
            enum cpu.q4 {
                if-feature feature-list:HAVE_DUNE;
                description "cpu.q4";
            }
            enum ipmc-miss {
                if-feature feature-list:NOT_HAVE_DUNE;
                description "IPMC-Miss  queue parameters";
            }
            enum cpu.q5 {
                if-feature feature-list:HAVE_DUNE;
                description "cpu.q5";
            }
            enum l3-miss {
                if-feature feature-list:NOT_HAVE_DUNE;
                description "L3-Miss queue parameters";
            }
            enum sflow {
                if-feature feature-list:HAVE_SFLOW;
                if-feature feature-list:NOT_HAVE_DUNE;
                description "SFLOW queue parameters";
            }
            enum bgp {
                if-feature feature-list:HAVE_BGPD;
                if-feature feature-list:NOT_HAVE_DUNE;
                description "BGP queue parameters";
            }
            enum ospf {
                if-feature feature-list:HAVE_OSPFD;
                if-feature feature-list:NOT_HAVE_DUNE;
                description "OSPF queue parameters";
            }
            enum igmp {
                if-feature feature-list:HAVE_DUNE;
                description "IGMP queue parameters";
            }
            enum nd {
                if-feature feature-list:HAVE_IPV6;
                if-feature feature-list:NOT_HAVE_DUNE;
                description "ND queue parameters";
            }
            enum isis {
                if-feature feature-list:HAVE_DUNE;
                if-feature feature-list:HAVE_ISISD;
                description "ISIS queue parameters";
            }
            enum mpls {
                if-feature feature-list:HAVE_MPLS;
                if-feature feature-list:NOT_HAVE_DUNE;
                description "MPLS queue parameters (For GAL label mpls oam packets)";
            }
            enum reserved-mc {
                if-feature feature-list:HAVE_DUNE;
                description "reserved-mc queue parameters";
            }
            enum pim {
                if-feature feature-list:HAVE_PIMD;
                if-feature feature-list:NOT_HAVE_DUNE;
                description "PIM queue parameters";
            }
            enum link-local {
                if-feature feature-list:HAVE_DUNE;
                description "Link-local  queue parameters";
            }
            enum arp {
                if-feature feature-list:NOT_HAVE_DUNE;
                description "ARP queue parameters";
            }
            enum bpdu {
                if-feature feature-list:NOT_HAVE_DUNE;
                description "BPDU queue parameters";
            }
            enum rsvp-ldp {
                if-feature feature-list:HAVE_DUNE;
                if-feature feature-list:HAVE_MPLS;
                description "RSVP/LDP queue parameters";
            }
            enum ccm {
                if-feature feature-list:HAVE_CFM;
                if-feature feature-list:NOT_HAVE_DUNE;
                description "CCM queue parameters";
            }
            enum vrrp-rip-dhcp {
                if-feature feature-list:HAVE_DUNE;
                description "VRRP/RIP/DHCP queue parameters";
            }
            enum bfd {
                if-feature feature-list:HAVE_BFD;
                if-feature feature-list:NOT_HAVE_DUNE;
                description "BFD queue parameters";
            }
            enum ptp {
                if-feature feature-list:HAVE_PTPD;
                if-feature feature-list:NOT_HAVE_DUNE;
                description "PTP queue parameters";
            }
            enum icmp {
                if-feature feature-list:HAVE_DUNE;
                description "ICMP queue parameters";
            }
            enum trill-isis {
                if-feature feature-list:HAVE_TRILLD;
                if-feature feature-list:NOT_HAVE_DUNE;
                description "TRILL queue parameters";
            }
            enum dsp {
                if-feature feature-list:HAVE_DUNE;
                description "DSP queue parameters";
            }
            enum acl {
                if-feature feature-list:NOT_HAVE_DUNE;
                description "ACL queue parameters (for acl logging)";
            }
            enum evpn {
                if-feature feature-list:HAVE_DUNE;
                if-feature feature-list:HAVE_BGP_EVPN;
                description "EVPN queue parameters";
            }
            enum vxlan {
                if-feature feature-list:HAVE_VXLAN;
                if-feature feature-list:NOT_HAVE_DUNE;
                description "VXLAN queue parameters";
            }
        }
        description "type definition for PLATFORM_CPU_QUEUE_NAME_T";
    }

    typedef  platform_cpu_queue_monitor_t {
        type enumeration {
            enum no-monitor {
                value 0;
                description "do not monitor cpu queue usage";
            }
            enum monitor {
                value 1;
                description "monitor cpu queue usage";
            }
        }
        description "type definition for PLATFORM_CPU_QUEUE_MONITOR_T";
    }

    typedef  platform_load_trill_t {
        type enumeration {
            enum outer-l2 {
                value 1;
                description "TRILL outer l2 header (outer SMAC, outer DMAC, outer VLAN)";
            }
            enum inner-l2 {
                value 2;
                description "TRILL inner l2 header (inner SMAC, inner DMAC, inner VLAN, trill tunnel)";
            }
            enum inner-l3 {
                value 3;
                description "TRILL inner l3 header (inner SIP, inner DIP, L4 srx/dest port)";
            }
        }
        description "type definition for PLATFORM_LOAD_TRILL_T";
    }

    typedef  platform_load_hash_t {
        type enumeration {
            enum crc16-bisync {
                value 0;
                description "16-bit CRC16 using the BISYNC Polynomial (DEFAULT)";
            }
            enum crc16-ccitt {
                value 1;
                description "16-bit CRC16 using the CCITT Polynomial";
            }
            enum crc32-lo {
                value 2;
                description "16 LSBs of computated CRC32";
            }
            enum crc32-hi {
                value 3;
                description "16 MSBs of computated CRC32";
            }
        }
        description "type definition for PLATFORM_LOAD_HASH_T";
    }

    typedef  platform_lacp_psc_t {
        type enumeration {
            enum dst-mac {
                value 1;
                description "Destination Mac address based load balancing";
            }
            enum src-mac {
                value 2;
                description "Source Mac address based load balancing";
            }
            enum src-dst-mac {
                value 3;
                description "Source and Destination Mac address based load balancing";
            }
            enum src-ip {
                value 4;
                description "Source IP address based load balancing";
            }
            enum dst-ip {
                value 5;
                description "Destination IP address based load balancing";
            }
            enum src-dst-ip {
                value 6;
                description "Source and Destination IP address based load balancing";
            }
            enum rtag7 {
                value 12;
                description "rtag7 hashing based on pkt type";
            }
        }
        description "type definition for PLATFORM_LACP_PSC_T";
    }

    typedef  platform_forwarding_profile_t {
        type enumeration {
            enum l2-profile-one {
                value 0;
                description "L2 profile One";
            }
            enum l2-profile-two {
                value 1;
                description "L2 profile Two";
            }
            enum l2-profile-three {
                value 2;
                description "L2 profile Three (default)";
            }
            enum l3-profile {
                value 3;
                description "L3 profile";
            }
            enum l3-128bit-profile {
                value 4;
                description "L3 profile with 128 bit prefix support";
            }
            enum lpm-profile {
                value 5;
                description "LPM profile (not supported on Helix4)";
            }
            enum lpm-128bit-profile {
                value 6;
                description "LPM profile with 128 bit prefix support (supported on Tomahawk and
                    Tomahawk2)";
            }
            enum custom-profile {
                value 8;
                description "custom profile (supported on Tomahawk, Tomahawk2 and Helix4)";
            }
        }
        description "type definition for PLATFORM_FORWARDING_PROFILE_T";
    }

    typedef  platform_lpm_custom_profile_t {
        type enumeration {
            enum 2 {
                value 2;
                description "Two banks for lpm and Remaining banks can be used by any";
            }
        }
        description "type definition for PLATFORM_LPM_CUSTOM_PROFILE_T";
    }

    typedef  platform_cpu_queue_lossy_t {
        type enumeration {
            enum lossless {
                value 0;
                description "Configure cpu queue as lossless";
            }
            enum lossy {
                value 1;
                description "Configure cpu queue as lossy";
            }
        }
        description "type definition for PLATFORM_CPU_QUEUE_LOSSY_T";
    }

    typedef  platform_mdb_profile_t {
        type enumeration {
            enum balanced {
                value 0;
                description "select mdb profile balanced";
            }
            enum balanced-p-and-p {
                value 1;
                description "select mdb profile balanced-p-and-p";
            }
            enum l2-xl {
                value 2;
                description "select mdb profile l2-xl";
            }
            enum l3-xl {
                value 3;
                description "select mdb profile l3-xl";
            }
            enum balanced-extended {
                value 4;
                description "select mdb profile balanced-extended";
            }
        }
        description "type definition for PLATFORM_MDB_PROFILE_T";
    }

    typedef  platform_mdb_kaps_type_t {
        type enumeration {
            enum 1 {
                value 1;
                description "kaps cfg 1";
            }
        }
        description "type definition for PLATFORM_MDB_KAPS_TYPE_T";
    }

    typedef  platform_soc_type_t {
        type enumeration {
            enum qax {
                value 0;
                description "QAX SOC";
            }
            enum qux {
                value 1;
                description "QUX SOC";
            }
            enum qmx {
                value 2;
                description "QMX SOC";
            }
            enum dnx {
                value 3;
                description "DNX SOC";
            }
            enum tomahawk {
                value 4;
                description "Tomahawk SOC";
            }
            enum tomahawk2 {
                value 5;
                description "Tomahawk2 SOC";
            }
            enum tomahawk3 {
                value 6;
                description "Tomahawk3 SOC";
            }
            enum tomahawkplus {
                value 7;
                description "TomahawkPlus SOC";
            }
            enum trident2 {
                value 8;
                description "Trident2 SOC";
            }
            enum trident2plus {
                value 9;
                description "Trident2Plus SOC";
            }
            enum trident3 {
                value 10;
                description "Trident3 SOC";
            }
            enum helix4 {
                value 11;
                description "Helix4 SOC";
            }
            enum saber2 {
                value 12;
                description "Saber2 SOC";
            }
            enum maverick2 {
                value 13;
                description "Maverick2 SOC";
            }
            enum unknown {
                value 14;
                description "Unknown";
            }
        }
        description "type definition for PLATFORM_SOC_TYPE_T";
    }

    typedef  platform_system_status_type_t {
        type enumeration {
            enum Normal {
                value 1;
                description "Status is normal";
            }
            enum Minor-Fault {
                value 2;
                description "Status is Minor Fault";
            }
            enum Major-Fault {
                value 3;
                description "Status is Major Fault";
            }
        }
        description "type definition for PLATFORM_SYSTEM_STATUS_TYPE_T";
    }

    typedef  cmm_poe_port_status_t {
        type enumeration {
            enum Disable {
                value 0;
                description "PoE state is disabled";
            }
            enum Enable {
                value 1;
                description "PoE state is enabled";
            }
        }
        description "type definition for CMM_POE_PORT_STATUS_T";
    }

    typedef  cml_cmm_storage_status_t {
        type enumeration {
            enum normal {
                value 1;
                description "Storage consumption <80% of reserved blocks";
            }
            enum critical {
                value 2;
                description "Storage consumption is  80% of reserved blocks";
            }
            enum alert {
                value 3;
                description "Storage consumption is an Alert leve";
            }
            enum undefined {
                value 4;
                description "Storage consumption state is unknown";
            }
        }
        description "type definition for CML_CMM_STORAGE_STATUS_T";
    }

}
