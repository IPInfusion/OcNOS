/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-ram.yang
*
*/

submodule ipi-platform-ram {

    yang-version 1.1;

    belongs-to  ipi-platform { prefix ipi-platform; }

    import feature-list {
        prefix feature-list;
        revision-date 2023-02-21;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for ram components in platform datamodel";


    revision "2022-06-01" {
        description "Updated the yang file with feature";
        reference " 0.4.0.";
    }

    revision "2021-09-03" {
        description "Update descriptions of attribute";
        reference " 0.3.0.";
    }

    revision "2020-12-15" {
        description "Change to have data-types in lower case instead of camel case";
        reference " 0.2.0.";
    }

    revision "2018-06-21" {
        description "Initial Version";
        reference " 0.1.0.";
    }

    grouping ram-state {
        description
            "Operational state data for ram components";
        leaf total-memory  {
            type  uint64;
            units "MBytes";
            description "CPU RAM's total free memory available for utilisation in MBytes.";
        } // END of total-memory definition.

        leaf used-memory  {
            type  uint64;
            units "MBytes";
            description "CPU RAM's used memory available for utilisation in MBytes.";
        } // END of used-memory definition.

        leaf available-memory  {
            type  uint64;
            units "MBytes";
            description "CPU RAM's available memory for utilisation in MBytes.";
        } // END of available-memory definition.

        leaf shared-memory  {
            type  uint64;
            units "MBytes";
            description "CPU RAM's shared memory available for utilisation in MBytes.";
        } // END of shared-memory definition.

        leaf buffers  {
            type  uint64;
            units "MBytes";
            description "CPU RAM's bufffer available for utilisation in MBytes.";
        } // END of buffers definition.

        leaf total-swap  {
            type  uint64;
            units "MBytes";
            description "CPU RAM's total swap memory available for utilisation in MBytes.";
        } // END of total-swap definition.

        leaf free-swap  {
            type  uint64;
            units "MBytes";
            description "CPU RAM's free swap memory available for utilisation in MBytes.";
        } // END of free-swap definition.

        leaf current-process-count  {
            type  uint16;
            description "Number of processes currently running in RAM.";
        } // END of current-process-count definition.

        leaf total-high-memory  {
            type  uint64;
            units "MBytes";
            description "CPU RAM's total High memory in MBytes.";
        } // END of total-high-memory definition.

        leaf available-high-memory  {
            type  uint64;
            units "MBytes";
            description "CPU RAM's available high memory in MBytes.";
        } // END of available-high-memory definition.

        leaf unit-size  {
            type  uint32;
            units "Bytes";
            description "CPU RAM's memory unit size in Bytes.";
        } // END of unit-size definition.

        leaf usage-critical-threshold  {
            type  uint32;
            units "%";
            description "RAM usage threshold % for critical level.";
        } // END of usage-critical-threshold definition.

        leaf usage-alert-threshold  {
            type  uint32;
            units "%";
            description "RAM usage threshold % for alert level.";
        } // END of usage-alert-threshold definition.

    } // END of ram-state definition.

    grouping  ram-grouping {
    description
        "Container for ram component";
    container ram {
        if-feature feature-list:HAVE_CMMD;
        config false;
        description
            "Container for ram component";
        container state {
            config false;
            description
                "Operational state data for ram components";
            uses ram-state;
        } // END of state-container definition.
    } // END of ram-container definition.
    } // END of ram-grouping definition.


}
