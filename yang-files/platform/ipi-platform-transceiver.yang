/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-transceiver.yang
*
*/

submodule ipi-platform-transceiver {

    yang-version 1.1;

    belongs-to  ipi-platform { prefix ipi-platform; }

    import feature-list {
        prefix feature-list;
        revision-date 2023-02-21;
    }

    import ipi-platform-transceiver-types {
        prefix ipi-platform-transceiver-types;
        revision-date 2022-06-01;
    }

    organization
        "IP Infusion Inc.";

    contact
        "Address: 3965 Freedom Circle, Suite 200, Santa Clara, CA 95054
         Phone: +1 408-4001900
         E-mail: support@ipinfusio.com
         Web: http://www.ipinfusion.com/";

    description
        "This module defines a schema for ram components in platform datamodel";


    revision "2022-11-30" {
        description "Adding transceiver critical/alert low/high warning thresholds attributes";
        reference " 0.3.6.";
    }

    revision "2022-06-01" {
        description "Updated the yang file with feature";
        reference " 0.3.5.";
    }

    revision "2022-02-10" {
        description "Added new notifications for rx_los on transceiver ports";
        reference " 0.3.4.";
    }

    revision "2021-09-03" {
        description "Update descriptions of attribute";
        reference " 0.3.4.";
    }

    revision "2021-08-19" {
        description "Changed string attributes length";
        reference " 0.3.3.";
    }

    revision "2021-08-16" {
        description "TSFP new attributes and notifications";
        reference " 0.3.2.";
    }

    revision "2021-08-05" {
        description "Notifications added for transceiver";
        reference " 0.3.1.";
    }

    revision "2021-07-07" {
        description "Removed pattern from string attributes";
        reference " 0.3.0.";
    }

    revision "2021-06-24" {
        description "Several new attributes added";
        reference " 0.3.0.";
    }

    revision "2020-12-15" {
        description "Change to have data-types in lower case instead of camel case";
        reference " 0.2.0.";
    }

    revision "2018-06-21" {
        description "Initial Version";
        reference " 0.1.0.";
    }

    grouping optical-power-state {
        description
            "opticalCMLSEPpowerCMLSEPstate";
        leaf input-power  {
            type  decimal64 {
                 fraction-digits 3;            }
            units "dBm";
            description "Measured RX input power in Channel of transceiver.";
        } // END of input-power definition.

        leaf input-power-alert-max-threshold  {
            type  decimal64 {
                 fraction-digits 3;            }
            units "dBm";
            description "The maximum Rx alert threshold in Channel of transceiver.";
        } // END of input-power-alert-max-threshold definition.

        leaf input-power-critical-max-threshold  {
            type  decimal64 {
                 fraction-digits 3;            }
            units "dBm";
            description "The maximum Rx critical threshold in Channel of transceiver.";
        } // END of input-power-critical-max-threshold definition.

        leaf input-power-critical-min-threshold  {
            type  decimal64 {
                 fraction-digits 3;            }
            units "dBm";
            description "The minimum Rx critical threshold in Channel of transceiver.";
        } // END of input-power-critical-min-threshold definition.

        leaf input-power-alert-min-threshold  {
            type  decimal64 {
                 fraction-digits 3;            }
            units "dBm";
            description "The minimum Rx alert threshold in Channel of transceiver.";
        } // END of input-power-alert-min-threshold definition.

        leaf output-power  {
            type  decimal64 {
                 fraction-digits 3;            }
            units "dBm";
            description "Measured TX output power in Channel of transceiver.";
        } // END of output-power definition.

        leaf output-power-alert-max-threshold  {
            type  decimal64 {
                 fraction-digits 3;            }
            units "dBm";
            description "The maximum Tx alert threshold in Channel of transceiver.";
        } // END of output-power-alert-max-threshold definition.

        leaf output-power-critical-max-threshold  {
            type  decimal64 {
                 fraction-digits 3;            }
            units "dBm";
            description "The maximum Tx critical threshold in Channel of transceiver.";
        } // END of output-power-critical-max-threshold definition.

        leaf output-power-critical-min-threshold  {
            type  decimal64 {
                 fraction-digits 3;            }
            units "dBm";
            description "The minimum Tx critical threshold in Channel of transceiver.";
        } // END of output-power-critical-min-threshold definition.

        leaf output-power-alert-min-threshold  {
            type  decimal64 {
                 fraction-digits 3;            }
            units "dBm";
            description "The minimum Tx alert threshold in Channel of transceiver.";
        } // END of output-power-alert-min-threshold definition.

        leaf laser-bias-current  {
            type  decimal64 {
                 fraction-digits 3;            }
            units "mA";
            description "Internally measured TX Bias Current in Channel of transceiver.";
        } // END of laser-bias-current definition.

        leaf laser-bias-current-alert-max-threshold  {
            type  decimal64 {
                 fraction-digits 3;            }
            units "ampere";
            description "The maximum current alert threshold in Channel of transceiver.";
        } // END of laser-bias-current-alert-max-threshold definition.

        leaf laser-bias-current-critical-max-threshold  {
            type  decimal64 {
                 fraction-digits 3;            }
            units "ampere";
            description "The maximum current critical threshold in Channel of transceiver.";
        } // END of laser-bias-current-critical-max-threshold definition.

        leaf laser-bias-current-critical-min-threshold  {
            type  decimal64 {
                 fraction-digits 3;            }
            units "ampere";
            description "The minimum current critical threshold in Channel of transceiver.";
        } // END of laser-bias-current-critical-min-threshold definition.

        leaf laser-bias-current-alert-min-threshold  {
            type  decimal64 {
                 fraction-digits 3;            }
            units "ampere";
            description "The minimum current alert threshold in Channel of transceiver.";
        } // END of laser-bias-current-alert-min-threshold definition.

    } // END of optical-power-state definition.
    grouping transceiver-channel-state {
        description
            "transceiverCMLSEPchannelCMLSEPstate";
        leaf index  {
            type  uint8;
            description "A unique value, greater than zero, for each channel in the transceiver
                        within the unit.";
        } // END of index definition.

    } // END of transceiver-channel-state definition.
    grouping transceiver-channel-top {
        description
            "transceiverCMLSEPchannelCMLSEPtop";

        list channel {
            key "index";
            config false;
            description
                "List to store operational data related to transceiver channels";
            leaf index  {
                type  leafref {
                    path  "../state/index";
                }
                description "A unique value, greater than zero, for each channel in the transceiver
                            within the unit.";
            } // END of index definition.

            container state {
                config false;
                description
                    "Operational state data for transceiver channel index";
                uses transceiver-channel-state;
                uses optical-power-state;
            } // END of state-container definition.
        } // End of channel-list
    } // END of transceiver-channel-top definition.
    grouping transceiver-state {
        description
            "Operational state data for transceiver components";
        leaf port-no  {
            type  uint8;
            description "Transceiver port number";
        } // END of port-no definition.

        leaf presence  {
            type  ipi-platform-transceiver-types:ddm_cmm_trans_presence_t;
            description "Transceiver presence status";
        } // END of presence definition.

        leaf type  {
            type  ipi-platform-transceiver-types:ddm_cmm_trans_type_t;
            description "Type of the transceiver SFP/QSFP.";
        } // END of type definition.

        leaf channel-count  {
            type  int32;
            description "Number of channels available for this transceiver.";
        } // END of channel-count definition.

        leaf transceiver-identifier  {
            type  ipi-platform-transceiver-types:ddm_cmm_trans_identifier_t;
            description "The Type of transceiver present eg:SFP/SFP+/SFP28/QSFP/QSFP+/QSFP28.";
        } // END of transceiver-identifier definition.

        leaf connector-type  {
            type  ipi-platform-transceiver-types:ddm_cmm_trans_connector_type_t;
            description "Connector type for the transceiver.";
        } // END of connector-type definition.

        leaf ethernet-compliance-code  {
            type  ipi-platform-transceiver-types:ddm_cmm_trans_eth_compliance_t;
            description "Values of Ethernet Compliance codes.";
        } // END of ethernet-compliance-code definition.

        leaf extended-ethernet-compliance-code  {
            type  ipi-platform-transceiver-types:ddm_cmm_trans_ext_eth_compliance_t;
            description "Bitmap of Extended Ethernet Compliance codes. null indicates
                        unavailable.";
        } // END of extended-ethernet-compliance-code definition.

        leaf sonet-compliance-code  {
            type  ipi-platform-transceiver-types:ddm_cmm_trans_sonet_compliance_t;
            description "Sonet Compliance codes of transceiver. null indicates unavailable.";
        } // END of sonet-compliance-code definition.

        leaf fiber-channel-link-length  {
            type  ipi-platform-transceiver-types:ddm_cmm_trans_fiber_channel_linklen_t;
            description "Fiber Channel Link Length.";
        } // END of fiber-channel-link-length definition.

        leaf fiber-channel-transmission-technology  {
            type  ipi-platform-transceiver-types:ddm_cmm_trans_fiber_channel_transmittech_t;
            description "Fiber Channel Transmitter Technology.";
        } // END of fiber-channel-transmission-technology definition.

        leaf fiber-channel-transmission-media  {
            type  ipi-platform-transceiver-types:ddm_cmm_trans_fiber_channel_transmitmedia_t;
            description "Fiber Channel Transmission Media.";
        } // END of fiber-channel-transmission-media definition.

        leaf serial-encoding-algorithm  {
            type  ipi-platform-transceiver-types:ddm_cmm_trans_encoding_t;
            description "Code for SFP/QSFP high speed serial encoding algorithm";
        } // END of serial-encoding-algorithm definition.

        leaf link-length-kilometer  {
            type  int32;
            units "Km";
            description "Link length supported for single mode fiber, units of km.";
        } // END of link-length-kilometer definition.

        leaf link-length-meter  {
            type  int32;
            units "100m";
            description "Link length supported for single mode fiber, units of 100 m.";
        } // END of link-length-meter definition.

        leaf om1-link-length  {
            type  int32;
            units "10m";
            description "Link length supported for 62.5 um OM1 fiber, units of 10 m.";
        } // END of om1-link-length definition.

        leaf om2-link-length  {
            type  int32;
            units "10m";
            description "Link length supported for 50 um OM2 fiber, units of 10 m.";
        } // END of om2-link-length definition.

        leaf om3-link-length  {
            type  int32;
            units "10m";
            description "Link length supported for 50 um OM3 fiber, units of 10 m.";
        } // END of om3-link-length definition.

        leaf om4-link-length  {
            type  int32;
            units "10m";
            description "Link length supported for 50 um OM4 fiber, units of 10 m.";
        } // END of om4-link-length definition.

        leaf vendor-name  {
            type  string {
                length "0..1965";
            }
            description "Transceiver vendor name.";
        } // END of vendor-name definition.

        leaf vendor-ieee-id  {
            type  string {
                length "0..1965";
            }
            description "SFP vendor IEEE company ID.";
        } // END of vendor-ieee-id definition.

        leaf vendor-part-number  {
            type  string {
                length "0..1965";
            }
            description "Part number provided by transceiver vendor.";
        } // END of vendor-part-number definition.

        leaf vendor-revision-number  {
            type  string {
                length "0..1965";
            }
            description "Revision level for part number provided by vendor.";
        } // END of vendor-revision-number definition.

        leaf check-code  {
            type  string {
                length "0..1965";
            }
            description "Check code for Base ID Fields.";
        } // END of check-code definition.

        leaf extended-check-code  {
            type  string {
                length "0..1965";
            }
            description "Check code for the Extended ID Fields.";
        } // END of extended-check-code definition.

        leaf nominal-signalling-rate  {
            type  int32;
            units "100MBd";
            description "Nominal signalling rate, units of 100MBd.";
        } // END of nominal-signalling-rate definition.

        leaf maximum-signalling-rate  {
            type  int32;
            description "Upper bit rate margin, units of 1% above the Nominal Bit Rate.";
        } // END of maximum-signalling-rate definition.

        leaf minimum-signalling-rate  {
            type  int32;
            description "Lower bit rate margin, units of 1% below the Nominal Bit Rate.";
        } // END of minimum-signalling-rate definition.

        leaf vendor-serial-number  {
            type  string {
                length "0..1965";
            }
            description "Serial number provided by vendor.";
        } // END of vendor-serial-number definition.

        leaf vendor-manufacturing-date  {
            type  string {
                length "0..1965";
            }
            description "Vendor's manufacturing date code.";
        } // END of vendor-manufacturing-date definition.

        leaf ddm-type  {
            type  ipi-platform-transceiver-types:ddm_cmm_trans_ddm_support_t;
            description "Indicates which type of diagnostic monitoring is implemented.";
        } // END of ddm-type definition.

        leaf maximum-case-temperature  {
            type  decimal64 {
                 fraction-digits 2;            }
            units "C";
            description "Maximum case temperature in Celsius.";
        } // END of maximum-case-temperature definition.

        leaf grid-spacing  {
            type  decimal64 {
                 fraction-digits 2;            }
            units "GHz";
            description "Transceiver grid spacing";
        } // END of grid-spacing definition.

        leaf first-frequency  {
            type  decimal64 {
                 fraction-digits 2;            }
            units "THz";
            description "Transceiver first frequency";
        } // END of first-frequency definition.

        leaf last-frequency  {
            type  decimal64 {
                 fraction-digits 2;            }
            units "THz";
            description "Transceiver last frequency";
        } // END of last-frequency definition.

        leaf frequency-error  {
            type  decimal64 {
                 fraction-digits 2;            }
            units "GHz";
            description "Transceiver frequency error";
        } // END of frequency-error definition.

        leaf frequency-error-critical-min-threshold  {
            type  decimal64 {
                 fraction-digits 2;            }
            units "GHz";
            description "The minimum critical threshold for transceiver frequency-error";
        } // END of frequency-error-critical-min-threshold definition.

        leaf frequency-error-critical-max-threshold  {
            type  decimal64 {
                 fraction-digits 2;            }
            units "GHz";
            description "The maximum critical threshold for transceiver frequency-error";
        } // END of frequency-error-critical-max-threshold definition.

        leaf frequency-error-alert-min-threshold  {
            type  decimal64 {
                 fraction-digits 2;            }
            units "GHz";
            description "The minimum alert threshold for transceiver frequency-error";
        } // END of frequency-error-alert-min-threshold definition.

        leaf frequency-error-alert-max-threshold  {
            type  decimal64 {
                 fraction-digits 2;            }
            units "GHz";
            description "The maximum alert threshold for transceiver frequency-error";
        } // END of frequency-error-alert-max-threshold definition.

        leaf wavelength-error  {
            type  decimal64 {
                 fraction-digits 4;            }
            units "nm";
            description "Transceiver wavelength error";
        } // END of wavelength-error definition.

        leaf wavelength-error-critical-min-threshold  {
            type  decimal64 {
                 fraction-digits 4;            }
            units "nm";
            description "The minimum critical threshold for transceiver wavelength-error";
        } // END of wavelength-error-critical-min-threshold definition.

        leaf wavelength-error-critical-max-threshold  {
            type  decimal64 {
                 fraction-digits 4;            }
            units "nm";
            description "The maximum critical threshold for transceiver wavelength-error";
        } // END of wavelength-error-critical-max-threshold definition.

        leaf wavelength-error-alert-min-threshold  {
            type  decimal64 {
                 fraction-digits 4;            }
            units "nm";
            description "The minimum alert threshold for transceiver wavelength-error";
        } // END of wavelength-error-alert-min-threshold definition.

        leaf wavelength-error-alert-max-threshold  {
            type  decimal64 {
                 fraction-digits 4;            }
            units "nm";
            description "The maximum alert threshold for transceiver wavelength-error";
        } // END of wavelength-error-alert-max-threshold definition.

        leaf tx-tune-ready  {
            type  boolean;
            description "Tunning process status";
        } // END of tx-tune-ready definition.

        leaf thermoelectric-cooler-fault  {
            type  boolean;
            description "Thermo-electric cooler fault indication";
        } // END of thermoelectric-cooler-fault definition.

        leaf wavelength-locked  {
            type  boolean;
            description "Transceiver wavelength locked";
        } // END of wavelength-locked definition.

        leaf transceiver-temperature  {
            type  decimal64 {
                 fraction-digits 3;            }
            units "celcius";
            description "Internally measured Temperature in Channel of transceiver.";
        } // END of transceiver-temperature definition.

        leaf temperature-alert-max-threshold  {
            type  decimal64 {
                 fraction-digits 3;            }
            units "celcius";
            description "The maximum temperature alert threshold in Channel of transceiver.";
        } // END of temperature-alert-max-threshold definition.

        leaf temperature-critical-max-threshold  {
            type  decimal64 {
                 fraction-digits 3;            }
            units "celcius";
            description "The maximum temperature critical threshold in Channel of transceiver.";
        } // END of temperature-critical-max-threshold definition.

        leaf temperature-critical-min-threshold  {
            type  decimal64 {
                 fraction-digits 3;            }
            units "celcius";
            description "The minimum temperature critical threshold in Channel of transceiver.";
        } // END of temperature-critical-min-threshold definition.

        leaf temperature-alert-min-threshold  {
            type  decimal64 {
                 fraction-digits 3;            }
            units "celcius";
            description "The minimum temperature alert threshold in Channel of transceiver.";
        } // END of temperature-alert-min-threshold definition.

        leaf transceiver-voltage  {
            type  decimal64 {
                 fraction-digits 3;            }
            units "volts";
            description "Measured Voltage in Channel of transceiver.";
        } // END of transceiver-voltage definition.

        leaf voltage-alert-max-threshold  {
            type  decimal64 {
                 fraction-digits 3;            }
            units "volts";
            description "The maximum voltage alert threshold in Channel of transceiver.";
        } // END of voltage-alert-max-threshold definition.

        leaf voltage-critical-max-threshold  {
            type  decimal64 {
                 fraction-digits 3;            }
            units "volts";
            description "The maximum voltage critical threshold in Channel of transceiver.";
        } // END of voltage-critical-max-threshold definition.

        leaf voltage-critical-min-threshold  {
            type  decimal64 {
                 fraction-digits 3;            }
            units "volts";
            description "The minimum voltage critical threshold in Channel of transceiver.";
        } // END of voltage-critical-min-threshold definition.

        leaf voltage-alert-min-threshold  {
            type  decimal64 {
                 fraction-digits 3;            }
            units "volts";
            description "The minimum voltage alert threshold in Channel of transceiver.";
        } // END of voltage-alert-min-threshold definition.

    } // END of transceiver-state definition.
    grouping sfp-xfp-state {
        description
            "Operational state data for sfp and xfp components";
        leaf transmit-status  {
            type  ipi-platform-transceiver-types:ddm_tx_rx_state_t;
            description "Transceiver transmit status";
        } // END of transmit-status definition.

        leaf recieve-loss-status  {
            type  ipi-platform-transceiver-types:ddm_tx_rx_state_t;
            description "Transceiver recieve status";
        } // END of recieve-loss-status definition.

    } // END of sfp-xfp-state definition.
    grouping sfp-state {
        description
            "Operational state data for sfp component";
        leaf sfp-identifier  {
            type  ipi-platform-transceiver-types:ddm_cmm_trans_sfp_extended_identifier_t;
            description "Extended identifier of SFP transceiver for additional information.";
        } // END of sfp-identifier definition.

        leaf sfp-options-implemented  {
            type  ipi-platform-transceiver-types:ddm_cmm_trans_sfp_options_implemented_t;
            description "Transceiver Options Implemented for SFP Transceiver.";
        } // END of sfp-options-implemented definition.

        leaf fiber-channel-sfp-speed  {
            type  ipi-platform-transceiver-types:ddm_cmm_trans_fiber_channel_speed_t;
            description "SFP Fiber Channel Speed.";
        } // END of fiber-channel-sfp-speed definition.

        leaf sfp-infiniband-compliance-code  {
            type  ipi-platform-transceiver-types:ddm_cmm_trans_sfp_infiniband_compliance_t;
            description "SFP Infiniband Compliance.";
        } // END of sfp-infiniband-compliance-code definition.

        leaf sfp-escon-compliance-code  {
            type  ipi-platform-transceiver-types:ddm_cmm_trans_sfp_escon_compliance_t;
            description "FP Enterprise Systems Connection compliance.";
        } // END of sfp-escon-compliance-code definition.

        leaf sfp-plus-cable-technology  {
            type  ipi-platform-transceiver-types:ddm_cmm_trans_sfp_plus_cable_tech_t;
            description "SFP+ Cable Technology";
        } // END of sfp-plus-cable-technology definition.

    } // END of sfp-state definition.
    grouping xfp-state {
        description
            "Operational state data for xfp component";
        leaf xsfp-identifier  {
            type  ipi-platform-transceiver-types:ddm_cmm_trans_xfp_extended_identifier_t;
            description "Extended identifier of XFP transceiver for additional information.";
        } // END of xsfp-identifier definition.

        leaf xfp-10g-ethernet-compliance-code  {
            type  ipi-platform-transceiver-types:ddm_cmm_trans_xfp_10g_eth_compliance_t;
            description "10G ethernet compliance codes of XFP transceiver.";
        } // END of xfp-10g-ethernet-compliance-code definition.

        leaf xfp-10g-fiber-channel-compliance-code  {
            type  ipi-platform-transceiver-types:ddm_cmm_trans_xfp_10g_fiber_chn_compliance_t;
            description "10G fiber channel compliance codes of XFP transceiver.";
        } // END of xfp-10g-fiber-channel-compliance-code definition.

        leaf xfp-10g-copper-link-compliance-code  {
            type  ipi-platform-transceiver-types:ddm_cmm_trans_xfp_10g_copper_links_rsvd_t;
            description "10G copper link codes of XFP transceiver.";
        } // END of xfp-10g-copper-link-compliance-code definition.

        leaf xfp-lower-speed-link-compliance-code  {
            type  ipi-platform-transceiver-types:ddm_cmm_trans_xfp_lower_speed_links_t;
            description "Lower speed codes of XFP transceiver.";
        } // END of xfp-lower-speed-link-compliance-code definition.

        leaf xfp-sonet-interconnect-compliance-code  {
            type  ipi-platform-transceiver-types:ddm_cmm_trans_xfp_sonet_interconnect_t;
            description "SONET/SDH interconnect codes of XFP transceiver.";
        } // END of xfp-sonet-interconnect-compliance-code definition.

        leaf xfp-sonet-short-haul-compliance-code  {
            type  ipi-platform-transceiver-types:ddm_cmm_trans_xfp_sonet_short_haul_t;
            description "SONET/SDH short haul codes of XFP transceiver.";
        } // END of xfp-sonet-short-haul-compliance-code definition.

        leaf xfp-sonet-long-haul-compliance-code  {
            type  ipi-platform-transceiver-types:ddm_cmm_trans_xfp_sonet_long_haul_t;
            description "SONET/SDH long haul codes of XFP transceiver.";
        } // END of xfp-sonet-long-haul-compliance-code definition.

        leaf xfp-sonet-very-long-haul-compliance-code  {
            type  ipi-platform-transceiver-types:ddm_cmm_trans_xfp_sonet_very_long_haul_t;
            description "SONET/SDH very long haul codes of XFP transceiver.";
        } // END of xfp-sonet-very-long-haul-compliance-code definition.

        leaf xfp-serial-encoding-algorithm  {
            type  ipi-platform-transceiver-types:ddm_cmm_trans_xfp_encoding_t;
            description "Code for XFP high speed serial encoding algorithm.";
        } // END of xfp-serial-encoding-algorithm definition.

        leaf xsfp-options-implemented  {
            type  ipi-platform-transceiver-types:ddm_cmm_trans_xfp_options_implemented_t;
            description "Transceiver Options Implemented for XFP Transceiver.";
        } // END of xsfp-options-implemented definition.

        leaf xfp-auxillary-voltage  {
            type  ipi-platform-transceiver-types:ddm_cmm_trans_xfp_voltage_aux_monitor_t;
            description "XFP Transceiver voltages monitored by auxiliary channels.";
        } // END of xfp-auxillary-voltage definition.

    } // END of xfp-state definition.
    grouping qsfp-state {
        description
            "Operational state data for qsfp components";
        leaf reset-status  {
            type  ipi-platform-transceiver-types:ddm_cmm_trans_reset_t;
            description "Transceiver reset status";
        } // END of reset-status definition.

        leaf power  {
            type  ipi-platform-transceiver-types:ddm_cmm_trans_power_t;
            description "Transceiver power status";
        } // END of power definition.

        leaf lane1-transmission  {
            type  ipi-platform-transceiver-types:ddm_tx_rx_state_t;
            description "Lane 1 Transmission";
        } // END of lane1-transmission definition.

        leaf lane1-transmission-loss  {
            type  ipi-platform-transceiver-types:ddm_tx_rx_state_t;
            description "Lane 1 Transmission Loss";
        } // END of lane1-transmission-loss definition.

        leaf lane1-recieve-loss  {
            type  ipi-platform-transceiver-types:ddm_tx_rx_state_t;
            description "Lane 1 recieve Loss";
        } // END of lane1-recieve-loss definition.

        leaf lane2-transmission  {
            type  ipi-platform-transceiver-types:ddm_tx_rx_state_t;
            description "Lane 2 Transmission";
        } // END of lane2-transmission definition.

        leaf lane2-transmission-loss  {
            type  ipi-platform-transceiver-types:ddm_tx_rx_state_t;
            description "Lane 2 Transmission Loss";
        } // END of lane2-transmission-loss definition.

        leaf lane2-recieve-loss  {
            type  ipi-platform-transceiver-types:ddm_tx_rx_state_t;
            description "Lane 2 recieve Loss";
        } // END of lane2-recieve-loss definition.

        leaf lane3-transmission  {
            type  ipi-platform-transceiver-types:ddm_tx_rx_state_t;
            description "Lane 3 transmission";
        } // END of lane3-transmission definition.

        leaf lane3-transmission-loss  {
            type  ipi-platform-transceiver-types:ddm_tx_rx_state_t;
            description "Lane 3 transmission Loss";
        } // END of lane3-transmission-loss definition.

        leaf lane3-recieve-loss  {
            type  ipi-platform-transceiver-types:ddm_tx_rx_state_t;
            description "Lane 3 recieve Loss";
        } // END of lane3-recieve-loss definition.

        leaf lane4-transmission  {
            type  ipi-platform-transceiver-types:ddm_tx_rx_state_t;
            description "Lane 4 transmission";
        } // END of lane4-transmission definition.

        leaf lane4-transmission-loss  {
            type  ipi-platform-transceiver-types:ddm_tx_rx_state_t;
            description "Lane 4 transmission Loss";
        } // END of lane4-transmission-loss definition.

        leaf lane4-recieve-loss  {
            type  ipi-platform-transceiver-types:ddm_tx_rx_state_t;
            description "Lane 4 recieve Loss";
        } // END of lane4-recieve-loss definition.

        leaf qsfp-identifier  {
            type  ipi-platform-transceiver-types:ddm_cmm_qsfp_extended_identifier_t;
            description "Extended identifier of QSFP transceiver for additional information.";
        } // END of qsfp-identifier definition.

        leaf fiber-channel-qsfp-speed  {
            type  ipi-platform-transceiver-types:ddm_cmm_trans_fiber_channel_speed_t;
            description "QSFP Fiber Channel Speed.";
        } // END of fiber-channel-qsfp-speed definition.

        leaf qsfp-options-implemented  {
            type  ipi-platform-transceiver-types:ddm_cmm_trans_qsfp_options_implemented_t;
            description "Transceiver Options Implemented for QSFP Transceiver.";
        } // END of qsfp-options-implemented definition.

    } // END of qsfp-state definition.

    grouping  transceiver-grouping {
    description
        "Container for transceiver component";
    container transceiver {
        if-feature feature-list:HAVE_CMMD;
        if-feature feature-list:NOT_HAVE_TIBIT;
        config false;
        description
            "Container for transceiver component";
        container state {
            config false;
            description
                "Operational state data for transceiver components";
            uses transceiver-state;
        } // END of state-container definition.
        container sfp {
            config false;
            description
                "Container for sfp type transceiver";
            container state {
                config false;
                description
                    "Operational state data for sfp type transcivers";
                uses sfp-xfp-state;
                uses sfp-state;
            } // END of state-container definition.
        } // END of sfp-container definition.
        container xfp {
            config false;
            description
                "Container for xfp type transceiver";
            container state {
                config false;
                description
                    "Operational state data for sfp type transceivers";
                uses sfp-xfp-state;
                uses xfp-state;
            } // END of state-container definition.
        } // END of xfp-container definition.
        container qsfp {
            config false;
            description
                "Container for qsfp type transceiver";
            container state {
                config false;
                description
                    "Operational state data for qsfp type transceivers";
                uses qsfp-state;
            } // END of state-container definition.
        } // END of qsfp-container definition.
        container channels {
            config false;
            description
                "Container for transceivers channels information";
            uses transceiver-channel-top;
        } // END of channels-container definition.
    } // END of transceiver-container definition.
    } // END of transceiver-grouping definition.


}
