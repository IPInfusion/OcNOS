/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-chassis.yang
*
*/

submodule ipi-platform-chassis {

    yang-version 1.1;

    belongs-to  ipi-platform { prefix ipi-platform; }

    import feature-list {
        prefix feature-list;
        revision-date 2023-02-21;
    }

    import ietf-yang-types {
        prefix yang;
        revision-date 2013-07-15;
    }

    import ipi-platform-types {
        prefix ipi-platform-types;
        revision-date 2022-06-01;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for chassis component in platform
                datamodel";


    revision "2022-06-01" {
        description "Updated the yang file with feature";
        reference " 0.5.0.";
    }

    revision "2021-12-10" {
        description "Change sytem status datatype from CML_RAW_STRING_T to PLATFORM_SYSTEM_STATUS_TYPE_T";
        reference " 0.4.0.";
    }

    revision "2021-09-03" {
        description "Update descriptions of attribute";
        reference " 0.3.0.";
    }

    revision "2021-03-18" {
        description "Updated fan-board-id attribute pattern";
        reference " 0.2.0.";
    }

    revision "2021-01-25" {
        description "Initial version adding support to chassis component in ipi-platform module";
        reference " 0.1.0.";
    }

    grouping chassis-state {
        description
            "Chassis data for platform components";
        leaf up-time  {
            type  yang:timeticks;
            description "The system up time of the unit";
        } // END of up-time definition.

        leaf mac-address  {
            type  yang:mac-address {
                pattern "[0-9a-fA-F]{2}(:[0-9a-fA-F]{2}){5}";
                }
                description "A 6-octet MAC Address assigned to this unit";
            } // END of mac-address definition.

            leaf label-revision  {
                type  string {
                    length "1..1965";
                }
                description "The unit's label revision";
            } // END of label-revision definition.

            leaf country-code  {
                type  string {
                    length "1..1965";
                }
                description "The unit manufacturer's country code";
            } // END of country-code definition.

            leaf fan-tray-count  {
                type  uint32;
                description "The number of fan trays on the unit";
            } // END of fan-tray-count definition.

            leaf power-supplies-count  {
                type  uint32;
                description "The number of power supplies available to the unit";
            } // END of power-supplies-count definition.

            leaf chassis-fast-ethernet-count  {
                type  uint32;
                description "The number of 100M Ethernet/802.3 interfaces in this unit";
            } // END of chassis-fast-ethernet-count definition.

            leaf chassis-1g-ethernet-count  {
                type  uint32;
                description "The number of 1G Ethernet/802.3 interfaces in this unit";
            } // END of chassis-1g-ethernet-count definition.

            leaf chassis-10g-ethernet-count  {
                type  uint32;
                description "The number of 10G Ethernet/802.3 interfaces in this unit";
            } // END of chassis-10g-ethernet-count definition.

            leaf chassis-25g-ethernet-count  {
                type  uint32;
                description "The number of 25G Ethernet/802.3 interfaces in this unit";
            } // END of chassis-25g-ethernet-count definition.

            leaf chassis-40g-ethernet-count  {
                type  uint32;
                description "The number of 40G Ethernet/802.3 interfaces in this unit";
            } // END of chassis-40g-ethernet-count definition.

            leaf chassis-50g-ethernet-count  {
                type  uint32;
                description "The number of 50G Ethernet/802.3 interfaces in this unit";
            } // END of chassis-50g-ethernet-count definition.

            leaf chassis-100g-ethernet-count  {
                type  uint32;
                description "The number of 100G Ethernet/802.3 interfaces in this unit";
            } // END of chassis-100g-ethernet-count definition.

            leaf service-tag  {
                type  string {
                    length "1..1965";
                }
                description "The unit's service tag";
            } // END of service-tag definition.

            leaf platform-name  {
                type  string {
                    length "1..1965";
                }
                description "The platform name for the unit";
            } // END of platform-name definition.

            leaf onie-version  {
                type  string {
                    length "1..1965";
                }
                description "The unit's ONIE version";
            } // END of onie-version definition.

            leaf vendor-name  {
                type  string {
                    length "1..1965";
                }
                description "The unit's vendor name";
            } // END of vendor-name definition.

            leaf diagnostic-version  {
                type  string {
                    length "1..1965";
                }
                description "The unit's diagnostic version";
            } // END of diagnostic-version definition.

            leaf cyclic-redundancy-32bit-value  {
                type  string {
                    length "1..1965";
                }
                description "The unit's Cyclic Redundancy Check 32 Bit value in hex";
            } // END of cyclic-redundancy-32bit-value definition.

            leaf switch-chip-revision  {
                type  string {
                    length "1..1965";
                }
                description "The unit's switch chip revision";
            } // END of switch-chip-revision definition.

            leaf fan-board-id  {
                type  string {
                    length "1..1965";
                }
                description "The unit's fan board identifier";
            } // END of fan-board-id definition.

            leaf supported-label-revision  {
                type  string {
                    length "1..1965";
                }
                description "The unit's supported label revision";
            } // END of supported-label-revision definition.

            leaf supported-switch-chip-revision  {
                type  string {
                    length "1..1965";
                }
                description "The unit's switch supported ship revision";
            } // END of supported-switch-chip-revision definition.

    } // END of chassis-state definition.
    grouping chassis-system-status {
        description
            "Chassis component system status";
        leaf system_status  {
            type  ipi-platform-types:platform_system_status_type_t;
            description "The overall unit system status";
        } // END of system_status definition.

        leaf cpu_status  {
            type  ipi-platform-types:platform_system_status_type_t;
            description "The overall CPU system status";
        } // END of cpu_status definition.

        leaf ram_status  {
            type  ipi-platform-types:platform_system_status_type_t;
            description "The overall RAM system status";
        } // END of ram_status definition.

        leaf storage_status  {
            type  ipi-platform-types:platform_system_status_type_t;
            description "The overall storage system status";
        } // END of storage_status definition.

        leaf temperature_status  {
            type  ipi-platform-types:platform_system_status_type_t;
            description "The overall temperature system status";
        } // END of temperature_status definition.

        leaf fan_status  {
            type  ipi-platform-types:platform_system_status_type_t;
            description "The overall FAN system status";
        } // END of fan_status definition.

        leaf psu_status  {
            type  ipi-platform-types:platform_system_status_type_t;
            description "The overall PSU system status";
        } // END of psu_status definition.

        leaf software_status  {
            type  ipi-platform-types:platform_system_status_type_t;
            description "The overall software system status";
        } // END of software_status definition.

    } // END of chassis-system-status definition.

    grouping  chassis-grouping {
    description
        "Container for chassis component";
    container chassis {
        if-feature feature-list:HAVE_CMMD;
        config false;
        description
            "Container for chassis component";
        container state {
            config false;
            description
                "Operational state data for chassis components";
            uses chassis-state;
            uses chassis-system-status;
        } // END of state-container definition.
    } // END of chassis-container definition.
    } // END of chassis-grouping definition.


}
