/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-linecard.yang
*
*/

submodule ipi-platform-linecard {

    yang-version 1.1;

    belongs-to  ipi-platform { prefix ipi-platform; }

    import feature-list {
        prefix feature-list;
        revision-date 2023-02-21;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for linecard components in platform
                datamodel";


    revision "2022-06-01" {
        description "Updated the yang file with feature";
        reference " 0.3.0.";
    }

    revision "2021-09-03" {
        description "Update descriptions of attribute";
        reference " 0.2.0.";
    }

    revision "2021-01-25" {
        description "Initial version adding support to linecard components in ipi-platform module";
        reference " 0.1.0.";
    }

    grouping linecard-state {
        description
            "Linecard data for platform components";
        leaf slot-id  {
            type  string {
                length "1..1965";
            }
            description "Identifier for the slot or chassis position in which the linecard is
                        installed";
        } // END of slot-id definition.

    } // END of linecard-state definition.

    grouping  linecard-grouping {
    description
        "Container for linecard component";
    container linecard {
        if-feature feature-list:HAVE_CMMD;
        config false;
        description
            "Container for linecard component";
        container state {
            config false;
            description
                "Operational state data for linecard components";
            uses linecard-state;
        } // END of state-container definition.
    } // END of linecard-container definition.
    } // END of linecard-grouping definition.


}
