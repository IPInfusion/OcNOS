/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-temperature.yang
*
*/

submodule ipi-platform-temperature {

    yang-version 1.1;

    belongs-to  ipi-platform { prefix ipi-platform; }

    import feature-list {
        prefix feature-list;
        revision-date 2023-02-21;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for temperature components in platform
                datamodel";


    revision "2022-06-01" {
        description "Updated the yang file with feature";
        reference " 0.5.0.";
    }

    revision "2021-09-03" {
        description "Update descriptions of attribute";
        reference " 0.4.0.";
    }

    revision "2021-06-24" {
        description "New attributes added:avg,min,max and interval.";
        reference " 0.3.0.";
    }

    revision "2021-03-18" {
        description "Added notifications for temperature alarms";
        reference " 0.2.0.";
    }

    revision "2021-01-25" {
        description "Initial version adding support to temperature components in ipi-platform module";
        reference " 0.1.0.";
    }



    typedef  cml_alarm_severity_t {
        type enumeration {
            enum indeterminate {
                value 2;
                description "Indicates that the severity level could not be determined.";
            }
            enum minor {
                value 3;
                description "Indicates the existence of a non-service affecting fault condition and that corrective action should be taken in order to prevent a more serious fault.";
            }
            enum warning {
                value 4;
                description "Indicates the detection of a potential or impending service affecting fault, before any significant effects have been felt.";
            }
            enum major {
                value 5;
                description "Indicates that a service affecting condition has developed and an urgent corrective action is required.";
            }
            enum critical {
                value 6;
                description "Indicates that a service affecting condition has occurred and an immediate corrective action is required.";
            }
        }
        description "type definition for CML_ALARM_SEVERITY_T";
    }    grouping platform-component-temp-alarm-state {
        description
            "Temperature alarm data for platform components";
        leaf alarm-status  {
            type  boolean;
            description "A value of true indicates the alarm has been raised or asserted. The
                        value should be false when the alarm is cleared.";
        } // END of alarm-status definition.

        leaf alarm-threshold  {
            type  decimal64 {
                 fraction-digits 2;            }
            units "celsius";
            description "The threshold value that was crossed for this alarm.";
        } // END of alarm-threshold definition.

        leaf alarm-severity  {
            type  cml_alarm_severity_t;
            description "The severity of the current alarm.";
        } // END of alarm-severity definition.

        leaf minimum-emergency-temperature  {
            type  decimal64 {
                 fraction-digits 2;            }
            units "celsius";
            description "The minimum temperature threshold for emergency alarm.";
        } // END of minimum-emergency-temperature definition.

        leaf maximum-emergency-temperature  {
            type  decimal64 {
                 fraction-digits 2;            }
            units "celsius";
            description "The maximum temperature threshold for emergency alarm.";
        } // END of maximum-emergency-temperature definition.

        leaf minimum-alert-temperature  {
            type  decimal64 {
                 fraction-digits 2;            }
            units "celsius";
            description "The minimum temperature threshold for alert alarm.";
        } // END of minimum-alert-temperature definition.

        leaf maximum-alert-temperature  {
            type  decimal64 {
                 fraction-digits 2;            }
            units "celsius";
            description "The maximum temperature threshold for alert alarm.";
        } // END of maximum-alert-temperature definition.

        leaf minimum-critical-temperature  {
            type  decimal64 {
                 fraction-digits 2;            }
            units "celsius";
            description "The minimum temperature threshold for critical alarm.";
        } // END of minimum-critical-temperature definition.

        leaf maximum-critical-temperature  {
            type  decimal64 {
                 fraction-digits 2;            }
            units "celsius";
            description "The maximum temperature threshold for critical alarm.";
        } // END of maximum-critical-temperature definition.

    } // END of platform-component-temp-alarm-state definition.
    grouping platform-component-temp-state {
        description
            "Temperature state data for device components";
        leaf instant  {
            type  decimal64 {
                 fraction-digits 2;            }
            units "celsius";
            description "The instantaneous temperature value.";
        } // END of instant definition.

        leaf min  {
            type  decimal64 {
                 fraction-digits 2;            }
            units "celsius";
            description "The minimum value of the statistic over the sampling period.";
        } // END of min definition.

        leaf max  {
            type  decimal64 {
                 fraction-digits 2;            }
            units "celsius";
            description "The maximum value of the statistic over the sampling period.";
        } // END of max definition.

        leaf avg  {
            type  decimal64 {
                 fraction-digits 2;            }
            units "celsius";
            description "The arithmetic mean value of the statistic over the sampling period.";
        } // END of avg definition.

        leaf interval  {
            type  uint32;
            units "seconds";
            description "This reports the time interval over which the min/max/average
                        statistics are computed by
                        the system.";
        } // END of interval definition.

        leaf sensor-name  {
            type  string {
                length "1..1965";
            }
            description "The name of the temperature sensor in the system.";
        } // END of sensor-name definition.

        leaf sensor-index  {
            type  uint8;
            description "The index of the temperature sensor in the system.";
        } // END of sensor-index definition.

    } // END of platform-component-temp-state definition.

    grouping  temperature-grouping {
    description
        "Container for temperature component";
    container temperature {
        if-feature feature-list:HAVE_CMMD;
        config false;
        description
            "Container for temperature component";
        uses platform-component-temp-state;
        uses platform-component-temp-alarm-state;
    } // END of temperature-container definition.
    } // END of temperature-grouping definition.


}
