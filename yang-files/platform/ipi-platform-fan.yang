/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-fan.yang
*
*/

submodule ipi-platform-fan {

    yang-version 1.1;

    belongs-to  ipi-platform { prefix ipi-platform; }

    import feature-list {
        prefix feature-list;
        revision-date 2023-02-21;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for fan components in platform datamodel";


    revision "2022-07-12" {
        description "New notifications added for FAN rpm changes";
        reference " 0.4.0.";
    }

    revision "2021-09-03" {
        description "Update descriptions of attribute";
        reference " 0.3.0.";
    }

    revision "2021-03-18" {
        description "Added notification for fan alarms";
        reference " 0.2.0.";
    }

    revision "2021-01-25" {
        description "Initial version adding support to fan components in ipi-platform module";
        reference " 0.1.0.";
    }



    typedef  cml_cmm_fan_status_t {
        type enumeration {
            enum unknown {
                value 0;
                description "Fan status unknown";
            }
            enum not-present {
                value 1;
                description "Fan not present";
            }
            enum running {
                value 2;
                description "Fan running";
            }
            enum faulty {
                value 3;
                description "Fan faulty";
            }
            enum stalled {
                value 4;
                description "Fan stalled";
            }
        }
        description "type definition for CML_CMM_FAN_STATUS_T";
    }

    typedef  cml_cmm_fan_location_t {
        type enumeration {
            enum unknown {
                value 0;
                description "Fan location unknown";
            }
            enum front {
                value 1;
                description "Fan located in front";
            }
            enum rear {
                value 2;
                description "Fan located in rear";
            }
            enum not-applicable {
                value 3;
                description "Fan location not-applicable";
            }
        }
        description "type definition for CML_CMM_FAN_LOCATION_T";
    }    grouping fan-state {
        description
            "Fan data for platform components";
        leaf fan-index  {
            type  uint8;
            description "Fan identifier index in the system";
        } // END of fan-index definition.

        leaf rpm  {
            type  uint32;
            units "rpm";
            description "Fan speed expressed in Rotations Per Minute";
        } // END of rpm definition.

        leaf minimum-rpm  {
            type  uint32;
            units "rpm";
            description "Value represents the minimum supported RPM of fan";
        } // END of minimum-rpm definition.

        leaf maximum-rpm  {
            type  uint32;
            units "rpm";
            description "Value represents the maximum supported RPM of fan";
        } // END of maximum-rpm definition.

        leaf fan-status  {
            type  cml_cmm_fan_status_t;
            description "The status of the fan";
        } // END of fan-status definition.

        leaf fan-location  {
            type  cml_cmm_fan_location_t;
            description "The location of fan in tray";
        } // END of fan-location definition.

    } // END of fan-state definition.

    grouping  fan-grouping {
    description
        "Container for fan component";
    container fan {
        if-feature feature-list:HAVE_CMMD;
        config false;
        description
            "Container for fan component";
        container state {
            config false;
            description
                "Operational state data for fan components";
            uses fan-state;
        } // END of state-container definition.
    } // END of fan-container definition.
    } // END of fan-grouping definition.


}
