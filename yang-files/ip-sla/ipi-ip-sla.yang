/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ip-sla.yang
*
*/

module ipi-ip-sla {

    yang-version 1.1;

    namespace   "http://www.ipinfusion.com/yang/ocnos/ipi-ip-sla";

    prefix "ipi-ip-sla";

    import cml-data-types {
        prefix cml-data-types;
        revision-date 2022-09-30;
    }

    import ietf-yang-types {
        prefix yang;
        revision-date 2013-07-15;
    }

    import ietf-inet-types {
        prefix inet;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for ipsla definations";


    revision "2022-06-01" {
        description "Updated the yang file with feature";
        reference " 0.2.0.";
    }

    revision "2021-02-12" {
        description "Initial Version";
        reference "Initial Version";
    }



    typedef  ip_sla_hostname_t {
        type union {
            type inet:ipv4-address {

            }
            type inet:ipv6-address {

            }
            type cml-data-types:cml_host_string_t {

            }
        }
        description "type definition for IP_SLA_HOSTNAME_T";
    }    grouping ip-sla-schedule-config {
        description
            "Grouping for IPSLA schedule configuration data";
        leaf scheduled-pid  {
            type  uint16 {
                 range "1..65535"  {
                    description "1..65535: Supported range 1 - 65535";
                 }
            }
            description "Use this attribute to schedule the IPSLA measurement operation.";
        } // END of scheduled-pid definition.

        leaf time-range-name  {
            type  string {
                length "1..1965";
                pattern "[^?' =,>|]+";
            }
            description "Time range object name to schedule this SLA operation.";
        } // END of time-range-name definition.

        leaf vrf-name  {
            type  string {
                length "1..1965";
                pattern "[^?' =,>|]+";
            }
            description "VRF name";
        } // END of vrf-name definition.

    } // END of ip-sla-schedule-config definition.
    grouping ip-sla-schedule-configs {
        description
            "Grouping for IP SLA Scheduling";
        container scheduled-processes {
            description
                "IP SLA Schedule Processes";

            list scheduled-process {
                key "scheduled-pid time-range-name";
                description
                    "IP SLA Schedule process";
                leaf scheduled-pid  {
                    type  leafref {
                        path  "../config/scheduled-pid";
                    }
                    description "Use this attribute to schedule the IPSLA measurement operation.";
                } // END of scheduled-pid definition.

                leaf time-range-name  {
                    type  leafref {
                        path  "../config/time-range-name";
                    }
                    description "Time range object name to schedule this SLA operation.";
                } // END of time-range-name definition.

                container config {
                    description
                        "Configuration data for IPSLA scheduling";
                    uses ip-sla-schedule-config;
                } // END of config-container definition.
                container state {
                    config false;
                    description
                        "Operational state data for IPSLA scheduling";
                    uses ip-sla-schedule-config;
                } // END of state-container definition.
            } // End of scheduled-process-list
        } // END of scheduled-processes-container definition.
    } // END of ip-sla-schedule-configs definition.
    grouping ip-sla-icmp-echo-config {
        description
            "Grouping for icmp echo configuration data";
        leaf host  {
            type  ip_sla_hostname_t;
            description "Use this attribute to set the ICMP Echo host name or IP address.";
        } // END of host definition.

        leaf source-interface  {
            type  string {
                length "1..1965";
                pattern "[^?' =,>|]+";
            }
            description "Source Interface name";
        } // END of source-interface definition.

        leaf frequency  {
            type  uint8 {
                 range "1..60"  {
                    description "1..60: Supported range 1 - 60";
                 }
            }
            units "seconds";
            description "The frequency (interval) correlates to how often the ICMP packet is
                        sent. The unit of this parameter is in seconds.";
        } // END of frequency definition.

        leaf timeout  {
            type  uint16 {
                 range "1000..60000"  {
                    description "1000..60000: Supported range 1000 - 60000";
                 }
            }
            units "milliseconds";
            description "The timeout value correlates to how long the Ping application will
                        wait for the response after sending packets ICMP Echo packets.";
        } // END of timeout definition.

        leaf threshold  {
            type  uint16 {
                 range "1000..60000"  {
                    description "1000..60000: Supported range 1000 - 60000";
                 }
            }
            units "milliseconds";
            description "The threshold value correlates to the limit the administrator sets as
                        what would be a successful test. Threshold can be configured in
                        milli-seconds.";
        } // END of threshold definition.

    } // END of ip-sla-icmp-echo-config definition.
    grouping ip-sla-icmp-echo-configs {
        description
            "Grouping for ICMP-Echo";
        container icmp-echo-processes {
            description
                "IP SLA ICMP Echo";

            list icmp-echo-process {
                key "host";
                max-elements 1;
                description
                    "List of ICMP Echo process";
                leaf host  {
                    type  leafref {
                        path  "../config/host";
                    }
                    description "Use this attribute to set the ICMP Echo host name or IP address.";
                } // END of host definition.

                container config {
                    description
                        "Configuration data for icmp-echo";
                    uses ip-sla-icmp-echo-config;
                } // END of config-container definition.
                container state {
                    config false;
                    description
                        "Operational state data for icmp-echo";
                    uses ip-sla-icmp-echo-config;
                } // END of state-container definition.
            } // End of icmp-echo-process-list
        } // END of icmp-echo-processes-container definition.
    } // END of ip-sla-icmp-echo-configs definition.
    grouping ip-sla-statistics-entries {
        description
            "Grouping for IP SLA stats data";
        leaf start-time  {
            type  yang:date-and-time {
                pattern "\\d{4}-\\d{2}-\\d{2}T\\d{2}:\\d{2}:\\d{2}(\\.\\d+)?(Z|[\\+\\-]\\d{2}:\\d{2})";
                }
                config false;
                description "Time at which ip sla measurement started";
            } // END of start-time definition.

            leaf elapsed-time  {
                type  uint64;
                config false;
                description "Time elapsed since the ip sla measurement started. In milliseconds";
            } // END of elapsed-time definition.

            leaf packets-sent  {
                type  uint32;
                config false;
                description "Number of test packets sent";
            } // END of packets-sent definition.

            leaf packets-received  {
                type  uint32;
                config false;
                description "Number of test packets received";
            } // END of packets-received definition.

            leaf packets-lost  {
                type  decimal64 {
                     fraction-digits 6;                }
                config false;
                description "Packet loss percentage";
            } // END of packets-lost definition.

            leaf invalid-tests  {
                type  uint32;
                config false;
                description "Number of Invalid tests";
            } // END of invalid-tests definition.

            leaf minimum-round-trip-delay  {
                type  uint64;
                config false;
                description "Minimum Round trip delay time";
            } // END of minimum-round-trip-delay definition.

            leaf maximum-round-trip-delay  {
                type  uint64;
                config false;
                description "Maximum Round Trip delay time";
            } // END of maximum-round-trip-delay definition.

            leaf average-round-trip-delay  {
                type  uint64;
                config false;
                description "Average Round Trip delay time";
            } // END of average-round-trip-delay definition.

    } // END of ip-sla-statistics-entries definition.
    grouping ip-sla-process-config {
        description
            "Grouping for icmp echo configuration data";
        leaf identifier  {
            type  uint16 {
                 range "1..65535"  {
                    description "1..65535: Supported range 1 - 65535";
                 }
            }
            description "Use this attribute to set the IPSLA.";
        } // END of identifier definition.

    } // END of ip-sla-process-config definition.
    grouping ip-sla-config {
        description
            "Grouping for IP SLA";
        container processes {
            description
                "IP SLA processes";

            list process {
                key "identifier";
                description
                    "List of IP SLA processes";
                leaf identifier  {
                    type  leafref {
                        path  "../config/identifier";
                    }
                    description "Use this attribute to set the IPSLA.";
                } // END of identifier definition.

                container config {
                    description
                        "Configuration data for IP SLA process";
                    uses ip-sla-process-config;
                } // END of config-container definition.
                container state {
                    config false;
                    description
                        "Operational state data for IP SLA";
                    uses ip-sla-process-config;
                } // END of state-container definition.
                container ip-sla-statistics {
                    config false;
                    description
                        "Statistics per SLA ID";
                    container state {
                        config false;
                        description
                            "Operational state data";
                        uses ip-sla-statistics-entries;
                    } // END of state-container definition.
                } // END of ip-sla-statistics-container definition.
                uses ip-sla-icmp-echo-configs;
            } // End of process-list
        } // END of processes-container definition.
    } // END of ip-sla-config definition.

    grouping  ip-sla-grouping {
    description
        "Grouping for IP SLA";
    container ip-sla {
        if-feature feature-list:HAVE_IPSLA;
        if-feature feature-list:HAVE_BFD;
        description
            "Grouping for IP SLA";
        uses ip-sla-config;
        uses ip-sla-schedule-configs;
    } // END of ip-sla-container definition.
    } // END of ip-sla-grouping definition.

    uses ip-sla-grouping;

    rpc ip-sla-clear-statistics {
        if-feature feature-list:HAVE_IPSLA;
        if-feature feature-list:HAVE_BFD;
        description "Use this RPC to clear the ipsla statistics";
        input  {
            leaf identifier  {
                type uint16 {
                    range "1..65535";
                }
                mandatory true;
                description "Use this attribute to clear the ipsla statistics.";
            }
        }
    }

    notification icmp-echo-threshold {
        if-feature feature-list:HAVE_IPSLA;
        if-feature feature-list:HAVE_BFD;

        description "icmp-echo-threshold event is generated when packet level RTT value is greater than the threshold value or within the threshold time response is not received.";

        leaf severity {
            type cml-data-types:cml_notif_severity_t;
            description "Notification severity level (value: CRITICAL)";
        }

        leaf eventClass {
            type cml-data-types:cml_notif_class_t;
            description "Notification event class (value: STATE)";
        }

        leaf host {
            type  ip_sla_hostname_t;
        description
            "Use this attribute to set the ICMP Echo host name or IP address.";
        }

        leaf identifier {
            type  uint16;
        description
            "Use this attribute to set the IPSLA.";
        }

        leaf threshold {
            type  uint16;
        description
            "The threshold value correlates to the limit the administrator sets as
                    what would be a successful test. Threshold can be configured in
                    milli-seconds.";
        }
    }

    notification icmp-echo-timeout {
        if-feature feature-list:HAVE_IPSLA;
        if-feature feature-list:HAVE_BFD;

        description "icmp-echo-timeout is generated when echo packet response is not received for any of the sent packets within the configured timeout value.";

        leaf severity {
            type cml-data-types:cml_notif_severity_t;
            description "Notification severity level (value: CRITICAL)";
        }

        leaf eventClass {
            type cml-data-types:cml_notif_class_t;
            description "Notification event class (value: STATE)";
        }

        leaf host {
            type  ip_sla_hostname_t;
        description
            "Use this attribute to set the ICMP Echo host name or IP address.";
        }

        leaf identifier {
            type  uint16;
        description
            "Use this attribute to set the IPSLA.";
        }

        leaf timeout {
            type  uint16;
        description
            "The timeout value correlates to how long the Ping application will
                    wait for the response after sending packets ICMP Echo packets.";
        }
    }

    notification icmp-echo-disconnect {
        if-feature feature-list:HAVE_IPSLA;
        if-feature feature-list:HAVE_BFD;

        description "icmp-echo-disconnect is generated when timeout is observed for any of the packet in sla measurement operation.";

        leaf severity {
            type cml-data-types:cml_notif_severity_t;
            description "Notification severity level (value: CRITICAL)";
        }

        leaf eventClass {
            type cml-data-types:cml_notif_class_t;
            description "Notification event class (value: STATE)";
        }

        leaf identifier {
            type  uint16;
        description
            "Use this attribute to set the IPSLA.";
        }
    }

}
