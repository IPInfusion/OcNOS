/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-acl-ipv6.yang
*
*/

submodule ipi-acl-ipv6 {

    yang-version 1.1;

    belongs-to  ipi-acl { prefix ipi-acl; }

    import feature-list {
        prefix feature-list;
        revision-date 2023-02-21;
    }

    import ipi-acl-types {
        prefix ipi-acl-types;
        revision-date 2022-06-01;
    }

    import ipi-acl-common {
        prefix ipi-acl-common;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for ACL IPV6 object";


    revision "2022-06-01" {
        description "Updated the yang file with feature";
        reference " 0.7.0.";
    }

    revision "2022-01-20" {
        description "Merged protocol-name and protocol-value into single attribute protocol-name";
        reference " 0.6.0.";
    }

    revision "2021-11-16" {
        description "IPV6 if-feature is added globally";
        reference " 0.5.0.";
    }

    revision "2021-10-29" {
        description "Remove RDN from forwarding-action for IPv6 Standard ACLs";
        reference " 0.4.0.";
    }

    revision "2021-09-03" {
        description "Update descriptions of attribute";
        reference " 0.3.0.";
    }

    revision "2021-08-18" {
        description "Changed ipv6/state to CONFIG_RUNTIME, to display default icmpv6 entry details in sget";
        reference " 0.2.0.";
    }

    revision "2021-07-14" {
        description "Restructured module as per OpenConfig style";
        reference " 0.1.0.";
    }

    grouping acl-ipv6-tcp-config {
        description
            "Configuration data specific for IPV6 TCP ACL entry";
        leaf tcp-flags  {
            if-feature feature-list:HAVE_CUSTOM1_ACL;
            type  ipi-acl-types:acl_tcp_flags_t;
            description "List of TCP flags to match";
        } // END of tcp-flags definition.

    } // END of acl-ipv6-tcp-config definition.
    grouping acl-ipv6-icmp-config {
        description
            "Configuration data specific for IPV6 ICMP ACL entry";
        leaf protocol-icmp  {
            type  empty;
            mandatory true;
            description "Use this attribute to indicates that protocol carried in the IP packet
                        is icmp.";
        } // END of protocol-icmp definition.

        leaf icmp-message  {
            if-feature feature-list:HAVE_CUSTOM1_ACL;
            type  ipi-acl-types:acl_icmpv6_options_t;
            description "Use this attribute to set ICMP message type";
        } // END of icmp-message definition.

        leaf icmp-type  {
            if-feature feature-list:HAVE_CUSTOM1_ACL;
            type  uint8 {
                 range "0..255"  {
                    description "0..255: Supported range 0 - 255";
                 }
            }
            description "Use this attribute to set ICMP type";
        } // END of icmp-type definition.

        leaf icmp-code  {
            when " /acl/acl-sets/acl-set/acl-entries/acl-entry/ipv6/config/icmp-type ";
            if-feature feature-list:HAVE_CUSTOM1_ACL;
            type  uint8 {
                 range "0..255"  {
                    description "0..255: Supported range 0 - 255";
                 }
            }
            description "Use this attribute to set ICMP sub-type";
        } // END of icmp-code definition.

    } // END of acl-ipv6-icmp-config definition.
    grouping acl-ipv6-sctp-config {
        description
            "Configuration data specific for IPV6 SCTP ACL entry";
        leaf protocol-sctp  {
            type  empty;
            mandatory true;
            description "Use this attribute to indicate that protocol carried in the IP packet
                        is sctp.";
        } // END of protocol-sctp definition.

        leaf sctp-source-port  {
            type  uint16 {
                 range "0..65535"  {
                    description "0..65535: Supported range 0 - 65535";
                 }
            }
            description "Use this attribute to set SCTP Source port";
        } // END of sctp-source-port definition.

        leaf sctp-destination-port  {
            type  uint16 {
                 range "0..65535"  {
                    description "0..65535: Supported range 0 - 65535";
                 }
            }
            description "Use this attribute to set SCTP destination port";
        } // END of sctp-destination-port definition.

    } // END of acl-ipv6-sctp-config definition.
    grouping acl-ipv6-config {
        description
            "Configuration data for IPV6 ACL entry";
        leaf source-address  {
            type  ipi-acl-types:acl_any_ipv6_src_addr_t;
            mandatory true;
            description "Source IPv6 address prefix.";
        } // END of source-address definition.

        leaf destination-address  {
            type  ipi-acl-types:acl_any_ipv6_dest_addr_t;
            mandatory true;
            description "Destination IPv6 address prefix.";
        } // END of destination-address definition.

        leaf dscp  {
            type  ipi-acl-types:acl_dscp_t;
            description "Use this attribute to set the value of Differentiated Services Code
                        Point.";
        } // END of dscp definition.

        leaf inner-vlan-id  {
            if-feature feature-list:HAVE_CUSTOM1_ACL;
            type  uint16 {
                 range "1..4094"  {
                    description "1..4094: Supported range 1 - 4094";
                 }
            }
            description "Use this attribute to set the inner-vlan-id";
        } // END of inner-vlan-id definition.

        leaf flow-label  {
            if-feature feature-list:HAVE_CUSTOM1_ACL;
            type  uint32 {
                 range "0..1048575"  {
                    description "0..1048575: Supported range 0 - 1048575";
                 }
            }
            description "Use this attribute to set IPv6 Flow label";
        } // END of flow-label definition.

        choice protocol {
            description
                "Protocol Types";
            case tcp {

                description
                    "Transmission Control Protocol";

                uses ipi-acl-common:acl-tcp-config;
                uses acl-ipv6-tcp-config;
            }
            case udp {

                description
                    "User Datagram Protocol";

                uses ipi-acl-common:acl-udp-config;
            }
            case icmp {

                description
                    "Internet Control Message Protocol";

                uses acl-ipv6-icmp-config;
            }
            case sctp {

                description
                    "Stream Control Transmission Protocol";

                uses acl-ipv6-sctp-config;
            }
            case other-protocols {

                description
                    "Other protocols";

                leaf protocol-name  {
                    type  ipi-acl-types:acl_ipv6_protocols_t;
                    mandatory true;
                    description "Use this attribute to set the protocol carried in the IP packet,
                                expressed by its name.";
                } // END of protocol-name definition.

            }
        } // END of protocol-choice definition.
    } // END of acl-ipv6-config definition.
    grouping acl-standard-ipv6-config {
        description
            "Configuration data for Standard IPV6 ACL set";
        leaf source-address  {
            type  ipi-acl-types:acl_any_ipv6_src_addr_t;
            description "Source IPv6 address prefix.";
        } // END of source-address definition.

        leaf forwarding-action  {
            type  ipi-acl-types:acl_forwarding_action_t;
            mandatory true;
            description "Specifies the forwarding action. One forwarding action must be
                        specified for each ACL entry.";
        } // END of forwarding-action definition.

    } // END of acl-standard-ipv6-config definition.

    grouping  ipv6-grouping {
    description
        "IPV6 ACL set configuration attributes";
    container ipv6 {
        if-feature feature-list:HAVE_IPV6;
        if-feature feature-list:HAVE_ACL;
        description
            "IPV6 ACL set configuration attributes";
        container config {
            description
                "ACL global configuration attributes";
            uses ipi-acl-common:acl-common-config;
            uses acl-ipv6-config;
            uses ipi-acl-common:acl-ip-config;
        } // END of config-container definition.
        container state {
            config false;
            description
                "Global Operational data for ACL";
            container counters {
                config false;
                description
                    "Counter data for ACL entries";
                uses ipi-acl-common:acl-counters;
            } // END of counters-container definition.
            uses ipi-acl-common:acl-common-config;
            uses acl-ipv6-config;
            uses ipi-acl-common:acl-ip-config;
        } // END of state-container definition.
        container fragment-actions {
            if-feature feature-list:HAVE_CUSTOM1_ACL;
            description
                "Container for fragmented packet actions";
            container config {
                description
                    "Fragments action configuration attributes";
                uses ipi-acl-common:acl-fragments-config;
            } // END of config-container definition.
            container state {
                config false;
                description
                    "Fragments action state information";
                uses ipi-acl-common:acl-fragments-config;
            } // END of state-container definition.
        } // END of fragment-actions-container definition.
    } // END of ipv6-container definition.
    } // END of ipv6-grouping definition.

    grouping  ipv6-acl-entries-grouping {
    description
        "Container for IPV6 Standard ACL entries";
    container ipv6-acl-entries {
        if-feature feature-list:HAVE_IPV6;
        if-feature feature-list:HAVE_ACL;
        description
            "Container for IPV6 Standard ACL entries";

        list ipv6-acl-entry {
            key "source-address";
            description
                "List of IPV6 ACL entries comprising an ACL set";
            leaf source-address  {
                type  leafref {
                    path  "../config/source-address";
                }
                description "Source IPv6 address prefix.";
            } // END of source-address definition.

            container config {
                description
                    "Standard ACL set configuration attributes";
                uses acl-standard-ipv6-config;
            } // END of config-container definition.
            container state {
                config false;
                description
                    "Standard ACL set state information";
                uses acl-standard-ipv6-config;
            } // END of state-container definition.
        } // End of ipv6-acl-entry-list
    } // END of ipv6-acl-entries-container definition.
    } // END of ipv6-acl-entries-grouping definition.


}
