/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-acl-ports.yang
*
*/

submodule ipi-acl-ports {

    yang-version 1.1;

    belongs-to  ipi-acl { prefix ipi-acl; }

    import feature-list {
        prefix feature-list;
        revision-date 2023-02-21;
    }

    import ipi-acl-types {
        prefix ipi-acl-types;
        revision-date 2022-06-01;
    }

    import ipi-interface {
        prefix ipi-interface;
        revision-date 2022-08-24;
    }

    import ietf-yang-types {
        prefix yang;
        revision-date 2013-07-15;
    }

    include ipi-acl-arp { revision-date 2022-06-01;}
    include ipi-acl-mac { revision-date 2022-06-01;}
    include ipi-acl-ipv6 { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Datamodel for ACL Ports object";


    revision "2022-06-01" {
        description "Updated the yang file with feature";
        reference " 0.6.0.";
    }

    revision "2021-11-16" {
        description "Added some if-feature to fix customer SKU compilation";
        reference " 0.5.0.";
    }

    revision "2021-08-16" {
        description "Added dependencies for correcting the order of API execution";
        reference " 0.4.0.";
    }

    revision "2021-08-02" {
        description "Changed acl-name as RDN";
        reference " 0.3.0.";
    }

    revision "2021-07-14" {
        description "Restructured module as per OpenConfig style";
        reference " 0.2.0.";
    }

    revision "2016-11-17" {
        description "Initial Version";
        reference " 0.1.0.";
    }

    grouping acl-type-config {
        description
            "ACL type configuration data for interface";
        leaf acl-type  {
            type  ipi-acl-types:acl_types_t;
            description "The type of the access-list set applied on the interface (e.g., ip,
                        ipv6, etc.)";
        } // END of acl-type definition.

    } // END of acl-type-config definition.
    grouping acl-interface-config {
        description
            "ACL configuration data for interface";
        leaf acl-name  {
            type  string {
                length "1..1965";
                pattern "[^?' =,>|]+";
            }
            description "The name of the access-list set applied on the interface";
        } // END of acl-name definition.

        leaf time-range  {
            type  string {
                length "1..1965";
                pattern "[^?' =,>|]+";
            }
            description "The time-range associated with this access-group";
        } // END of time-range definition.

    } // END of acl-interface-config definition.
    grouping acl-interface-name-config {
        description
            "Configuration data for interface name";
        leaf name  {
            type  leafref {
                path  "/ipi-interface:interfaces/ipi-interface:interface/ipi-interface:name";
            }
            description "Reference to the base interface name";
        } // END of name definition.

    } // END of acl-interface-name-config definition.
    grouping acl-vty-config {
        description
            "ACL configuration data for vty line";
        leaf acl-type  {
            type  ipi-acl-types:acl_vty_types_t;
            description "The type of the access-list set applied on vty line (e.g., ip, ipv6,
                        etc.)";
        } // END of acl-type definition.

        leaf acl-name  {
            type  string {
                length "1..1965";
                pattern "[^?' =,>|]+";
            }
            description "The name of the access-list set applied on vty line";
        } // END of acl-name definition.

    } // END of acl-vty-config definition.
    grouping acl-summary-state {
        description
            "ACL Operational Information";
        leaf statistics-enabled  {
            type  empty;
            description "This attribute indicates if statistics enabled for the acl-set";
        } // END of statistics-enabled definition.

    } // END of acl-summary-state definition.
    grouping acl-summary-counter {
        description
            "ACL Counter Info";
        leaf total-acl-entries  {
            type  yang:counter32;
            description "Total acl entries configured in the acl-set";
        } // END of total-acl-entries definition.

    } // END of acl-summary-counter definition.
    grouping acl-interface-summary-state {
        description
            "ACL Interface Operational Info";
        leaf interface-name  {
            type  leafref {
                path  "/ipi-interface:interfaces/ipi-interface:interface/ipi-interface:name";
            }
            description "Reference to the base interface name";
        } // END of interface-name definition.

        leaf filter-direction  {
            type  ipi-acl-types:acl_filter_direction_t;
            description "Direction in which the ACL is applied - ingress or egress";
        } // END of filter-direction definition.

        leaf interface-type  {
            type  ipi-acl-types:acl_interface_type_t;
            description "Interface type - Port or Router";
        } // END of interface-type definition.

        leaf interface-status  {
            type  ipi-acl-types:acl_interface_status_t;
            description "Interface status - active or inactive";
        } // END of interface-status definition.

    } // END of acl-interface-summary-state definition.
    grouping acl-vty-summary-state {
        description
            "ACL VTY Operational Info";
        leaf filter-direction  {
            type  ipi-acl-types:acl_filter_direction_t;
            description "Direction in which the ACL is applied - ingress or egress";
        } // END of filter-direction definition.

    } // END of acl-vty-summary-state definition.
    grouping acl-interface-access-groups-top {
        description
            "ACL interface related Configurations";
        container access-groups {
            description
                "ACL interface configs";

            list access-group {
                key "acl-name";
                max-elements 1;
                description
                    "List of ACLs for the interface";
                leaf acl-name  {
                    type  leafref {
                        path  "../config/acl-name";
                    }
                    description "The name of the access-list set applied on the interface";
                } // END of acl-name definition.

                container config {
                    description
                        "ACL interface related Configurations";
                    uses acl-interface-config;
                } // END of config-container definition.
                container state {
                    config false;
                    description
                        "Operational data for ACL interface";
                    uses acl-interface-config;
                } // END of state-container definition.
            } // End of access-group-list
        } // END of access-groups-container definition.
    } // END of acl-interface-access-groups-top definition.

    grouping  interfaces-grouping {
    description
        "ACL interface related Configurations";
    container interfaces {
        if-feature feature-list:HAVE_ACL;
        description
            "ACL interface related Configurations";

        list interface {
            key "name";
            description
                "ACL interface list";
            leaf name  {
                type  leafref {
                    path  "../config/name";
                }
                description "Reference to the base interface name";
            } // END of name definition.

            container config {
                description
                    "ACL interface related Configurations";
                uses acl-interface-name-config;
            } // END of config-container definition.
            container state {
                config false;
                description
                    "Operational data for ACL interface";
                uses acl-interface-name-config;
            } // END of state-container definition.
            container ingress-acl-sets {
                description
                    "Container for Ingress ACL sets";

                list ingress-acl-set {
                when " /acl/interfaces/interface/ingress-acl-sets/ingress-acl-set/access-groups/access-group/acl-name ";
                    key "acl-type";
                    description
                        "List of Ingress ACL sets, each comprising of a list of ACL entries";
                    leaf acl-type  {
                        type  leafref {
                            path  "../config/acl-type";
                        }
                        description "The type of the access-list set applied on the interface (e.g., ip,
                                    ipv6, etc.)";
                    } // END of acl-type definition.

                    container config {
                        description
                            "ACL interface related Configurations";
                        uses acl-type-config;
                    } // END of config-container definition.
                    container state {
                        config false;
                        description
                            "Operational data for ACL interface";
                        uses acl-type-config;
                    } // END of state-container definition.
                    uses acl-interface-access-groups-top;
                } // End of ingress-acl-set-list
            } // END of ingress-acl-sets-container definition.
            container egress-acl-sets {
                description
                    "Container for Egress ACL sets";

                list egress-acl-set {
                when " /acl/interfaces/interface/egress-acl-sets/egress-acl-set/access-groups/access-group/acl-name ";
                    key "acl-type";
                    description
                        "List of Egress ACL sets, each comprising of a list of ACL entries";
                    leaf acl-type  {
                        type  leafref {
                            path  "../config/acl-type";
                        }
                        description "The type of the access-list set applied on the interface (e.g., ip,
                                    ipv6, etc.)";
                    } // END of acl-type definition.

                    container config {
                        description
                            "ACL interface related Configurations";
                        uses acl-type-config;
                    } // END of config-container definition.
                    container state {
                        config false;
                        description
                            "Operational data for ACL interface";
                        uses acl-type-config;
                    } // END of state-container definition.
                    uses acl-interface-access-groups-top;
                } // End of egress-acl-set-list
            } // END of egress-acl-sets-container definition.
        } // End of interface-list
    } // END of interfaces-container definition.
    } // END of interfaces-grouping definition.

    grouping  vty-line-grouping {
    description
        "ACL vty-line related Configurations";
    container vty-line {
        if-feature feature-list:HAVE_ACL;
        description
            "ACL vty-line related Configurations";
        container ingress-acl-sets {
            description
                "Container for Ingress ACL sets";

            list ingress-acl-set {
                key "acl-type";
                description
                    "List of Ingress ACL sets, each comprising of a list of ACL entries";
                leaf acl-type  {
                    type  leafref {
                        path  "../config/acl-type";
                    }
                    description "The type of the access-list set applied on vty line (e.g., ip, ipv6,
                                etc.)";
                } // END of acl-type definition.

                container config {
                    description
                        "ACL vty-line related Configurations";
                    uses acl-vty-config;
                } // END of config-container definition.
                container state {
                    config false;
                    description
                        "Operational data for ACL interface";
                    uses acl-vty-config;
                } // END of state-container definition.
            } // End of ingress-acl-set-list
        } // END of ingress-acl-sets-container definition.
        container egress-acl-sets {
            description
                "Container for Egress ACL sets";

            list egress-acl-set {
                key "acl-type";
                description
                    "List of Egress ACL sets, each comprising of a list of ACL entries";
                leaf acl-type  {
                    type  leafref {
                        path  "../config/acl-type";
                    }
                    description "The type of the access-list set applied on vty line (e.g., ip, ipv6,
                                etc.)";
                } // END of acl-type definition.

                container config {
                    description
                        "ACL vty-line related Configurations";
                    uses acl-vty-config;
                } // END of config-container definition.
                container state {
                    config false;
                    description
                        "Operational data for ACL interface";
                    uses acl-vty-config;
                } // END of state-container definition.
            } // End of egress-acl-set-list
        } // END of egress-acl-sets-container definition.
    } // END of vty-line-container definition.
    } // END of vty-line-grouping definition.

    grouping  summary-info-grouping {
    description
        "ACL run-time attributes";
    container summary-info {
        if-feature feature-list:HAVE_ACL;
        config false;
        description
            "ACL run-time attributes";
        container state {
            config false;
            description
                "ACL Operational Info";
            container counters {
                config false;
                description
                    "ACL Counters";
                uses acl-summary-counter;
            } // END of counters-container definition.
            uses acl-summary-state;
        } // END of state-container definition.
        container interfaces {
            config false;
            description
                "ACL interfaces";

            list interface {
                key "interface-name";
                config false;
                description
                    "ACL interface list";
                leaf interface-name  {
                    type  leafref {
                        path  "../state/interface-name";
                    }
                    description "Reference to the base interface name";
                } // END of interface-name definition.

                container state {
                    config false;
                    description
                        "ACL Interface Operational Info";
                    uses acl-interface-summary-state;
                } // END of state-container definition.
            } // End of interface-list
        } // END of interfaces-container definition.
        container vty-line {
            config false;
            description
                "Virtual Terminal Line";
            container state {
                config false;
                description
                    "VTY Operational Info";
                uses acl-vty-summary-state;
            } // END of state-container definition.
        } // END of vty-line-container definition.
    } // END of summary-info-container definition.
    } // END of summary-info-grouping definition.


}
