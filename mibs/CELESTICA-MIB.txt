CELESTICA-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

celestica MODULE-IDENTITY
    LAST-UPDATED "202507100000Z"
    ORGANIZATION "Celestica Corporation"
    CONTACT-INFO
        "http://www.celestica.com"
    DESCRIPTION
        "The Celestica Corporation enterprise Module Identity."

    REVISION "202507100000Z"
        DESCRIPTION "Initial revision."

    ::= { cmmStackUnitModelName 12244 }

celesticaOIDS OBJECT IDENTIFIER ::= { celestica 1 }
celesticaProducts OBJECT IDENTIFIER ::= { celestica 2 }
celesticaREDSTONED2060 OBJECT IDENTIFIER ::= { celesticaProducts 1 }
celesticaSEASTONEDX010 OBJECT IDENTIFIER ::= { celesticaProducts 2 }
celesticaSEASTONE2DX030 OBJECT IDENTIFIER ::= { celesticaProducts 3 }
celesticaSEASTONE2DS3000 OBJECT IDENTIFIER ::= { celesticaProducts 4 }
celesticaSILVERSTONER1141 OBJECT IDENTIFIER ::= { celesticaProducts 5 }
celesticaSILVERSTONER4023 OBJECT IDENTIFIER ::= { celesticaProducts 6 }
celesticaBELGITEE1070 OBJECT IDENTIFIER ::= { celesticaProducts 7 }

END
