-- /* Copyright (C) 2001-2026 IP Infusion, Inc. All Rights Reserved. */

    IPI-CMM-CMIS-MODULE-MIB DEFINITIONS ::= BEGIN

    --  This module provides authoritative definitions for
    --    Common Management Interface Specification (CMIS).
    --
    --  This module will be extended, as needed.
    --

    IMPORTS
        OBJECT-TYPE, MODULE-IDENTITY,
        Unsigned32, TimeTicks, NOTIFICATION-TYPE
            FROM SNMPv2-SMI
        DateAndTime, DisplayString, TruthValue,
        MacAddress, RowStatus, TEXTUAL-CONVENTION
            FROM SNMPv2-TC
        MODULE-COMPLIANCE, OBJECT-GROUP, NOTIFICATION-GROUP
            FROM SNMPv2-CONF
        enterprises,OBJECT-IDENTITY
            FROM SNMPv2-SMI
      ipi FROM IPI-MODULE-MIB
      cmmChassisObject,
      cmmStackUnitIndex FROM IPI-CMM-CHASSIS-MIB
      ConnectorType, MediaInterfaceTechEncodings FROM IPI-CMM-CMIS-8024-MIB;

   cmm  MODULE-IDENTITY
   LAST-UPDATED "202206230000Z"   -- 2022 Jun 23, 12:00:00 GMT
   ORGANIZATION "IP Infusion"
   CONTACT-INFO "support@ipinfusion.com"

   DESCRIPTION
      "The Structure of CMM Common Management Interface Specification (CMIS) for
       the IPI enterprise."
   REVISION "202206230000Z"
   DESCRIPTION
      "Complying to level 3 of SMILINT"
   ::= { ipi 100 }


    -- ### Groups ###

    cmmCmisModule      OBJECT IDENTIFIER ::={ cmmChassisObject 20 }

    cmmCmisModuleObjects          OBJECT IDENTIFIER ::={ cmmCmisModule 1 }
    cmmCmisModuleMonitorObjects   OBJECT IDENTIFIER ::={ cmmCmisModule 2 }

    -- ### Textual Convention
    CmisInterfaceType ::= TEXTUAL-CONVENTION
      STATUS      current
      DESCRIPTION
          "The interface type value for CMIS module."
      SYNTAX  INTEGER   {
                          if-undefined(-1),
                          if-1000base-cx(1),
                          if-xaui(2),
                          if-xfi(3),
                          if-sfi(4),
                          if-25gaui-c2m(5),
                          if-xlaui-c2m(6),
                          if-xlppi(7),
                          if-laui-2-c2m(8),
                          if-50gaui-2-c2m(9),
                          if-50gaui-1-c2m(10),
                          if-caui-4-c2m(11),
                          if-100gaui-4-c2m(12),
                          if-100gaui-2-c2m(13),
                          if-200gaui-8-c2m(14),
                          if-200gaui-4-c2m(15),
                          if-400gaui-16-c2m(16),
                          if-400gaui-8-c2m(17),
                          if-10gbase-cx4(18),
                          if-ca-25g-l(19),
                          if-ca-25g-s(20),
                          if-ca-25g-n(21),
                          if-40gbase-cr4(22),
                          if-50gbase-cr(23),
                          if-100gbase-cr10(24),
                          if-100gbase-cr4(25),
                          if-100gbase-cr2(26),
                          if-200gbase-cr4(27),
                          if-400g-cr8(28),
                          if-caui-4-c2m-without-fec(29),
                          if-caui-4-c2m-with-rs-fec(30),
                          if-50gbase-cr2-with-rs-fec(31),
                          if-50gbase-cr2-with-base-r-fire-code-fec(32),
                          if-50gbase-cr2-with-no-fec(33),
                          if-100gbase-cr1(34),
                          if-200gbase-cr2(35),
                          if-400gbase-cr4(36),
                          if-800gbase-cr8(37),
                          if-100gaui-1-s-c2m(38),
                          if-100gaui-1-l-c2m(39),
                          if-200gaui-2-s-c2m(40),
                          if-200gaui-2-l-c2m(41),
                          if-400gaui-4-s-c2m(42),
                          if-400gaui-4-l-c2m(43),
                          if-800gaui-8-s-c2m(44),
                          if-800guai-8-l-c2m(45),
                          if-10gbase-sw(46),
                          if-10gbase-sr(47),
                          if-25gbase-sr(48),
                          if-40gbase-sr4(49),
                          if-40ge-swdm4-msa-spec(50),
                          if-40ge-bidi(51),
                          if-50gbase-sr(52),
                          if-100gbase-sr10(53),
                          if-100gbase-sr4(54),
                          if-100ge-swdm4-msa-spec(55),
                          if-100ge-bidi(56),
                          if-100gbase-sr2(57),
                          if-100gbase-sr(58),
                          if-200gbase-sr4(59),
                          if-400gbase-sr16(60),
                          if-400gbase-sr8(61),
                          if-400gbase-sr4(62),
                          if-800gbase-sr8(63),
                          if-400gbase-sr4point2(64),
                          if-200gbase-sr2(65),
                          if-100gbase-vr(66),
                          if-200gbase-vr2(67),
                          if-400gbase-vr4(68),
                          if-10gbase-lw(69),
                          if-10gbase-ew(70),
                          if-10g-zw(71),
                          if-10gbase-lr(72),
                          if-10gbase-er(73),
                          if-10g-zr(74),
                          if-25gbase-lr(75),
                          if-25gbase-er(76),
                          if-40gbase-lr4(77),
                          if-40gbase-fr(78),
                          if-50gbase-fr(79),
                          if-50gbase-lr(80),
                          if-100gbase-lr4(81),
                          if-100gbase-er4(82),
                          if-100g-psm4-msa-spec(83),
                          if-100g-cwdm4-msa-spec(84),
                          if-100g-4wdm-10-msa-spec(85),
                          if-100g-4wdm-20-msa-spec(86),
                          if-100g-4wdm-40-msa-spec(87),
                          if-100gbase-dr(88),
                          if-100g-fr-msa-spec-or-100gbase-fr1(89),
                          if-100g-lr-msa-spec-or-100gbase-lr1(90),
                          if-200gbase-dr4(91),
                          if-200gbase-fr4(92),
                          if-200gbase-lr4(93),
                          if-400gbase-fr8(94),
                          if-400gbase-lr8(95),
                          if-400gbase-dr4(96),
                          if-400g-fr4-msa-spec-or-400gbase-fr4(97),
                          if-400g-lr4-10-msa-spec(98),
                          if-100g-cwdm4-ocp(99),
                          if-400zr-dwdm-amplified(100),
                          if-400zr-singlewavelen-unamp(101),
                          if-50gbase-er(102),
                          if-200gbase-er4(103),
                          if-400gbase-er8(104),
                          if-400gbase-lr4-6(105),
                          if-100gbase-zr(106),
                          if-zr400-ofec-16qam(107),
                          if-zr300-ofec-8qam(108),
                          if-zr200-ofec-qpsk(109),
                          if-zr100-ofec-qpsk(110),
                          if-100g-lr1-20-msa-spec(111),
                          if-100g-er1-30-msa-spec(112),
                          if-100g-er1-40-msa-spec(113),
                          if-400gbase-zr(114),
                          if-10gbase-br(115),
                          if-25gbase-br(116),
                          if-50gbase-br(117),
                          if-400zrp-dwdm-amplified-450km(118),
                          if-100zrp-dwdm-amplified-600km(119),
                          if-100zrp-dwdm-amplified-1000km(120),
                          if-100zrp-dwdm-amplified-2000km(121),
                          if-400zrp-dwdm-amplified-120km(122),
                          if-400zrp-dwdm-amplified-450km-ec(123),
                          if-100zrp-dwdm-amplified-600km-ec(124),
                          if-zr400-ofec-16qam-ep(125),
                          if-zr200-ofec-16qam(126),
                          if-copper-cable(127),
                          if-passive-loopback-module(128),
                          if-active-cable-assembly-with-ber-lessthan-10exp-neg12(129),
                          if-active-cable-assembly-with-ber-lessthan-5x10exp-neg5(130),
                          if-active-cable-assembly-with-ber-lessthan-2point6x10exp-neg4(131),
                          if-active-cable-assembly-with-ber-lessthan-10exp-6(132),
                          if-active-loopback-module(133),
                          if-1000base-t(134),
                          if-twopoint5gbase-t(135),
                          if-5gbase-t(136),
                          if-10gbase-t(137),
                          if-25gbase-t(138),
                          if-40gbase-t(139),
                          if-50gbase-t(140),
                          if-4i1-9d1f(141),
                          if-4l1-9c1f(142),
                          if-4l1-9d1f(143),
                          if-c4s1-9d1f(144),
                          if-c4s1-4d1f(145),
                          if-4i1-4d1f(146),
                          if-8r1-4d1f(147),
                          if-8i1-4d1f(148),
                          if-foic1point4-do(149),
                          if-foic2point8-do(150),
                          if-foic4point8-do(151),
                          if-foic2point4-do(152),
                          if-otl4point4(153),
                          if-otl4point2(154),
                          if-foic1point4(155),
                          if-foic1point2(156),
                          if-800gbase-cr4(157),
                          if-800gaui-4(158),
                          if-800gbase-vr8(159),
                          if-800g-vr4point2(160),
                          if-800g-sr4point2(161),
                          if-800gbase-dr8(162),
                          if-800gbase-dr8-2(163),
                          if-800gbase-dr4(164),
                          if-800gbase-dr4-2(165),
                          if-800gbase-fr4-500(166),
                          if-800gbase-fr4(167),
                          if-800gbase-lr4(168),
                          if-800gbase-lr1(169),
                          if-800gbase-er1-20(170),
                          if-800gbase-er1(171),
                          if-flexo-8e-do-16qam-foice8point8-do(172),
                          if-flexo-8-do-16qam-foic8point8-do(173),
                          if-flexo-8e-dpo-16qam-foice8point8-dpo(174),
                          if-flexo-8-dpo-16qam-foic8point8-dpo(175),
                          if-flexo-6e-dpo-16qam-foic6e-dpo(176),
                          if-flexo-6-dpo-16qam-foicpointe-dpo(177),
                          if-800zr-a-150ghz-dwdm-tx-output-range-a(178),
                          if-800zr-b-150ghz-dwdm-tx-output-range-b(179),
                          if-800zr-c-150ghz-dwdm-tx-output-range-c(180),
                          if-200gbase-cr1(181),
                          if-400gbase-cr2(182),
                          if-1point6taui-16-s-c2m(183),
                          if-1point6taui-16-l-c2m(184),
                          if-1point6tbase-cr8(185),
                          if-200gaui-1(186),
                          if-400gaui-2(187),
                          if-1point6taui-8(188),
                          if-1point6t-vr8point2(189),
                          if-1point6t-sr8point2(190),
                          if-zr400-ofec-16qam-ha(191),
                          if-zr400-ofec-16qam-hb(192),
                          if-zr400-ofec-8qam-ha(193),
                          if-400gbase-dr4-2(194),
                          if-zr400-ofec-8qam-hb(195),
                          if-zr300-ofec-8qam-ha(196),
                          if-zr300-ofec-8qam-hb(197),
                          if-zr200-ofec-qpsk-ha(198),
                          if-zr200-ofec-qpsk-hb(199),
                          if-zr100-ofec-qpsk-ha(200),
                          if-zr100-ofec-qpsk-hb(201),
                          if-flexo-4-do-16qam--foic4point8-do(202),
                          if-flexo-3-do-8qam--foic3point6-do(203),
                          if-flexo-2-do-qpsk--foic2point4-do(204),
                          if-flexo-2-do-16qam--foic2point8-do(205),
                          if-flexo-1-do-qpsk--foic1point4-do(206),
                          if-flexo-4e-do-qpsk--foic4epoint4-do(207),
                          if-flexo-4-do-qpsk--foic4point4-do(208),
                          if-400g-er4-30(209),
                          if-foic1point1-rs(210),
                          if-200gbase-dr1(211),
                          if-200gbase-dr1-2(212),
                          if-400gbase-dr2(213),
                          if-400gbase-dr2-2(214),
                          if-1point6tbase-dr8(215),
                          if-1point6tbase-dr8-2(216),
                          if-custom-100gofec31point5(1001),
                          if-custom-200gofec31point5(1002),
                          if-custom-otnmax200gsfec35(1003),
                          if-custom-otnmax200gsfec58(1004),
                          if-custom-pktmax200gsfec60(1005),
                          if-custom-pktmax300gsfec65(1006),
                          if-custom-otnmax300gsfec70(1007),
                          if-custom-pktmax400sfec65(1008),
                          if-custom-pktmax400sfec70(1009),
                          if-custom-otnmax400sfec70(1010),
                          if-custom-200gbase-dr2(2001),
                          if-custom-800gbase-fr8(3001),
                          if-custom-200gbase-fr2(3002),
                          if-custom-100gbase-fr1(3003),
                          if-custom-100g-client-only(4001),
                        }

    CmisBitRate ::= TEXTUAL-CONVENTION
      STATUS      current
      DESCRIPTION
          "The bit rate value for CMIS module."
      SYNTAX  INTEGER   {
                          undefined(-1),
                          zeropoint125(1),
                          zeropoint20(2),
                          zeropoint40(3),
                          zeropoint80(4),
                          onepoint12(5),
                          onepoint25(6),
                          twopoint00(7),
                          twopoint50(8),
                          threepoint125(9),
                          threepoint20(10),
                          fivepoint00(11),
                          ninepoint25(12),
                          ninepoint95(13),
                          ninepoint953(14),
                          ninepoint95328(15),
                          ninepoint95-11point18(16),
                          tenpoint00(17),
                          tenpoint31(18),
                          tenpoint3125(19),
                          twelvepoint50(20),
                          twentypoint625(21),
                          twentyfivepoint00(22),
                          twentyfivepoint78(23),
                          twentyfivepoint78125(24),
                          twentysixpoint5625(25),
                          twentysevenpoint9523(26),
                          twentysevenpoint9524(27),
                          twentysevenpoint9525(28),
                          twentyeightpoint00(29),
                          thirtypoint069273(30),
                          thirtyonepoint5697(31),
                          fortypoint00(32),
                          fortyonepoint25(33),
                          fiftypoint00(34),
                          fiftyonepoint56(35),
                          fiftythreepoint125(36),
                          fiftythree53point13(37),
                          fiftyninepoint84375(38),
                          sixtypoint1385468(39),
                          sixtythreepoint1395(40),
                          onehundredthreepoint13(41),
                          onehundredsixpoint25(42),
                          oneelevenpoint81(43),
                          onetwelvepoint00(44),
                          onetwentypoint277094(45),
                          onetwentysixpoint28(46),
                          twotwelvepoint50(47),
                          twotwentyfourpoint00(48),
                          twofortypoint554187(49),
                          twofiftytwopoint56(50),
                          threesixtypoint831281(51),
                          fourtwentyfivepoint00(52),
                          fourfortysevenpoint00(53),
                          fourseventyeightpoint75(54),
                          foureightonepoint108374(55),
                          fivenotfivepoint12(56),
                          eightfiftypoint00(57),
                          not-applicable(58),
                          onethirteenpoint4375(59),
                          oneeighteenpoint2(60),
                          oneeighteenpoint203350603(61),
                          oneeighteenpoint749324509(62),
                          onetwentythreepoint6364(63),
                          onetwentyfourpoint101712814(64),
                          onetwentyfourpoint674930887(65),
                          onethirtyonepoint337056226(66),
                          onethirtyonepoint348528160(67),
                          ninefourtyfivepoint626804824(68),
                          ninefourtyninepoint994596072(69),
                          nineninetytwopoint813702512(70),
                          nineninetysevenpoint399447096(71),
                          tenfiftypoint696449808(72),
                          tenfiftypoint788225280(73),
                          onethousandsevenhundred(74),
                          eightypoint1847291(75),
                          fivenotfivepoint115743(76),
                          sixtythreepoint1394679(77),
                          threeseventyeightpoint836807(78),
                          twofiftytwopoint557871(79),
                          thirtyonepoint569734(80),
                          onetwentysixpoint278935(81),
                          fourseventytwopoint813402412(82),
                          fourninetysixpoint406851256(83),
                          custom-thirtyonepointfive(1001),
                          custom-thirtyfive(1002),
                          custom-fiftyeight(1003),
                          custom-sixty(1004),
                          custom-sixtyfive(1005),
                          custom-seventy(1006),
                          custom-onehundred(1007),
                          custom-twohundred(1008),
                          custom-threehundred(1009),
                          custom-fourhundred(1010)
                        }

    CmisModulationFormat ::= TEXTUAL-CONVENTION
      STATUS      current
      DESCRIPTION
          "The modulation format types for CMIS module."
      SYNTAX  INTEGER   {
                          undefined(-1),
                          nrz(1),
                          pam4(2),
                          dp-qpsk(3),
                          dp-8qam(4),
                          dp-16qam(5),
                          pam5(6),
                          pam16(7),
                          none(8),
                          pcs(9),
                          custom-psc16qam(1001)
                        }

    CmisDurationsTime ::= TEXTUAL-CONVENTION
      STATUS      current
      DESCRIPTION
          "The duration time for CMIS module."
      SYNTAX  INTEGER   {
                          timelessthan1ms(1),
                          timebetween1msto5ms(2),
                          timebetween5msto10ms(3),
                          timebetween10msto50ms(4),
                          timebetween50msto100ms(5),
                          timebetween100msto500ms(6),
                          timebetween500msto1s(7),
                          timebetween1sto5s(8),
                          timebetween5sto10s(9),
                          timebetween10sto1min(10),
                          timebetween1minto5min(11),
                          timebetween5minto10min(12),
                          timebetween10minto50min(13),
                          timegreaterthan50min(14)
                        }

    CmisPrbsTypes ::= TEXTUAL-CONVENTION
    STATUS      current
    DESCRIPTION
    "The supported prbs types for CMIS module."
    SYNTAX  BITS    {
                        prbs-31q(0),
                        prbs-31(1),
                        prbs-23q(2),
                        prbs-23(3),
                        prbs-15q(4),
                        prbs-15(5),
                        prbs-13q(6),
                        prbs-13(7),
                        prbs-9q(8),
                        prbs-9(9),
                        prbs-7q(10),
                        prbs-7(11),
                        ssprq(12),
                        reserved(13),
                        vendor-defined(14),
                        programmable(15)
                     }

    CmisLanesAssigned ::= TEXTUAL-CONVENTION
      STATUS      current
      DESCRIPTION
      "The supported host and media lane types for CMIS module."
      SYNTAX  BITS    {
                         lane-1(0),
                         lane-2(1),
                         lane-3(2),
                         lane-4(3),
                         lane-5(4),
                         lane-6(5),
                         lane-7(6),
                         lane-8(7)
                      }

    CmisHostAttrFlags ::= TEXTUAL-CONVENTION
      STATUS      current
      DESCRIPTION
      "The Cmis module host lane attr flags type."
      SYNTAX          INTEGER
                              {
                                  txloss(1),
                                  txcdrlol(2),
                                  txadaptiveeqfailure(3),
                                  rxoutputstatus(4),
                                  fecexcessivedegrade(5),
                                  fecdetecteddegrade(6),
                                  remotedegrade(7),
                                  localdegrade(8),
                                  flexelossofpadblock(9),
                                  flexelossofmultiframe(10),
                                  flexelossofframe(11),
                                  flexeinstanceidmismatch(12),
                                  flexecalendermismatch(13),
                                  flexeinstancemapmismatch(14),
                                  flexegidmismatch(15),
                                  txlocalfault(16),
                                  txremotefault(17),
                                  txlossofalignment(18),
                                  rxlocalfault(19),
                                  rxremotefault(20),
                                  rxlossofalignment(21),
                                  flexeremotephyfault(22)
                              }

    CmisHostAttrMonitorings ::= TEXTUAL-CONVENTION
      STATUS      current
      DESCRIPTION
      "The Cmis module media lane attr monitorings type."
      SYNTAX          INTEGER
                              {
                                  esnrinput(1),
                                  pam4leveltrans(2),
                                  prefecbermin(3),
                                  prefecbermax(4),
                                  prefecberaverage(5),
                                  prefecbercurrent(6),
                                  fercmin(7),
                                  fercmax(8),
                                  fercaverage(9),
                                  ferccurrent(10),
                                  ferctotal(11),
                                  txbits(12),
                                  txcorrectedbits(13),
                                  txframes(14),
                                  txuncorrectedframes(15),
                                  txcorrectedframes(16)
                              }

    CmisMediaAttrFlags ::= TEXTUAL-CONVENTION
      STATUS      current
      DESCRIPTION
      "The Cmis module media lane attr flags type."
      SYNTAX          INTEGER
                              {
                                  rxloss(1),
                                  rxcdrlol(2),
                                  txfailure(3),
                                  txoutputstatus(4),
                                  txfifoerror(5),
                                  txdeskewlol(6),
                                  txreferenceclocklol(7),
                                  txcmulol(8),
                                  txoutofalignment(9),
                                  txlossofalignment(10),
                                  rxfifolol(11),
                                  rxdeskewlol(12),
                                  rxoutofalignment(13),
                                  rxlossofalignment(14),
                                  rxchromaticdispersioncompensationlol(15),
                                  rxdemodulatorlol(16),
                                  rxlossofmultiframe(17),
                                  rxlossofframe(18),
                                  fecdetecteddegradeoverpminterval(19),
                                  fecexcessivedegradeoverpminterval(20),
                                  remotePHYfault(21),
                                  localdegrade(22),
                                  remotedegrade(23)
                              }

    CmisMediaAttrMonitorings ::= TEXTUAL-CONVENTION
      STATUS      current
      DESCRIPTION
      "The Cmis module media lane attr monitorings type."
      SYNTAX          INTEGER
                               {
                                   rxopticalpwr(1),
                                   txopticalpwr(2),
                                   txbias(3),
                                   laserage(4),
                                   laserfrequencyerror(5),
                                   lasertemperature(6),
                                   esnrinput(7),
                                   pam4leveltransitparaminput(8),
                                   prefecberminsampleinput(9),
                                   prefecbermaxsampleinput(10),
                                   prefecbersampleaverageinput(11),
                                   prefecbercurrentsampleinput(12),
                                   fercminsamplevalueinput(13),
                                   fercmaxsamplevalueinput(14),
                                   fercsampleaveragevalueinput(15),
                                   ferccurrentsamplevalueinput(16),
                                   ferctotalaccumulatedinput(17),
                                   modularbiasxi(18),
                                   modularbiasxq(19),
                                   modularbiasyi(20),
                                   modularbiasyq(21),
                                   modularbiasxphase(22),
                                   modularbiasyphase(23),
                                   cdhighgranularityshortlink(24),
                                   cdlowgranularitylonglink(25),
                                   dgd(26),
                                   sopmdhighgranularity(27),
                                   pdl(28),
                                   osnr(29),
                                   esnr(30),
                                   cfo(31),
                                   evm(32),
                                   txpower(33),
                                   rxtotalpower(34),
                                   rxsignalpower(35),
                                   soproc(36),
                                   mer(37),
                                   clockrecoveryloop(38),
                                   sopmdlowgranularity(39),
                                   rxdspccdaverage(40),
                                   rxdspccdminimum(41),
                                   rxdspccdmaximum(42),
                                   rxdgdaverage(43),
                                   rxdgdminimum(44),
                                   rxdgdmaximum(45),
                                   rxhgsopmdaverage(46),
                                   rxhgsopmdminimum(47),
                                   rxhgsopmdmaximum(48),
                                   rxpdlaverage(49),
                                   rxpdlminimum(50),
                                   rxpdlmaximum(51),
                                   rxosnraverage(52),
                                   rxosnrminimum(53),
                                   rxosnrmaximum(54),
                                   rxesnraverage(55),
                                   rxesnrminimum(56),
                                   rxesnrmaximum(57),
                                   rxcfoaverage(58),
                                   rxcfominimum(59),
                                   rxcfomaximum(60),
                                   rxevmaverage(61),
                                   rxevmminimum(62),
                                   rxevmmaximum(63),
                                   txpoweraverage(64),
                                   txpowerminimum(65),
                                   txpowermaximum(66),
                                   rxpoweraverage(67),
                                   rxpowerminimum(68),
                                   rxpowermaximum(69),
                                   rxsignalpoweraverage(70),
                                   rxsignalpowerminimum(71),
                                   rxsignalpowermaximum(72),
                                   rxsopcraverage(73),
                                   rxsopcrminimum(74),
                                   rxsopcrmaximum(75),
                                   rxmeraverage(76),
                                   rxmerminimum(77),
                                   rxmermaximum(78),
                                   rxclockrecoveryloopaverage(79),
                                   rxclockrecoveryloopminimum(80),
                                   rxclockrecoveryloopmaximum(81),
                                   rxlgsopmdaverage(82),
                                   rxlgsopmdminimum(83),
                                   rxlgsopmdmaximum(84),
                                   rxbits(85),
                                   rxcorrectedbits(86),
                                   rxframes(87),
                                   rxuncorrectedframes(88),
                                   rxsnrmargin(89),
                                   rxsnrmarginaverage(90),
                                   rxsnrmarginminimum(91),
                                   rxsnrmarginmaximum(92),
                                   rxqfactor(93),
                                   rxqfactoraverage(94),
                                   rxqfactorminimum(95),
                                   rxqfactormaximum(96),
                                   rxqmargin(97),
                                   rxqmarginaverage(98),
                                   rxqmarginminimum(99),
                                   rxqmarginmaximum(100)
                               }

    CmisModuleAttrMonitorings ::= TEXTUAL-CONVENTION
      STATUS      current
      DESCRIPTION
      "The Cmis module attr monitorings types."
      SYNTAX       INTEGER {
                               voltage(1),
                               temperature(2),
                               tech-current(3),
                               tech-current2(4),
                               laser-temperature(5),
                               laser-temperature2(6),
                               voltage2(7)
                           }

    CmisModuleCcmisRxLosTypes ::= TEXTUAL-CONVENTION
      STATUS      current
      DESCRIPTION
      "The Cmis module C-CMIS Rx LoS detection type."
      SYNTAX       INTEGER {
                               rxlosrespondstorxtotalpower(1),
                               rxlosrespondstorxsignalpower(2),
                               rxlosrespondstorxdspframelol(3),
                               rxtotalpowerdetectionandrxdspframelolhybrid(4),
                               rxsingalpowerdetectionandrxdspframelolhybrid(5)
                           }

    CmisModuleTxFilterTypes ::= TEXTUAL-CONVENTION
      STATUS      current
      DESCRIPTION
      "The Cmis module Tx Filter type."
      SYNTAX  INTEGER {
                        none(1),
                        rootraisedcosine(2),
                        raisedcosine(3),
                        gaussian(4)
                      }

    CmisModuleFPPortTypes ::= TEXTUAL-CONVENTION
      STATUS      deprecated
      DESCRIPTION
      "The Cmis transceiver front panel port type."
      SYNTAX  INTEGER {
                        unknown(-1),
                        sfp(1),
                        sfp-plus(2),
                        sfp-28(3),
                        sfp-56(4),
                        sfp-56-dd(5),
                        sfp-112(6),
                        sfp-112-dd(7),
                        qsfp(8),
                        qsfp-plus(9),
                        qsfp-28(10),
                        qsfp-28-dd(11),
                        qsfp-56(12),
                        qsfp-56-dd(13),
                        qsfp-112(14),
                        qsfp-112-dd(15),
                        xfp(16),
                        osfp(17)
                      }

    CmisModuleFPPortModuleTypes ::= TEXTUAL-CONVENTION
      STATUS      deprecated
      DESCRIPTION
      "The Cmis transceiver front panel port module type."
      SYNTAX  INTEGER {
                        unknown(-1),
                        sfp(1),
                        sfp-plus(2),
                        sfp-plus-edfa(3),
                        sfp-28(4),
                        sfp-56(5),
                        sfp-56-dd(6),
                        sfp-112(7),
                        sfp-112-dd(8),
                        qsfp(9),
                        qsfp-plus(10),
                        qsfp-28(11),
                        qsfp-28-dd(12),
                        qsfp-28-edfa(13),
                        qsfp-56(14),
                        qsfp-56-dd(15),
                        qsfp-112(16),
                        qsfp-112-dd(17),
                        qsa(18),
                        xfp(19),
                        pon-xfp(20),
                        osfp-8x(21),
                      }


    cmmCmisModuleEEPROMTable     OBJECT-TYPE
      SYNTAX            SEQUENCE OF CmmCmisModuleEEPROMTableEntry
      MAX-ACCESS        not-accessible
      STATUS            current
      DESCRIPTION
        "A list of entries containing Cmis module EEPROM information."
        ::= { cmmCmisModuleObjects 1 }

    cmmCmisModuleEEPROMTableEntry OBJECT-TYPE
      SYNTAX         CmmCmisModuleEEPROMTableEntry
      MAX-ACCESS        not-accessible
      STATUS            current
      DESCRIPTION
        "A list of table entries containing Cmis module EEPROM information."
        INDEX    { cmmStackUnitIndex, cmmCmisModuleType,
                   cmmCmisModulePortNumber }
        ::= { cmmCmisModuleEEPROMTable 1 }

    CmmCmisModuleEEPROMTableEntry   ::=
       SEQUENCE {
         cmmCmisModuleType                      INTEGER,
         cmmCmisModulePortNumber                INTEGER,
         cmmCmisModuleVendorName                DisplayString,
         cmmCmisModuleIdentifier                INTEGER,
         cmmCmisModuleVendorOUI                 DisplayString,
         cmmCmisModuleVendorPartNumber          DisplayString,
         cmmCmisModuleVendorRevision            DisplayString,
         cmmCmisModuleVendorSerialNumber        DisplayString,
         cmmCmisModuleMfgDate                   DateAndTime,
         cmmCmisModulePowerClass                INTEGER,
         cmmCmisModuleMaxPower                  INTEGER,
         cmmCmisModuleCoolingImplemented        TruthValue,
         cmmCmisModuleTemperatureMax            INTEGER,
         cmmCmisModuleTemperatureMin            INTEGER,
         cmmCmisModuleOperatingVoltageMin       INTEGER,
         cmmCmisModuleOpticalDetector           INTEGER,
         cmmCmisModuleRxPowerMeasurement        INTEGER,
         cmmCmisModuleTxDisableModuleWide       TruthValue,
         cmmCmisModuleCableAssemblyLinkLength   INTEGER,
         cmmCmisModuleConnectorType             ConnectorType,
         cmmCmisModuleMediaInterfaceTechnology  MediaInterfaceTechEncodings,
         cmmCmisModuleCMISRevision              DisplayString,
         cmmCmisModuleCCMISRevision             DisplayString,
         cmmCmisModuleMemoryModel               INTEGER,
         cmmCmisModuleMCIMaxSpeed               INTEGER,
         cmmCmisModuleActiveFirmwareRevision    DisplayString,
         cmmCmisModuleInactiveFirmwareRevision  DisplayString,
         cmmCmisModuleHardwareRevision          DisplayString,
         cmmCmisModuleMediaType                 INTEGER,
         cmmCmisModuleWavelengthNominal         INTEGER,
         cmmCmisModuleWavelengthTolerance       INTEGER,
         cmmCmisModuleCleiCode                  DisplayString,
         cmmCmisModuleCCA5GHz                   INTEGER,
         cmmCmisModuleCCA7GHz                   INTEGER,
         cmmCmisModuleCCA12P9GHz                INTEGER,
         cmmCmisModuleCCA25P8GHz                INTEGER,
         cmmCmisModuleMaxSmfLinkLength          INTEGER,
         cmmCmisModuleMaxMmfOm2LinkLength       INTEGER,
         cmmCmisModuleMaxMmfOm3LinkLength       INTEGER,
         cmmCmisModuleMaxMmfOm4LinkLength       INTEGER,
         cmmCmisModuleMaxMmfOm5LinkLength       INTEGER,
         cmmCmisModuleRxLosType                 CmisModuleCcmisRxLosTypes
       }

    cmmCmisModuleType  OBJECT-TYPE
      SYNTAX                INTEGER {
                              qsfp-dd(1),
                              sfp(2),
                              qsfp(3),
                              xfp(4),
                              osfp(5),
                            }
      MAX-ACCESS            read-only
      STATUS                current
      DESCRIPTION
        "Module type."
      ::= { cmmCmisModuleEEPROMTableEntry 1 }

  cmmCmisModulePortNumber  OBJECT-TYPE
    SYNTAX          INTEGER (0..128)
    MAX-ACCESS      read-only
    STATUS          current
    DESCRIPTION
      "Module Port index number."
    ::= { cmmCmisModuleEEPROMTableEntry 2 }

    cmmCmisModuleVendorName  OBJECT-TYPE
      SYNTAX                DisplayString
      MAX-ACCESS            read-only
      STATUS                current
      DESCRIPTION
        "Module vendor name."
      ::= { cmmCmisModuleEEPROMTableEntry 3 }

    cmmCmisModuleIdentifier  OBJECT-TYPE
      SYNTAX        INTEGER {
                      id-unknown(1),
                      gbic(2),
                      soldered-to-motherboard(3),
                      sfp-or-sfpplus-or-sfp28(4),
                      xbi-300pin(5),
                      xenpak(6),
                      xfp(7),
                      xff(8),
                      xfpe(9),
                      xpak(10),
                      x2(11),
                      dwdmsfp-or-dwdmsfpplus(12),
                      qsfp(13),
                      qsfpplus-or-later(14),
                      cxp-or-later(15),
                      shielded-mini-multilane-hd4x(16),
                      shielded-mini-multilane-hd8x(17),
                      qsfp28-or-later(18),
                      cxp2-aka-cxp28-or-later(19),
                      cdfpstyle1-or-cdfpstyle2(20),
                      shielded-mini-multilane-hd4x-fanoutcable(21),
                      shielded-mini-multilane-hd8x-fanoutcable(22),
                      cdfpstyle3(23),
                      microqsfp(24),
                      qsfp-doubledensity-8x-pluggable-transceiver(25),
                      osfp-8x-pluggable-transceiver(26),
                      qsfpplus-or-later-with-cmis(31),
                      reserved(254),
                      vendor-specific(255)
                    }
      MAX-ACCESS            read-only
      STATUS                current
      DESCRIPTION
        "Module indentifier."
      ::= { cmmCmisModuleEEPROMTableEntry 4 }

    cmmCmisModuleVendorOUI  OBJECT-TYPE
      SYNTAX                DisplayString
      MAX-ACCESS            read-only
      STATUS                current
      DESCRIPTION
        "IEEE company ID provided by module vendor."
      ::= { cmmCmisModuleEEPROMTableEntry 5 }

    cmmCmisModuleVendorPartNumber  OBJECT-TYPE
      SYNTAX                DisplayString
      MAX-ACCESS            read-only
      STATUS                current
      DESCRIPTION
        "Part number for module provided by vendor."
      ::= { cmmCmisModuleEEPROMTableEntry 6 }

    cmmCmisModuleVendorRevision  OBJECT-TYPE
      SYNTAX                DisplayString
      MAX-ACCESS            read-only
      STATUS                current
      DESCRIPTION
        "Revision level for module provided by vendor."
      ::= { cmmCmisModuleEEPROMTableEntry 7 }

    cmmCmisModuleVendorSerialNumber  OBJECT-TYPE
      SYNTAX                DisplayString
      MAX-ACCESS            read-only
      STATUS                current
      DESCRIPTION
        "Serial number for module provided by vendor."
      ::= { cmmCmisModuleEEPROMTableEntry 8 }

    cmmCmisModuleMfgDate    OBJECT-TYPE
      SYNTAX                DateAndTime
      MAX-ACCESS            read-only
      STATUS                current
      DESCRIPTION
        "The manufactured date of module."
      ::= { cmmCmisModuleEEPROMTableEntry 9 }

    cmmCmisModulePowerClass  OBJECT-TYPE
      SYNTAX                INTEGER {
                              powerclass1(1),
                              powerclass2(2),
                              powerclass3(3),
                              powerclass4(4),
                              powerclass5(5),
                              powerclass6(6),
                              powerclass7(7),
                              powerclass8(8)
                            }
      MAX-ACCESS            read-only
      STATUS                current
      DESCRIPTION
        "Module power class."
      ::= { cmmCmisModuleEEPROMTableEntry 10 }

    cmmCmisModuleMaxPower  OBJECT-TYPE
      SYNTAX                INTEGER
      UNITS                 "0.01 Watt"
      MAX-ACCESS            read-only
      STATUS                current
      DESCRIPTION
        "Module maximum power."
      ::= { cmmCmisModuleEEPROMTableEntry 11 }

    cmmCmisModuleCoolingImplemented  OBJECT-TYPE
      SYNTAX                TruthValue
      MAX-ACCESS            read-only
      STATUS                current
      DESCRIPTION
        "Module supports cooling feature."
      ::= { cmmCmisModuleEEPROMTableEntry 12 }

    cmmCmisModuleTemperatureMax  OBJECT-TYPE
      SYNTAX                INTEGER
      UNITS                 "0.01 Celsius"
      MAX-ACCESS            read-only
      STATUS                current
      DESCRIPTION
        "Module maximum temperature."
      ::= { cmmCmisModuleEEPROMTableEntry 13 }


    cmmCmisModuleTemperatureMin  OBJECT-TYPE
      SYNTAX                INTEGER
      UNITS                 "0.01 Celsius"
      MAX-ACCESS            read-only
      STATUS                current
      DESCRIPTION
        "Module minimum temperature."
      ::= { cmmCmisModuleEEPROMTableEntry 14 }

    cmmCmisModuleOperatingVoltageMin  OBJECT-TYPE
      SYNTAX                INTEGER
      UNITS                 "0.01 Volt"
      MAX-ACCESS            read-only
      STATUS                current
      DESCRIPTION
        "Module minimum operating voltage."
      ::= { cmmCmisModuleEEPROMTableEntry 15 }

    cmmCmisModuleOpticalDetector  OBJECT-TYPE
      SYNTAX                INTEGER {
                              pin(1),
                              apd(2)
                            }
      MAX-ACCESS            read-only
      STATUS                current
      DESCRIPTION
        "Module optical detector type."
      ::= { cmmCmisModuleEEPROMTableEntry 16 }

    cmmCmisModuleRxPowerMeasurement  OBJECT-TYPE
      SYNTAX                INTEGER {
                              oma(1),
                              averagepower(2)
                            }
      MAX-ACCESS            read-only
      STATUS                current
      DESCRIPTION
        "Module rx power measurement."
      ::= { cmmCmisModuleEEPROMTableEntry 17 }

    cmmCmisModuleTxDisableModuleWide  OBJECT-TYPE
      SYNTAX                TruthValue
      MAX-ACCESS            read-only
      STATUS                current
      DESCRIPTION
        "Module tx output disable support per lane."
      ::= { cmmCmisModuleEEPROMTableEntry 18 }

    cmmCmisModuleCableAssemblyLinkLength  OBJECT-TYPE
      SYNTAX                INTEGER
      MAX-ACCESS            read-only
      STATUS                current
      DESCRIPTION
        "Module cable assembly link length.
        -1 is separablemedia, -2 is greaterthan6300meter, -3 is undefined"
      ::= { cmmCmisModuleEEPROMTableEntry 19 }

    cmmCmisModuleConnectorType  OBJECT-TYPE
      SYNTAX                ConnectorType
      MAX-ACCESS            read-only
      STATUS                current
      DESCRIPTION
        "Module connector type for the media side."
      ::= { cmmCmisModuleEEPROMTableEntry 20 }

    cmmCmisModuleMediaInterfaceTechnology  OBJECT-TYPE
      SYNTAX                MediaInterfaceTechEncodings
      MAX-ACCESS            read-only
      STATUS                current
      DESCRIPTION
        "Module media interface technology."
      ::= { cmmCmisModuleEEPROMTableEntry 21 }

    cmmCmisModuleCMISRevision  OBJECT-TYPE
      SYNTAX                DisplayString
      MAX-ACCESS            read-only
      STATUS                current
      DESCRIPTION
        "Cmis module revision provided by vendor."
      ::= { cmmCmisModuleEEPROMTableEntry 22 }

    cmmCmisModuleMemoryModel  OBJECT-TYPE
      SYNTAX                INTEGER {
                              paged(1),
                              flat(2)
                            }
      MAX-ACCESS            read-only
      STATUS                current
      DESCRIPTION
        "Cmis module memory model."
      ::= { cmmCmisModuleEEPROMTableEntry 23 }

    cmmCmisModuleMCIMaxSpeed  OBJECT-TYPE
      SYNTAX                INTEGER {
                              speed-400(1),
                              speed-1000(2),
                              reserved(3)
                            }
      UNITS                 "kHz"
      MAX-ACCESS            read-only
      STATUS                current
      DESCRIPTION
        "Module clock maximum speed of
        Management Communication Interface(MCI)."
      ::= { cmmCmisModuleEEPROMTableEntry 24 }

    cmmCmisModuleActiveFirmwareRevision  OBJECT-TYPE
      SYNTAX                DisplayString
      MAX-ACCESS            read-only
      STATUS                current
      DESCRIPTION
        "Module active firmware revision."
      ::= { cmmCmisModuleEEPROMTableEntry 25 }

    cmmCmisModuleInactiveFirmwareRevision  OBJECT-TYPE
      SYNTAX                DisplayString
      MAX-ACCESS            read-only
      STATUS                current
      DESCRIPTION
        "Module inactive firmware revision."
      ::= { cmmCmisModuleEEPROMTableEntry 26 }

    cmmCmisModuleHardwareRevision  OBJECT-TYPE
      SYNTAX                DisplayString
      MAX-ACCESS            read-only
      STATUS                current
      DESCRIPTION
        "Module hardware revision."
      ::= { cmmCmisModuleEEPROMTableEntry 27 }

    cmmCmisModuleMediaType  OBJECT-TYPE
      SYNTAX                INTEGER {
                              none(1),
                              mmf(2),
                              smf(3),
                              passive-copper-c(4),
                              active-c(5),
                              base-t(6),
                              reserved(7)
                            }
      MAX-ACCESS            read-only
      STATUS                current
      DESCRIPTION
        "Module media type."
      ::= { cmmCmisModuleEEPROMTableEntry 28 }

    cmmCmisModuleWavelengthNominal  OBJECT-TYPE
      SYNTAX                INTEGER
      UNITS                 "0.01 nm"
      MAX-ACCESS            read-only
      STATUS                current
      DESCRIPTION
        "Module wavelength nominal."
      ::= { cmmCmisModuleEEPROMTableEntry 29 }

    cmmCmisModuleWavelengthTolerance  OBJECT-TYPE
      SYNTAX                INTEGER
      UNITS                 "0.01 nm"
      MAX-ACCESS            read-only
      STATUS                current
      DESCRIPTION
        "Module wavelength tolerance."
      ::= { cmmCmisModuleEEPROMTableEntry 30 }

    cmmCmisModuleCleiCode  OBJECT-TYPE
      SYNTAX                DisplayString
      MAX-ACCESS            read-only
      STATUS                current
      DESCRIPTION
        "Module Common Language Equiment Identification (CLEI)."
      ::= { cmmCmisModuleEEPROMTableEntry 31 }

    cmmCmisModuleCCA5GHz  OBJECT-TYPE
      SYNTAX                INTEGER
      UNITS                 "dB"
      MAX-ACCESS            read-only
      STATUS                current
      DESCRIPTION
        "Module passive copper cable attenuation at 5 GHz."
      ::= { cmmCmisModuleEEPROMTableEntry 32 }

    cmmCmisModuleCCA7GHz  OBJECT-TYPE
      SYNTAX                INTEGER
      UNITS                 "dB"
      MAX-ACCESS            read-only
      STATUS                current
      DESCRIPTION
        "Module passive copper cable attenuation at 7 GHz."
      ::= { cmmCmisModuleEEPROMTableEntry 33 }

    cmmCmisModuleCCA12P9GHz  OBJECT-TYPE
      SYNTAX                INTEGER
      UNITS                 "dB"
      MAX-ACCESS            read-only
      STATUS                current
      DESCRIPTION
        "Module passive copper cable attenuation at 12.9 GHz."
      ::= { cmmCmisModuleEEPROMTableEntry 34 }

    cmmCmisModuleCCA25P8GHz  OBJECT-TYPE
      SYNTAX                INTEGER
      UNITS                 "dB"
      MAX-ACCESS            read-only
      STATUS                current
      DESCRIPTION
        "Module passive copper cable attenuation at 25.8 GHz."
      ::= { cmmCmisModuleEEPROMTableEntry 35 }

    cmmCmisModuleMaxSmfLinkLength  OBJECT-TYPE
      SYNTAX                INTEGER
      UNITS                 "0.01 Km"
      MAX-ACCESS            read-only
      STATUS                current
      DESCRIPTION
        "Module supported fiber link cable length."
      ::= { cmmCmisModuleEEPROMTableEntry 36 }

    cmmCmisModuleMaxMmfOm2LinkLength  OBJECT-TYPE
      SYNTAX                INTEGER
      UNITS                 "meter"
      MAX-ACCESS            read-only
      STATUS                current
      DESCRIPTION
        "Module Link length supported for 50/125 micrometer fiber (OM2)."
      ::= { cmmCmisModuleEEPROMTableEntry 37 }

    cmmCmisModuleMaxMmfOm3LinkLength  OBJECT-TYPE
      SYNTAX                INTEGER
      UNITS                 "meter"
      MAX-ACCESS            read-only
      STATUS                current
      DESCRIPTION
        "Module Link length supported for EBW 50/125 micrometer fiber (OM3)."
      ::= { cmmCmisModuleEEPROMTableEntry 38 }

    cmmCmisModuleMaxMmfOm4LinkLength  OBJECT-TYPE
      SYNTAX                INTEGER
      UNITS                 "meter"
      MAX-ACCESS            read-only
      STATUS                current
      DESCRIPTION
        "Module Link length supported for OM4 fiber."
      ::= { cmmCmisModuleEEPROMTableEntry 39 }

    cmmCmisModuleMaxMmfOm5LinkLength  OBJECT-TYPE
      SYNTAX                INTEGER
      UNITS                 "meter"
      MAX-ACCESS            read-only
      STATUS                current
      DESCRIPTION
        "Module Link length supported for OM5 fiber."
      ::= { cmmCmisModuleEEPROMTableEntry 40 }

    cmmCmisModuleCCMISRevision  OBJECT-TYPE
      SYNTAX                DisplayString
      MAX-ACCESS            read-only
      STATUS                current
      DESCRIPTION
        "Coherent Cmis revision provided by vendor."
      ::= { cmmCmisModuleEEPROMTableEntry 41 }

    cmmCmisModuleRxLosType  OBJECT-TYPE
      SYNTAX                CmisModuleCcmisRxLosTypes
      MAX-ACCESS            read-only
      STATUS                current
      DESCRIPTION
        "Coherent CMIS Rx LoS detection type."
      ::= { cmmCmisModuleEEPROMTableEntry 42 }

    cmmCmisModuleOperationalStateTable OBJECT-TYPE
      SYNTAX            SEQUENCE OF CmmCmisModuleOperationalStateTableEntry
      MAX-ACCESS        not-accessible
      STATUS            current
      DESCRIPTION
        "A list of entries containing Cmis operational state information."
        ::= { cmmCmisModuleObjects 2 }

    cmmCmisModuleOperationalStateTableEntry OBJECT-TYPE
      SYNTAX            CmmCmisModuleOperationalStateTableEntry
      MAX-ACCESS        not-accessible
      STATUS            current
      DESCRIPTION
        "A list of table entries containing Cmis operational state information."
      INDEX    { cmmStackUnitIndex, cmmCmisModuleType,
                 cmmCmisModulePortNumber }
        ::= { cmmCmisModuleOperationalStateTable 1 }

    CmmCmisModuleOperationalStateTableEntry   ::=
       SEQUENCE {
         cmmCmisModuleFaultState            INTEGER,
         cmmCmisModuleState                 INTEGER
       }

    cmmCmisModuleFaultState OBJECT-TYPE
      SYNTAX                INTEGER {
                              no-fault(1),
                              tec-runaway(2),
                              data-memory-corrupted(3),
                              program-memory-corrupted(4),
                              reserved(5)
                            }
      MAX-ACCESS            read-only
      STATUS                current
      DESCRIPTION
        "Module fault information."
      ::= { cmmCmisModuleOperationalStateTableEntry 1 }

    cmmCmisModuleState OBJECT-TYPE
       SYNTAX                INTEGER {
                               reserved(1),
                               low-power(2),
                               power-up(3),
                               ready(4),
                               power-down(5),
                               fault(6)
                             }
       MAX-ACCESS            read-only
       STATUS                current
       DESCRIPTION
         "Module operation state."
       ::= { cmmCmisModuleOperationalStateTableEntry 2 }


    cmmCmisModuleDataPathStateTable OBJECT-TYPE
       SYNTAX            SEQUENCE OF CmmCmisModuleDataPathStateTableEntry
       MAX-ACCESS        not-accessible
       STATUS            current
       DESCRIPTION
         "A list of entries containing Cmis data path information."
       ::= { cmmCmisModuleObjects 3 }

    cmmCmisModuleDataPathStateTableEntry OBJECT-TYPE
       SYNTAX            CmmCmisModuleDataPathStateTableEntry
       MAX-ACCESS        not-accessible
       STATUS            current
       DESCRIPTION
         "A list of table entries containing Cmis data path state information."
       INDEX    { cmmStackUnitIndex, cmmCmisModuleType,
                  cmmCmisModulePortNumber, cmmCmisModuleLaneNumber }
         ::= { cmmCmisModuleDataPathStateTable 1 }

    CmmCmisModuleDataPathStateTableEntry   ::=
       SEQUENCE {
           cmmCmisModuleLaneNumber            INTEGER,
           cmmCmisModuleDataPathState         INTEGER
       }

    cmmCmisModuleLaneNumber  OBJECT-TYPE
      SYNTAX          INTEGER (1..8)
      MAX-ACCESS      read-only
      STATUS          current
      DESCRIPTION
        "Module Port lane number."
      ::= { cmmCmisModuleDataPathStateTableEntry 1 }

    cmmCmisModuleDataPathState OBJECT-TYPE
       SYNTAX                INTEGER {
                               reserved(1),
                               deactivated(2),
                               init(3),
                               deinit(4),
                               activated(5),
                               tx-turn-on(6),
                               tx-turn-off(7),
                               initialized(8)
                             }
       MAX-ACCESS            read-only
       STATUS                current
       DESCRIPTION
         "Module data path state for particular lane."
       ::= { cmmCmisModuleDataPathStateTableEntry 2 }

    cmmCmisModuleMonitoringTable OBJECT-TYPE
       SYNTAX            SEQUENCE OF CmmCmisModuleMonitoringTableEntry
       MAX-ACCESS        not-accessible
       STATUS            current
       DESCRIPTION
         "A list of entries containing Cmis module monitoring."
       ::= { cmmCmisModuleObjects 4 }

    cmmCmisModuleMonitoringTableEntry OBJECT-TYPE
       SYNTAX            CmmCmisModuleMonitoringTableEntry
       MAX-ACCESS        not-accessible
       STATUS            current
       DESCRIPTION
         "A list of table entries containing Cmis module monitoring information."
       INDEX    { cmmStackUnitIndex, cmmCmisModuleType,
                  cmmCmisModulePortNumber, cmmCmisModuleMonitoringAttrType }
         ::= { cmmCmisModuleMonitoringTable 1 }

    CmmCmisModuleMonitoringTableEntry   ::=
       SEQUENCE {
           cmmCmisModuleMonitoringAttrType         CmisModuleAttrMonitorings,
           cmmCmisModuleAttrValue                  INTEGER,
           cmmCmisModuleAttrThreshAlertMax         INTEGER,
           cmmCmisModuleAttrThreshCriticalMax      INTEGER,
           cmmCmisModuleAttrThreshCriticalMin      INTEGER,
           cmmCmisModuleAttrThreshAlertMin         INTEGER
         }

    cmmCmisModuleMonitoringAttrType  OBJECT-TYPE
      SYNTAX       CmisModuleAttrMonitorings
      MAX-ACCESS   accessible-for-notify
      STATUS       current
      DESCRIPTION
        "A generic threshold alarm event type information"
        ::= { cmmCmisModuleMonitoringTableEntry 1 }

    cmmCmisModuleAttrValue OBJECT-TYPE
      SYNTAX          INTEGER
      UNITS           "0.01 unit"
      MAX-ACCESS      read-only
      STATUS          current
      DESCRIPTION
        "Cmis Module value.
         Unit: Temperature in degree C, Voltage in Volts,
         Aux in Percent."
        ::= { cmmCmisModuleMonitoringTableEntry 2 }

    cmmCmisModuleAttrThreshAlertMax OBJECT-TYPE
      SYNTAX          INTEGER
      MAX-ACCESS      read-only
      STATUS          current
      DESCRIPTION
        "Cmis Module maximum alert threshold value"
        ::= { cmmCmisModuleMonitoringTableEntry 3 }

    cmmCmisModuleAttrThreshCriticalMax OBJECT-TYPE
      SYNTAX          INTEGER
      MAX-ACCESS      read-only
      STATUS          current
      DESCRIPTION
        "Cmis Module maximum critical threshold value"
        ::= { cmmCmisModuleMonitoringTableEntry 4 }

    cmmCmisModuleAttrThreshCriticalMin OBJECT-TYPE
      SYNTAX          INTEGER
      MAX-ACCESS      read-only
      STATUS          current
      DESCRIPTION
        "Cmis Module minimum critical threshold value"
        ::= { cmmCmisModuleMonitoringTableEntry 5 }

    cmmCmisModuleAttrThreshAlertMin OBJECT-TYPE
      SYNTAX          INTEGER
      MAX-ACCESS      read-only
      STATUS          current
      DESCRIPTION
        "Cmis Module minimum alert threshold value"
        ::= { cmmCmisModuleMonitoringTableEntry 6 }


    -- for cmmCmisModuleMonitoringFlagsTable, cmmCmisModuleObjects: 5
    -- is reserved

    cmmCmisModuleMediaLaneMonitoringTable OBJECT-TYPE
      SYNTAX            SEQUENCE OF CmmCmisModuleMediaLaneMonitoringTableEntry
      MAX-ACCESS        not-accessible
      STATUS            current
      DESCRIPTION
        "A list of entries containing Cmis module media lane monitoring."
        ::= { cmmCmisModuleObjects 6 }

    cmmCmisModuleMediaLaneMonitoringTableEntry OBJECT-TYPE
       SYNTAX            CmmCmisModuleMediaLaneMonitoringTableEntry
       MAX-ACCESS        not-accessible
       STATUS            current
       DESCRIPTION
         "A list of table entries containing Cmis module media lane monitoring
         information."
       INDEX    { cmmStackUnitIndex, cmmCmisModuleType,
                  cmmCmisModulePortNumber, cmmCmisModuleMediaMonitoringAttrType,
                  cmmCmisModuleLaneNumber
                }
         ::= { cmmCmisModuleMediaLaneMonitoringTable 1 }

    CmmCmisModuleMediaLaneMonitoringTableEntry   ::=
       SEQUENCE {
           cmmCmisModuleMediaMonitoringAttrType         CmisMediaAttrMonitorings,
           cmmCmisModuleMediaAttrValue                  INTEGER,
           cmmCmisModuleMediaAttrThreshAlertMax         INTEGER,
           cmmCmisModuleMediaAttrThreshCriticalMax      INTEGER,
           cmmCmisModuleMediaAttrThreshCriticalMin      INTEGER,
           cmmCmisModuleMediaAttrThreshAlertMin         INTEGER
         }

    cmmCmisModuleMediaMonitoringAttrType  OBJECT-TYPE
      SYNTAX          CmisMediaAttrMonitorings
      MAX-ACCESS      accessible-for-notify
      STATUS          current
      DESCRIPTION
        "Cmis Module Media lane event types"
        ::= { cmmCmisModuleMediaLaneMonitoringTableEntry 1 }

    cmmCmisModuleMediaAttrValue OBJECT-TYPE
      SYNTAX          INTEGER
      UNITS           "0.01 dBm"
      MAX-ACCESS      read-only
      STATUS          current
      DESCRIPTION
        "Cmis Module media lane attribute value"
        ::= { cmmCmisModuleMediaLaneMonitoringTableEntry 2 }

    cmmCmisModuleMediaAttrThreshAlertMax OBJECT-TYPE
      SYNTAX          INTEGER
      UNITS           "0.01 dBm"
      MAX-ACCESS      read-only
      STATUS          current
      DESCRIPTION
        "Cmis Module media lane maximum alert threshold value"
        ::= { cmmCmisModuleMediaLaneMonitoringTableEntry 3 }

    cmmCmisModuleMediaAttrThreshCriticalMax OBJECT-TYPE
      SYNTAX          INTEGER
      UNITS           "0.01 dBm"
      MAX-ACCESS      read-only
      STATUS          current
      DESCRIPTION
        "Cmis Module media lane maximum critical threshold value"
        ::= { cmmCmisModuleMediaLaneMonitoringTableEntry 4 }

    cmmCmisModuleMediaAttrThreshCriticalMin OBJECT-TYPE
      SYNTAX          INTEGER
      UNITS           "0.01 dBm"
      MAX-ACCESS      read-only
      STATUS          current
      DESCRIPTION
        "Cmis Module media lane minimum critical threshold value"
        ::= { cmmCmisModuleMediaLaneMonitoringTableEntry 5 }

    cmmCmisModuleMediaAttrThreshAlertMin OBJECT-TYPE
      SYNTAX          INTEGER
      UNITS           "0.01 dBm"
      MAX-ACCESS      read-only
      STATUS          current
      DESCRIPTION
        "Cmis Module media lane minimum alert threshold value"
        ::= { cmmCmisModuleMediaLaneMonitoringTableEntry 6 }


    cmmCmisModuleMediaLaneFlagsTable OBJECT-TYPE
       SYNTAX            SEQUENCE OF CmmCmisModuleMediaLaneFlagsTableEntry
       MAX-ACCESS        not-accessible
       STATUS            current
       DESCRIPTION
         "A list of table entries containing Cmis module media lane flags information."
        ::= { cmmCmisModuleObjects 7 }

    cmmCmisModuleMediaLaneFlagsTableEntry OBJECT-TYPE
       SYNTAX            CmmCmisModuleMediaLaneFlagsTableEntry
       MAX-ACCESS        not-accessible
       STATUS            current
       DESCRIPTION
         "A list of table entries containing Cmis module media lane flags information."
       INDEX    { cmmStackUnitIndex, cmmCmisModuleType,
                  cmmCmisModulePortNumber, cmmCmisModuleMediaLaneAttrFlagType,
                  cmmCmisModuleLaneNumber
                 }
         ::= { cmmCmisModuleMediaLaneFlagsTable 1 }

    CmmCmisModuleMediaLaneFlagsTableEntry  ::=
    SEQUENCE {
               cmmCmisModuleMediaLaneAttrFlagType   CmisMediaAttrFlags,
               cmmCmisModuleMediaLaneFlags          TruthValue
             }

    cmmCmisModuleMediaLaneAttrFlagType  OBJECT-TYPE
      SYNTAX          CmisMediaAttrFlags
      MAX-ACCESS      accessible-for-notify
      STATUS          current
      DESCRIPTION
        "Cmis Module Media lane event types"
        ::= { cmmCmisModuleMediaLaneFlagsTableEntry 1 }

    cmmCmisModuleMediaLaneFlags OBJECT-TYPE
      SYNTAX          TruthValue
      MAX-ACCESS      read-only
      STATUS          current
      DESCRIPTION
        "Cmis Module media lane flags"
        ::= { cmmCmisModuleMediaLaneFlagsTableEntry 2 }


    cmmCmisModuleHostLaneMonitoringTable OBJECT-TYPE
      SYNTAX            SEQUENCE OF CmmCmisModuleHostLaneMonitoringTableEntry
      MAX-ACCESS        not-accessible
      STATUS            current
      DESCRIPTION
      "A list of entries containing Cmis module host lane monitoring."
      ::= { cmmCmisModuleObjects 8 }

    cmmCmisModuleHostLaneMonitoringTableEntry OBJECT-TYPE
      SYNTAX            CmmCmisModuleHostLaneMonitoringTableEntry
      MAX-ACCESS        not-accessible
      STATUS            current
      DESCRIPTION
      "A list of table entries containing Cmis module host lane monitoring
      information."
      INDEX    { cmmStackUnitIndex, cmmCmisModuleType,
                 cmmCmisModulePortNumber, cmmCmisModuleHostLaneMonitoringAttrType,
                 cmmCmisModuleLaneNumber
               }
      ::= { cmmCmisModuleHostLaneMonitoringTable 1 }

    CmmCmisModuleHostLaneMonitoringTableEntry  ::=
      SEQUENCE {
                 cmmCmisModuleHostLaneMonitoringAttrType  CmisHostAttrMonitorings,
                 cmmCmisModuleHostLaneAttrValue           INTEGER,
                 cmmCmisModuleHostLaneAttrThreshAlertMax  INTEGER,
                 cmmCmisModuleHostLaneAttrThreshCriticalMax INTEGER,
                 cmmCmisModuleHostLaneAttrThreshCriticalMin INTEGER,
                 cmmCmisModuleHostLaneAttrThreshAlertMin    INTEGER
               }

    cmmCmisModuleHostLaneMonitoringAttrType  OBJECT-TYPE
      SYNTAX          CmisHostAttrMonitorings
      MAX-ACCESS      accessible-for-notify
      STATUS          current
      DESCRIPTION
        "Cmis Module Host lane monitoring event types"
        ::= { cmmCmisModuleHostLaneMonitoringTableEntry 1 }

    cmmCmisModuleHostLaneAttrValue  OBJECT-TYPE
      SYNTAX          INTEGER
      MAX-ACCESS      read-only
      STATUS          current
      DESCRIPTION
        "Cmis Module host lane monitoring value"
        ::= { cmmCmisModuleHostLaneMonitoringTableEntry 2 }

    cmmCmisModuleHostLaneAttrThreshAlertMax OBJECT-TYPE
      SYNTAX          INTEGER
      MAX-ACCESS      read-only
      STATUS          current
      DESCRIPTION
        "Cmis Module host lane maximum alert threshold value"
        ::= { cmmCmisModuleHostLaneMonitoringTableEntry 3 }

    cmmCmisModuleHostLaneAttrThreshCriticalMax OBJECT-TYPE
      SYNTAX          INTEGER
      MAX-ACCESS      read-only
      STATUS          current
      DESCRIPTION
        "Cmis Module host lane maximum criticcal threshold value"
        ::= { cmmCmisModuleHostLaneMonitoringTableEntry 4 }

    cmmCmisModuleHostLaneAttrThreshCriticalMin OBJECT-TYPE
      SYNTAX          INTEGER
      MAX-ACCESS      read-only
      STATUS          current
      DESCRIPTION
        "Cmis Module host lane maminum critical threshold value"
        ::= { cmmCmisModuleHostLaneMonitoringTableEntry 5 }

    cmmCmisModuleHostLaneAttrThreshAlertMin OBJECT-TYPE
      SYNTAX          INTEGER
      MAX-ACCESS      read-only
      STATUS          current
      DESCRIPTION
        "Cmis Module host lane minimum alert threshold value"
        ::= { cmmCmisModuleHostLaneMonitoringTableEntry 6 }


    cmmCmisModuleHostLaneFlagsTable OBJECT-TYPE
       SYNTAX            SEQUENCE OF CmmCmisModuleHostLaneFlagsTableEntry
       MAX-ACCESS        not-accessible
       STATUS            current
       DESCRIPTION
         "A list of entries containing Cmis module host lane flags."
       ::= { cmmCmisModuleObjects 9 }

    cmmCmisModuleHostLaneFlagsTableEntry OBJECT-TYPE
       SYNTAX            CmmCmisModuleHostLaneFlagsTableEntry
       MAX-ACCESS        not-accessible
       STATUS            current
       DESCRIPTION
         "A list of table entries containing Cmis module host lane flags
         information."
       INDEX    { cmmStackUnitIndex, cmmCmisModuleType,
                  cmmCmisModulePortNumber, cmmCmisModuleHostLaneAttrFlagType,
                  cmmCmisModuleLaneNumber
                }
         ::= { cmmCmisModuleHostLaneFlagsTable 1 }

    CmmCmisModuleHostLaneFlagsTableEntry   ::=
       SEQUENCE {
           cmmCmisModuleHostLaneAttrFlagType     CmisHostAttrFlags,
           cmmCmisModuleHostLaneFlags            TruthValue
         }

    cmmCmisModuleHostLaneAttrFlagType  OBJECT-TYPE
      SYNTAX          CmisHostAttrFlags
      MAX-ACCESS      accessible-for-notify
      STATUS          current
      DESCRIPTION
        "Cmis Module Host lane event types"
        ::= { cmmCmisModuleHostLaneFlagsTableEntry 1 }

    cmmCmisModuleHostLaneFlags OBJECT-TYPE
      SYNTAX          TruthValue
      MAX-ACCESS      read-only
      STATUS          current
      DESCRIPTION
        "Cmis Module host lane flags"
        ::= { cmmCmisModuleHostLaneFlagsTableEntry 2 }


    cmmCmisModuleHostLaneUserThresholdTable OBJECT-TYPE
       SYNTAX            SEQUENCE OF CmmCmisModuleHostLaneUserThresholdTableEntry
       MAX-ACCESS        not-accessible
       STATUS            current
       DESCRIPTION
         "A list of entries containing Cmis module host lane user threshold status."
       ::= { cmmCmisModuleObjects 10 }

    cmmCmisModuleHostLaneUserThresholdTableEntry OBJECT-TYPE
       SYNTAX            CmmCmisModuleHostLaneUserThresholdTableEntry
       MAX-ACCESS        not-accessible
       STATUS            current
       DESCRIPTION
         "A list of table entries containing Cmis module host lane user threshold
         status information."
       INDEX    { cmmStackUnitIndex, cmmCmisModuleType,
                  cmmCmisModulePortNumber, cmmCmisModuleHostLaneUTAttrType,
                  cmmCmisModuleLaneNumber
                }
         ::= { cmmCmisModuleHostLaneUserThresholdTable 1 }

    CmmCmisModuleHostLaneUserThresholdTableEntry   ::=
       SEQUENCE {
           cmmCmisModuleHostLaneUTAttrType        INTEGER,
           cmmCmisModuleHostLaneHWConfigValue     INTEGER,
           cmmCmisModuleHostLaneMinimumValue      INTEGER,
           cmmCmisModuleHostLaneMaximumValue      INTEGER,
           cmmCmisModuleHOstLaneUTValueActive     TruthValue
         }

    cmmCmisModuleHostLaneUTAttrType  OBJECT-TYPE
      SYNTAX      INTEGER {
                    txfddactive(1),
                    txfddclear(2),
                    txfedactive(3),
                    txfedclear(4)
                  }
      MAX-ACCESS      accessible-for-notify
      STATUS          current
      DESCRIPTION
        "Cmis Module Host lane user thresold attribute types"
        ::= { cmmCmisModuleHostLaneUserThresholdTableEntry 1 }

    cmmCmisModuleHostLaneHWConfigValue  OBJECT-TYPE
      SYNTAX      INTEGER
      MAX-ACCESS  read-only
      STATUS      current
      DESCRIPTION
        "Cmis Module Host lane user thresold hardware config value"
        ::= { cmmCmisModuleHostLaneUserThresholdTableEntry 2 }

    cmmCmisModuleHostLaneMinimumValue  OBJECT-TYPE
      SYNTAX      INTEGER
      MAX-ACCESS  read-only
      STATUS      current
      DESCRIPTION
        "Cmis Module Host lane user thresold minimum value"
        ::= { cmmCmisModuleHostLaneUserThresholdTableEntry 3 }

    cmmCmisModuleHostLaneMaximumValue  OBJECT-TYPE
      SYNTAX      INTEGER
      MAX-ACCESS  read-only
      STATUS      current
      DESCRIPTION
        "Cmis Module Host lane user thresold maximum value"
        ::= { cmmCmisModuleHostLaneUserThresholdTableEntry 4 }

    cmmCmisModuleHOstLaneUTValueActive  OBJECT-TYPE
      SYNTAX      TruthValue
      MAX-ACCESS  read-only
      STATUS      current
      DESCRIPTION
        "Cmis Module Host lane user thresold value active status"
        ::= { cmmCmisModuleHostLaneUserThresholdTableEntry 5 }


    cmmCmisModuleMediaLaneUserThresholdTable OBJECT-TYPE
       SYNTAX            SEQUENCE OF CmmCmisModuleMediaLaneUserThresholdTableEntry
       MAX-ACCESS        not-accessible
       STATUS            current
       DESCRIPTION
         "A list of entries containing Cmis module media lane user threshold status."
       ::= { cmmCmisModuleObjects 11 }

    cmmCmisModuleMediaLaneUserThresholdTableEntry OBJECT-TYPE
       SYNTAX            CmmCmisModuleMediaLaneUserThresholdTableEntry
       MAX-ACCESS        not-accessible
       STATUS            current
       DESCRIPTION
         "A list of table entries containing Cmis module media lane user threshold
         status information."
       INDEX    { cmmStackUnitIndex, cmmCmisModuleType,
                  cmmCmisModulePortNumber, cmmCmisModuleMediaLaneUTAttrType,
                  cmmCmisModuleLaneNumber
                }
         ::= { cmmCmisModuleMediaLaneUserThresholdTable 1 }

    CmmCmisModuleMediaLaneUserThresholdTableEntry   ::=
       SEQUENCE {
           cmmCmisModuleMediaLaneUTAttrType       INTEGER,
           cmmCmisModuleMediaLaneHWConfigValue    INTEGER,
           cmmCmisModuleMediaLaneMinimumValue     INTEGER,
           cmmCmisModuleMediaLaneMaximumValue     INTEGER,
           cmmCmisModuleMediaLaneUTValueActive    TruthValue
         }

    cmmCmisModuleMediaLaneUTAttrType  OBJECT-TYPE
      SYNTAX      INTEGER {
                    rxfddactive(1),
                    rxfddclear(2),
                    rxfedactive(3),
                    rxfedclear(4),
                    rxtotalpowerha(5),
                    rxtotalpowerhw(6),
                    rxtotalpowerlw(7),
                    rxtotalpowerla(8),
                    rxsignalpowerha(9),
                    rxsignalpowerhw(10),
                    rxsignalpowerlw(11),
                    rxsignalpowerla(12)
                  }
      MAX-ACCESS      accessible-for-notify
      STATUS          current
      DESCRIPTION
        "Cmis Module Media lane user thresold attribute types"
        ::= { cmmCmisModuleMediaLaneUserThresholdTableEntry 1 }

    cmmCmisModuleMediaLaneHWConfigValue  OBJECT-TYPE
      SYNTAX      INTEGER
      MAX-ACCESS  read-only
      STATUS      current
      DESCRIPTION
        "Cmis Module Media lane user thresold hardware config value"
        ::= { cmmCmisModuleMediaLaneUserThresholdTableEntry 2 }

    cmmCmisModuleMediaLaneMinimumValue  OBJECT-TYPE
      SYNTAX      INTEGER
      MAX-ACCESS  read-only
      STATUS      current
      DESCRIPTION
        "Cmis Module Media lane user thresold minimum value"
        ::= { cmmCmisModuleMediaLaneUserThresholdTableEntry 3 }

    cmmCmisModuleMediaLaneMaximumValue  OBJECT-TYPE
      SYNTAX      INTEGER
      MAX-ACCESS  read-only
      STATUS      current
      DESCRIPTION
        "Cmis Module Media lane user thresold maximum value"
        ::= { cmmCmisModuleMediaLaneUserThresholdTableEntry 4 }

    cmmCmisModuleMediaLaneUTValueActive  OBJECT-TYPE
      SYNTAX      TruthValue
      MAX-ACCESS  read-only
      STATUS      current
      DESCRIPTION
        "Cmis Module Media lane user thresold value active status"
        ::= { cmmCmisModuleMediaLaneUserThresholdTableEntry 5 }


    cmmCmisModuleHostLaneSIStatusTable OBJECT-TYPE
       SYNTAX            SEQUENCE OF CmmCmisModuleHostLaneSIStatusTableEntry
       MAX-ACCESS        not-accessible
       STATUS            current
       DESCRIPTION
         "A list of entries containing Cmis module host lane signal integrity status."
       ::= { cmmCmisModuleObjects 12 }

    cmmCmisModuleHostLaneSIStatusTableEntry OBJECT-TYPE
       SYNTAX            CmmCmisModuleHostLaneSIStatusTableEntry
       MAX-ACCESS        not-accessible
       STATUS            current
       DESCRIPTION
         "A list of table entries containing Cmis module host lane signal integrity
         status information."
       INDEX    { cmmStackUnitIndex, cmmCmisModuleType,
                  cmmCmisModulePortNumber, cmmCmisModuleHostLaneSIStatusAttrType,
                  cmmCmisModuleLaneNumber
                }
         ::= { cmmCmisModuleHostLaneSIStatusTable 1 }

    CmmCmisModuleHostLaneSIStatusTableEntry   ::=
       SEQUENCE {
           cmmCmisModuleHostLaneSIStatusAttrType  INTEGER,
           cmmCmisModuleHostLaneSIHWConfigValue   INTEGER
         }

    cmmCmisModuleHostLaneSIStatusAttrType  OBJECT-TYPE
      SYNTAX      INTEGER {
                    txequalization(1),
                    rxprecursoreq(2),
                    rxpostcursoreq(3),
                    rxamplitude(4),
                    txcdrbypass(5),
                    rxcdrbypass(6)
                  }
      MAX-ACCESS      accessible-for-notify
      STATUS          current
      DESCRIPTION
        "Cmis Module Host lane signal integrity attribute types"
        ::= { cmmCmisModuleHostLaneSIStatusTableEntry 1 }

    cmmCmisModuleHostLaneSIHWConfigValue  OBJECT-TYPE
      SYNTAX      INTEGER
      MAX-ACCESS  read-only
      STATUS      current
      DESCRIPTION
        "Cmis Module Host lane signal integrity hardware config value"
        ::= { cmmCmisModuleHostLaneSIStatusTableEntry 2 }


    cmmCmisModuleAdvertisementHostApplicationTable OBJECT-TYPE
      SYNTAX            SEQUENCE OF CmmCmisModuleAdvertisementHostApplicationTableEntry
      MAX-ACCESS        not-accessible
      STATUS            current
      DESCRIPTION
      "A list of entries containing Cmis module host lane advertisement application details."
      ::= { cmmCmisModuleObjects 13 }

    cmmCmisModuleAdvertisementHostApplicationTableEntry OBJECT-TYPE
      SYNTAX            CmmCmisModuleAdvertisementHostApplicationTableEntry
      MAX-ACCESS        not-accessible
      STATUS            current
      DESCRIPTION
      "A list of table entries containing Cmis module host lane advertisement application information."
      INDEX    { cmmStackUnitIndex, cmmCmisModuleType,
         cmmCmisModulePortNumber, cmmCmisModuleApplicationID }
         ::= { cmmCmisModuleAdvertisementHostApplicationTable 1 }

    CmmCmisModuleAdvertisementHostApplicationTableEntry   ::=
      SEQUENCE  {
                  cmmCmisModuleApplicationID            INTEGER,
                  cmmCmisModuleHostInterfaceType        CmisInterfaceType,
                  cmmCmisModuleHostApplicationBitrate   CmisBitRate,
                  cmmCmisModuleHostLaneCount            INTEGER,
                  cmmCmisModuleHostSignalBitrate        CmisBitRate,
                  cmmCmisModuleHostModulationFormat     CmisModulationFormat,
                  cmmCmisModuleHostBitsPerUnitInterval  INTEGER,
                  cmmCmisModuleHostLaneAssigned         CmisLanesAssigned,
                  cmmCmisModuleHostConfig               DisplayString
                }

    cmmCmisModuleApplicationID  OBJECT-TYPE
      SYNTAX          INTEGER (1..15)
      MAX-ACCESS      not-accessible
      STATUS          current
      DESCRIPTION
      "The unique Cmis module advertising application number"
      ::= { cmmCmisModuleAdvertisementHostApplicationTableEntry 1 }

    cmmCmisModuleHostInterfaceType  OBJECT-TYPE
      SYNTAX      CmisInterfaceType
      MAX-ACCESS      read-only
      STATUS          current
      DESCRIPTION
      "Cmis Module Host interface type.
      '-100002' indicates not-applicable."
      ::= { cmmCmisModuleAdvertisementHostApplicationTableEntry 2 }

    cmmCmisModuleHostApplicationBitrate  OBJECT-TYPE
      SYNTAX      CmisBitRate
      MAX-ACCESS  read-only
      STATUS      current
      DESCRIPTION
      "Cmis Module Host application bit rate value"
      ::= { cmmCmisModuleAdvertisementHostApplicationTableEntry 3 }

    cmmCmisModuleHostLaneCount  OBJECT-TYPE
      SYNTAX      INTEGER
      MAX-ACCESS  read-only
      STATUS      current
      DESCRIPTION
      "Cmis Module Host lane count"
      ::= { cmmCmisModuleAdvertisementHostApplicationTableEntry 4 }

    cmmCmisModuleHostSignalBitrate  OBJECT-TYPE
      SYNTAX      CmisBitRate
      MAX-ACCESS  read-only
      STATUS      current
      DESCRIPTION
      "Cmis Module Host signal bit rate value"
      ::= { cmmCmisModuleAdvertisementHostApplicationTableEntry 5 }

    cmmCmisModuleHostModulationFormat  OBJECT-TYPE
      SYNTAX      CmisModulationFormat
      MAX-ACCESS  read-only
      STATUS      current
      DESCRIPTION
      "Cmis Module Host modulation format.
      '-100002' indicates not-applicable."
      ::= { cmmCmisModuleAdvertisementHostApplicationTableEntry 6 }

    cmmCmisModuleHostBitsPerUnitInterval  OBJECT-TYPE
      SYNTAX      INTEGER
      UNITS       "0.01 unit"
      MAX-ACCESS  read-only
      STATUS      current
      DESCRIPTION
      "Cmis Module Host bits per unit interval value"
      ::= { cmmCmisModuleAdvertisementHostApplicationTableEntry 7 }

    cmmCmisModuleHostLaneAssigned  OBJECT-TYPE
      SYNTAX          CmisLanesAssigned
      MAX-ACCESS  read-only
      STATUS      current
      DESCRIPTION
      "Bitmap of Cmis Module Host lane assigned value"
      ::= { cmmCmisModuleAdvertisementHostApplicationTableEntry 8 }

    cmmCmisModuleHostConfig  OBJECT-TYPE
      SYNTAX      DisplayString
      MAX-ACCESS  read-only
      STATUS      current
      DESCRIPTION
      "Cmis Module Host configured breakout mode and lane speed"
      ::= { cmmCmisModuleAdvertisementHostApplicationTableEntry 9 }

    cmmCmisModuleAdvertisementMediaApplicationTable OBJECT-TYPE
      SYNTAX            SEQUENCE OF CmmCmisModuleAdvertisementMediaApplicationTableEntry
      MAX-ACCESS        not-accessible
      STATUS            current
      DESCRIPTION
      "A list of entries containing Cmis module media lane advertisement
      application details."
      ::= { cmmCmisModuleObjects 14 }

    cmmCmisModuleAdvertisementMediaApplicationTableEntry OBJECT-TYPE
      SYNTAX            CmmCmisModuleAdvertisementMediaApplicationTableEntry
      MAX-ACCESS        not-accessible
      STATUS            current
      DESCRIPTION
      "A list of table entries containing Cmis module media lane advertisement
      application information."
      INDEX    { cmmStackUnitIndex, cmmCmisModuleType,
          cmmCmisModulePortNumber, cmmCmisModuleApplicationID }
      ::= { cmmCmisModuleAdvertisementMediaApplicationTable 1 }

    CmmCmisModuleAdvertisementMediaApplicationTableEntry   ::=
      SEQUENCE  {
                  cmmCmisModuleMediaInterfaceType        CmisInterfaceType,
                  cmmCmisModuleMediaApplicationBitrate   CmisBitRate,
                  cmmCmisModuleMediaLaneCount            INTEGER,
                  cmmCmisModuleMediaSignalBitrate        CmisBitRate,
                  cmmCmisModuleMediaModulationFormat     CmisModulationFormat,
                  cmmCmisModuleMediaBitsPerUnitInterval  INTEGER,
                  cmmCmisModuleMediaLaneAssigned         CmisLanesAssigned
                }

    cmmCmisModuleMediaInterfaceType  OBJECT-TYPE
      SYNTAX      CmisInterfaceType
      MAX-ACCESS      read-only
      STATUS          current
      DESCRIPTION
      "Cmis Module Media interface type.
      '-100002' indicates not-applicable."
      ::= { cmmCmisModuleAdvertisementMediaApplicationTableEntry 1 }

    cmmCmisModuleMediaApplicationBitrate  OBJECT-TYPE
      SYNTAX      CmisBitRate
      MAX-ACCESS  read-only
      STATUS      current
      DESCRIPTION
      "Cmis Module Media application bit rate value"
      ::= { cmmCmisModuleAdvertisementMediaApplicationTableEntry 2 }

    cmmCmisModuleMediaLaneCount  OBJECT-TYPE
      SYNTAX      INTEGER
      MAX-ACCESS  read-only
      STATUS      current
      DESCRIPTION
      "Cmis Module Media lane count"
      ::= { cmmCmisModuleAdvertisementMediaApplicationTableEntry 3 }

    cmmCmisModuleMediaSignalBitrate  OBJECT-TYPE
      SYNTAX      CmisBitRate
      MAX-ACCESS  read-only
      STATUS      current
      DESCRIPTION
      "Cmis Module Media signal bit rate value"
      ::= { cmmCmisModuleAdvertisementMediaApplicationTableEntry 4 }

    cmmCmisModuleMediaModulationFormat  OBJECT-TYPE
      SYNTAX      CmisModulationFormat
      MAX-ACCESS  read-only
      STATUS      current
      DESCRIPTION
      "Cmis Module Media modulation format.
      '-100002' indicates not-applicable."
      ::= { cmmCmisModuleAdvertisementMediaApplicationTableEntry 5 }

    cmmCmisModuleMediaBitsPerUnitInterval  OBJECT-TYPE
      SYNTAX      INTEGER
      UNITS       "0.01 unit"
      MAX-ACCESS  read-only
      STATUS      current
      DESCRIPTION
      "Cmis Module Media bits per unit interval value"
      ::= { cmmCmisModuleAdvertisementMediaApplicationTableEntry 6 }

    cmmCmisModuleMediaLaneAssigned  OBJECT-TYPE
      SYNTAX      CmisLanesAssigned
      MAX-ACCESS  read-only
      STATUS      current
      DESCRIPTION
      "Bitmap of Cmis Module Media lane assigned value"
      ::= { cmmCmisModuleAdvertisementMediaApplicationTableEntry 7 }


    cmmCmisModuleAdvertisementControlsTable OBJECT-TYPE
      SYNTAX            SEQUENCE OF CmmCmisModuleAdvertisementControlsTableEntry
      MAX-ACCESS        not-accessible
      STATUS            current
      DESCRIPTION
      "A list of entries containing Cmis module advertisement control details."
      ::= { cmmCmisModuleObjects 15 }

    cmmCmisModuleAdvertisementControlsTableEntry OBJECT-TYPE
      SYNTAX            CmmCmisModuleAdvertisementControlsTableEntry
      MAX-ACCESS        not-accessible
      STATUS            current
      DESCRIPTION
      "A list of table entries containing Cmis module advertisement control
      information."
      INDEX    { cmmStackUnitIndex, cmmCmisModuleType,
          cmmCmisModulePortNumber }
      ::= { cmmCmisModuleAdvertisementControlsTable 1 }

    CmmCmisModuleAdvertisementControlsTableEntry   ::=
      SEQUENCE  {
                  cmmCmisModuleWavelengthControl         TruthValue,
                  cmmCmisModuleTunableTransmitter        TruthValue,
                  cmmCmisModuleTxOutputSquelching        INTEGER,
                  cmmCmisModuleForcedTxOutputSquelching  TruthValue,
                  cmmCmisModuleTxOutputSquelchingDisable TruthValue,
                  cmmCmisModuleTxOutputDisable           TruthValue,
                  cmmCmisModuleTxInputPolarityFlip       TruthValue,
                  cmmCmisModuleRxOutputSquelchingDisable  TruthValue,
                  cmmCmisModuleRxOutputDisable           TruthValue,
                  cmmCmisModuleRxOutputPolarityFlip      TruthValue,
                  cmmCmisModuleRxMediaFedPmImplemented   TruthValue,
                  cmmCmisModuleRxMediaFddPmImplemented   TruthValue,
                  cmmCmisModuleTxHostFedPmImplemented    TruthValue,
                  cmmCmisModuleTxHostFddPmImplemented    TruthValue
                }

    cmmCmisModuleWavelengthControl  OBJECT-TYPE
      SYNTAX      TruthValue
      MAX-ACCESS      read-only
      STATUS          current
      DESCRIPTION
      "Cmis Module wavelength control status, true(1) represents supported,
      false(2) represents not supported"
      ::= { cmmCmisModuleAdvertisementControlsTableEntry 1 }

    cmmCmisModuleTunableTransmitter  OBJECT-TYPE
      SYNTAX      TruthValue
      MAX-ACCESS      read-only
      STATUS          current
      DESCRIPTION
      "Cmis Module tunable transmitter status, true(1) represents supported,
      false(2) represents not supported"
      ::= { cmmCmisModuleAdvertisementControlsTableEntry 2 }

    cmmCmisModuleTxOutputSquelching  OBJECT-TYPE
      SYNTAX  INTEGER   {
                           not-supported(1),
                           reduces-oma(2),
                           reduces-pav(3),
                           host-controllable(4)
                        }
      MAX-ACCESS      read-only
      STATUS          current
      DESCRIPTION
      "Cmis Module tx output squelching status, true(1) represents supported,
      false(2) represents not supported"
      ::= { cmmCmisModuleAdvertisementControlsTableEntry 3 }

    cmmCmisModuleForcedTxOutputSquelching  OBJECT-TYPE
      SYNTAX      TruthValue
      MAX-ACCESS      read-only
      STATUS          current
      DESCRIPTION
      "Cmis Module forced tx output squelching status,
      true(1) represents supported,
      false(2) represents not supported"
      ::= { cmmCmisModuleAdvertisementControlsTableEntry 4 }

    cmmCmisModuleTxOutputSquelchingDisable  OBJECT-TYPE
      SYNTAX      TruthValue
      MAX-ACCESS      read-only
      STATUS          current
      DESCRIPTION
      "Cmis Module forced tx output squelching disable status,
      true(1) represents disabled,
      false(2) represents enabled"
      ::= { cmmCmisModuleAdvertisementControlsTableEntry 5 }

    cmmCmisModuleTxOutputDisable  OBJECT-TYPE
      SYNTAX      TruthValue
      MAX-ACCESS      read-only
      STATUS          current
      DESCRIPTION
      "Cmis Module forced tx output disable status,
      true(1) represents disabled,
      false(2) represents enabled"
      ::= { cmmCmisModuleAdvertisementControlsTableEntry 6 }

    cmmCmisModuleTxInputPolarityFlip  OBJECT-TYPE
      SYNTAX      TruthValue
      MAX-ACCESS      read-only
      STATUS          current
      DESCRIPTION
      "Cmis Module forced tx input polarity flip status,
      true(1) represents supported,
      false(2) represents not supported"
      ::= { cmmCmisModuleAdvertisementControlsTableEntry 7 }

    cmmCmisModuleRxOutputSquelchingDisable  OBJECT-TYPE
      SYNTAX      TruthValue
      MAX-ACCESS      read-only
      STATUS          current
      DESCRIPTION
      "Cmis Module forced rx output squelching disable status,
      true(1) represents disabled,
      false(2) represents supported"
      ::= { cmmCmisModuleAdvertisementControlsTableEntry 8 }

    cmmCmisModuleRxOutputDisable  OBJECT-TYPE
      SYNTAX      TruthValue
      MAX-ACCESS      read-only
      STATUS          current
      DESCRIPTION
      "Cmis Module forced rx output disable status,
      true(1) represents disabled,
      false(2) represents supported"
      ::= { cmmCmisModuleAdvertisementControlsTableEntry 9 }

    cmmCmisModuleRxOutputPolarityFlip  OBJECT-TYPE
      SYNTAX      TruthValue
      MAX-ACCESS      read-only
      STATUS          current
      DESCRIPTION
      "Cmis Module forced rx output disable status,
      true(1) represents disabled,
      false(2) represents supported"
      ::= { cmmCmisModuleAdvertisementControlsTableEntry 10 }

    cmmCmisModuleRxMediaFedPmImplemented  OBJECT-TYPE
      SYNTAX      TruthValue
      MAX-ACCESS      read-only
      STATUS          current
      DESCRIPTION
      "Cmis Module rx media Fed Pm implementation status,
      true(1) represents implemented,
      false(2) represents not implemented"
      ::= { cmmCmisModuleAdvertisementControlsTableEntry 11 }

    cmmCmisModuleRxMediaFddPmImplemented  OBJECT-TYPE
      SYNTAX      TruthValue
      MAX-ACCESS      read-only
      STATUS          current
      DESCRIPTION
      "Cmis Module rx media Fdd Pm implementation status,
      true(1) represents implemented,
      false(2) represents not implemented"
      ::= { cmmCmisModuleAdvertisementControlsTableEntry 12 }

    cmmCmisModuleTxHostFedPmImplemented  OBJECT-TYPE
      SYNTAX      TruthValue
      MAX-ACCESS      read-only
      STATUS          current
      DESCRIPTION
      "Cmis Module tx host Fed Pm implementation status,
      true(1) represents implemented,
      false(2) represents not implemented"
      ::= { cmmCmisModuleAdvertisementControlsTableEntry 13 }

    cmmCmisModuleTxHostFddPmImplemented  OBJECT-TYPE
      SYNTAX      TruthValue
      MAX-ACCESS      read-only
      STATUS          current
      DESCRIPTION
      "Cmis Module tx host Fdd Pm implementation status,
      true(1) represents implemented,
      false(2) represents not implemented"
      ::= { cmmCmisModuleAdvertisementControlsTableEntry 14 }

    cmmCmisModuleAdvertisementHostDiagnosticsTable OBJECT-TYPE
      SYNTAX            SEQUENCE OF CmmCmisModuleAdvertisementHostDiagnosticsTableEntry
      MAX-ACCESS        not-accessible
      STATUS            current
      DESCRIPTION
      "A list of entries containing Cmis module advertisement host diagnostics details."
      ::= { cmmCmisModuleObjects 16 }

    cmmCmisModuleAdvertisementHostDiagnosticsTableEntry OBJECT-TYPE
      SYNTAX            CmmCmisModuleAdvertisementHostDiagnosticsTableEntry
      MAX-ACCESS        not-accessible
      STATUS            current
      DESCRIPTION
      "A list of table entries containing Cmis module advertisement host
      diagnostics information."
      INDEX    { cmmStackUnitIndex, cmmCmisModuleType,
          cmmCmisModulePortNumber }
      ::= { cmmCmisModuleAdvertisementHostDiagnosticsTable 1 }

    CmmCmisModuleAdvertisementHostDiagnosticsTableEntry   ::=
      SEQUENCE  {
                  cmmCmisModuleHostLaneOutputLoopback       TruthValue,
                  cmmCmisModuleHostLaneInputLoopback        TruthValue,
                  cmmCmisModuleHostLanePerLaneLoopback      TruthValue,
                  cmmCmisModuleHostLaneReportInputSNR       TruthValue,
                  cmmCmisModuleHostLaneReportFEC            TruthValue,
                  cmmCmisModuleHostLanePrbsCheckerPostFEC   TruthValue,
                  cmmCmisModuleHostLanePrbsCheckerPreFEC    TruthValue,
                  cmmCmisModuleHostLanePrbsCheckerTypes     CmisPrbsTypes,
                  cmmCmisModuleHostLanePrbsGeneratorPostFEC TruthValue,
                  cmmCmisModuleHostLanePrbsGeneratorPreFEC  TruthValue,
                  cmmCmisModuleHostLanePrbsGeneratorTypes   CmisPrbsTypes
                }

    cmmCmisModuleHostLaneOutputLoopback  OBJECT-TYPE
      SYNTAX      TruthValue
      MAX-ACCESS      read-only
      STATUS          current
      DESCRIPTION
      "Cmis Module host lane output loopback status,
      true(1) represents supported,
      false(2) represents not supported"
      ::= { cmmCmisModuleAdvertisementHostDiagnosticsTableEntry 1 }

    cmmCmisModuleHostLaneInputLoopback  OBJECT-TYPE
      SYNTAX      TruthValue
      MAX-ACCESS      read-only
      STATUS          current
      DESCRIPTION
      "Cmis Module host lane input loopback status,
      true(1) represents supported,
      false(2) represents not supported"
      ::= { cmmCmisModuleAdvertisementHostDiagnosticsTableEntry 2 }

    cmmCmisModuleHostLanePerLaneLoopback  OBJECT-TYPE
      SYNTAX      TruthValue
      MAX-ACCESS      read-only
      STATUS          current
      DESCRIPTION
      "Cmis Module host side per lane loopback status,
      true(1) represents supported,
      false(2) represents not supported"
      ::= { cmmCmisModuleAdvertisementHostDiagnosticsTableEntry 3 }

    cmmCmisModuleHostLaneReportInputSNR  OBJECT-TYPE
      SYNTAX      TruthValue
      MAX-ACCESS      read-only
      STATUS          current
      DESCRIPTION
      "Cmis Module host lane report input SNR status,
      true(1) represents supported,
      false(2) represents not supported"
      ::= { cmmCmisModuleAdvertisementHostDiagnosticsTableEntry 4 }

    cmmCmisModuleHostLaneReportFEC  OBJECT-TYPE
      SYNTAX      TruthValue
      MAX-ACCESS      read-only
      STATUS          current
      DESCRIPTION
      "Cmis Module host lane report FEC status,
      true(1) represents supported,
      false(2) represents not supported"
      ::= { cmmCmisModuleAdvertisementHostDiagnosticsTableEntry 5 }

    cmmCmisModuleHostLanePrbsCheckerPostFEC  OBJECT-TYPE
      SYNTAX      TruthValue
      MAX-ACCESS      read-only
      STATUS          current
      DESCRIPTION
      "Cmis Module host lane prbs checker post FEC status,
      true(1) represents supported,
      false(2) represents not supported"
      ::= { cmmCmisModuleAdvertisementHostDiagnosticsTableEntry 6 }

    cmmCmisModuleHostLanePrbsCheckerPreFEC  OBJECT-TYPE
      SYNTAX      TruthValue
      MAX-ACCESS      read-only
      STATUS          current
      DESCRIPTION
      "Cmis Module host lane prbs checker pre FEC status,
      true(1) represents supported,
      false(2) represents not supported"
      ::= { cmmCmisModuleAdvertisementHostDiagnosticsTableEntry 7 }

    cmmCmisModuleHostLanePrbsCheckerTypes  OBJECT-TYPE
      SYNTAX          CmisPrbsTypes
      MAX-ACCESS      read-only
      STATUS          current
      DESCRIPTION
      "Bitmap of cmis Module host lane prbs checker types."
      ::= { cmmCmisModuleAdvertisementHostDiagnosticsTableEntry 8 }

    cmmCmisModuleHostLanePrbsGeneratorPostFEC  OBJECT-TYPE
      SYNTAX          TruthValue
      MAX-ACCESS      read-only
      STATUS          current
      DESCRIPTION
      "Cmis Module host lane prbs generator post FEC status,
      true(1) represents supported,
      false(2) represents not supported"
      ::= { cmmCmisModuleAdvertisementHostDiagnosticsTableEntry 9 }

    cmmCmisModuleHostLanePrbsGeneratorPreFEC  OBJECT-TYPE
      SYNTAX          TruthValue
      MAX-ACCESS      read-only
      STATUS          current
      DESCRIPTION
      "Cmis Module host lane prbs generator pre FEC status,
      true(1) represents supported,
      false(2) represents not supported"
      ::= { cmmCmisModuleAdvertisementHostDiagnosticsTableEntry 10 }

    cmmCmisModuleHostLanePrbsGeneratorTypes  OBJECT-TYPE
      SYNTAX          CmisPrbsTypes
      MAX-ACCESS      read-only
      STATUS          current
      DESCRIPTION
      "Bitmap of cmis module host lane prbs generator types."
      ::= { cmmCmisModuleAdvertisementHostDiagnosticsTableEntry 11 }


    cmmCmisModuleAdvertisementMediaDiagnosticsTable OBJECT-TYPE
      SYNTAX            SEQUENCE OF CmmCmisModuleAdvertisementMediaDiagnosticsTableEntry
      MAX-ACCESS        not-accessible
      STATUS            current
      DESCRIPTION
      "A list of entries containing Cmis module advertisement media
      diagnostics details."
      ::= { cmmCmisModuleObjects 17 }

    cmmCmisModuleAdvertisementMediaDiagnosticsTableEntry OBJECT-TYPE
      SYNTAX            CmmCmisModuleAdvertisementMediaDiagnosticsTableEntry
      MAX-ACCESS        not-accessible
      STATUS            current
      DESCRIPTION
      "A list of table entries containing Cmis module advertisement media
      diagnostics information."
      INDEX    { cmmStackUnitIndex, cmmCmisModuleType,
          cmmCmisModulePortNumber }
      ::= { cmmCmisModuleAdvertisementMediaDiagnosticsTable 1 }

    CmmCmisModuleAdvertisementMediaDiagnosticsTableEntry   ::=
      SEQUENCE  {
                  cmmCmisModuleMediaLaneOutputLoopback       TruthValue,
                  cmmCmisModuleMediaLaneInputLoopback        TruthValue,
                  cmmCmisModuleMediaLanePerLaneLoopback      TruthValue,
                  cmmCmisModuleMediaLaneReportInputSNR       TruthValue,
                  cmmCmisModuleMediaLaneReportFEC            TruthValue,
                  cmmCmisModuleMediaLanePrbsCheckerPostFEC   TruthValue,
                  cmmCmisModuleMediaLanePrbsCheckerPreFEC    TruthValue,
                  cmmCmisModuleMediaLanePrbsCheckerTypes     CmisPrbsTypes,
                  cmmCmisModuleMediaLanePrbsGeneratorPostFEC TruthValue,
                  cmmCmisModuleMediaLanePrbsGeneratorPreFEC  TruthValue,
                  cmmCmisModuleMediaLanePrbsGeneratorTypes   CmisPrbsTypes
                }

    cmmCmisModuleMediaLaneOutputLoopback  OBJECT-TYPE
      SYNTAX          TruthValue
      MAX-ACCESS      read-only
      STATUS          current
      DESCRIPTION
      "Cmis Module media lane output loopback status,
      true(1) represents supported,
      false(2) represents not supported"
      ::= { cmmCmisModuleAdvertisementMediaDiagnosticsTableEntry 1 }

    cmmCmisModuleMediaLaneInputLoopback  OBJECT-TYPE
      SYNTAX          TruthValue
      MAX-ACCESS      read-only
      STATUS          current
      DESCRIPTION
      "Cmis Module media lane input loopback status,
      true(1) represents supported,
      false(2) represents not supported"
      ::= { cmmCmisModuleAdvertisementMediaDiagnosticsTableEntry 2 }

    cmmCmisModuleMediaLanePerLaneLoopback  OBJECT-TYPE
      SYNTAX          TruthValue
      MAX-ACCESS      read-only
      STATUS          current
      DESCRIPTION
      "Cmis Module media side per lane loopback status,
      true(1) represents supported,
      false(2) represents not supported"
      ::= { cmmCmisModuleAdvertisementMediaDiagnosticsTableEntry 3 }

    cmmCmisModuleMediaLaneReportInputSNR  OBJECT-TYPE
      SYNTAX          TruthValue
      MAX-ACCESS      read-only
      STATUS          current
      DESCRIPTION
      "Cmis Module media lane report input SNR status,
      true(1) represents supported,
      false(2) represents not supported"
      ::= { cmmCmisModuleAdvertisementMediaDiagnosticsTableEntry 4 }

    cmmCmisModuleMediaLaneReportFEC  OBJECT-TYPE
      SYNTAX          TruthValue
      MAX-ACCESS      read-only
      STATUS          current
      DESCRIPTION
      "Cmis Module media lane report FEC status,
      true(1) represents supported,
      false(2) represents not supported"
      ::= { cmmCmisModuleAdvertisementMediaDiagnosticsTableEntry 5 }

    cmmCmisModuleMediaLanePrbsCheckerPostFEC  OBJECT-TYPE
      SYNTAX          TruthValue
      MAX-ACCESS      read-only
      STATUS          current
      DESCRIPTION
      "Cmis Module media lane prbs checker post FEC status,
      true(1) represents supported,
      false(2) represents not supported"
      ::= { cmmCmisModuleAdvertisementMediaDiagnosticsTableEntry 6 }

    cmmCmisModuleMediaLanePrbsCheckerPreFEC  OBJECT-TYPE
      SYNTAX          TruthValue
      MAX-ACCESS      read-only
      STATUS          current
      DESCRIPTION
      "Cmis Module media lane prbs checker pre FEC status,
      true(1) represents supported,
      false(2) represents not supported"
      ::= { cmmCmisModuleAdvertisementMediaDiagnosticsTableEntry 7 }

    cmmCmisModuleMediaLanePrbsCheckerTypes  OBJECT-TYPE
      SYNTAX          CmisPrbsTypes
      MAX-ACCESS      read-only
      STATUS          current
      DESCRIPTION
      "Bitmap of cmis module media lane prbs checker types."
      ::= { cmmCmisModuleAdvertisementMediaDiagnosticsTableEntry 8 }

    cmmCmisModuleMediaLanePrbsGeneratorPostFEC  OBJECT-TYPE
      SYNTAX          TruthValue
      MAX-ACCESS      read-only
      STATUS          current
      DESCRIPTION
      "Cmis Module media lane prbs generator post FEC status,
      true(1) represents supported,
      false(2) represents not supported"
      ::= { cmmCmisModuleAdvertisementMediaDiagnosticsTableEntry 9 }

    cmmCmisModuleMediaLanePrbsGeneratorPreFEC  OBJECT-TYPE
      SYNTAX          TruthValue
      MAX-ACCESS      read-only
      STATUS          current
      DESCRIPTION
      "Cmis Module media lane prbs generator pre FEC status,
      true(1) represents supported,
      false(2) represents not supported"
      ::= { cmmCmisModuleAdvertisementMediaDiagnosticsTableEntry 10 }

    cmmCmisModuleMediaLanePrbsGeneratorTypes  OBJECT-TYPE
      SYNTAX          CmisPrbsTypes
      MAX-ACCESS      read-only
      STATUS          current
      DESCRIPTION
      "Bitmap of cmis Module media lane prbs generator types."
      ::= { cmmCmisModuleAdvertisementMediaDiagnosticsTableEntry 11 }


    cmmCmisModuleAdvertisementModuleDiagnosticsTable OBJECT-TYPE
      SYNTAX            SEQUENCE OF CmmCmisModuleAdvertisementModuleDiagnosticsTableEntry
      MAX-ACCESS        not-accessible
      STATUS            current
      DESCRIPTION
      "A list of entries containing Cmis advertisement module diagnostics details."
      ::= { cmmCmisModuleObjects 18 }

    cmmCmisModuleAdvertisementModuleDiagnosticsTableEntry OBJECT-TYPE
      SYNTAX            CmmCmisModuleAdvertisementModuleDiagnosticsTableEntry
      MAX-ACCESS        not-accessible
      STATUS            current
      DESCRIPTION
      "A list of table entries containing Cmis advertisement module diagnostics
      information."
      INDEX    { cmmStackUnitIndex, cmmCmisModuleType,
          cmmCmisModulePortNumber }
      ::= { cmmCmisModuleAdvertisementModuleDiagnosticsTable 1 }

    CmmCmisModuleAdvertisementModuleDiagnosticsTableEntry   ::=
      SEQUENCE  {
                  cmmCmisModuleSimultaneousHostAndMediaLoopback  TruthValue,
                  cmmCmisModuleReportBitErrorRatio               TruthValue,
                  cmmCmisModuleCountBitsAndErrors                TruthValue
                }

    cmmCmisModuleSimultaneousHostAndMediaLoopback  OBJECT-TYPE
      SYNTAX          TruthValue
      MAX-ACCESS      read-only
      STATUS          current
      DESCRIPTION
      "Cmis Module simultaneous host and media lane loopback status,
      true(1) represents supported,
      false(2) represents not supported"
      ::= { cmmCmisModuleAdvertisementModuleDiagnosticsTableEntry 1 }

    cmmCmisModuleReportBitErrorRatio  OBJECT-TYPE
      SYNTAX          TruthValue
      MAX-ACCESS      read-only
      STATUS          current
      DESCRIPTION
      "Cmis Module report bit error ratio status,
      true(1) represents supported,
      false(2) represents not supported"
      ::= { cmmCmisModuleAdvertisementModuleDiagnosticsTableEntry 2 }

    cmmCmisModuleCountBitsAndErrors  OBJECT-TYPE
      SYNTAX          TruthValue
      MAX-ACCESS      read-only
      STATUS          current
      DESCRIPTION
      "Cmis Module count bits and error status,
      true(1) represents supported,
      false(2) represents not supported"
      ::= { cmmCmisModuleAdvertisementModuleDiagnosticsTableEntry 3 }


    cmmCmisModuleAdvertisementDurationsTable OBJECT-TYPE
      SYNTAX            SEQUENCE OF CmmCmisModuleAdvertisementDurationsTableEntry
      MAX-ACCESS        not-accessible
      STATUS            current
      DESCRIPTION
      "A list of entries containing Cmis advertisement durations details."
      ::= { cmmCmisModuleObjects 19 }

    cmmCmisModuleAdvertisementDurationsTableEntry OBJECT-TYPE
      SYNTAX            CmmCmisModuleAdvertisementDurationsTableEntry
      MAX-ACCESS        not-accessible
      STATUS            current
      DESCRIPTION
      "A list of table entries containing Cmis advertisement duration information."
      INDEX    { cmmStackUnitIndex, cmmCmisModuleType,
          cmmCmisModulePortNumber }
      ::= { cmmCmisModuleAdvertisementDurationsTable 1 }

    CmmCmisModuleAdvertisementDurationsTableEntry   ::=
      SEQUENCE  {
                  cmmCmisModuleModSelWaitTime        INTEGER,
                  cmmCmisModuleDpInitMaxDuration     CmisDurationsTime,
                  cmmCmisModuleDpDeInitMaxDuration   CmisDurationsTime,
                  cmmCmisModuleDpTurnOnMaxDuration   CmisDurationsTime,
                  cmmCmisModuleDpTurnOffMaxDuration  CmisDurationsTime,
                  cmmCmisModulePowerUpMaxDuration    CmisDurationsTime,
                  cmmCmisModulePowerDownMaxDuration  CmisDurationsTime,
                  cmmCmisModuleNpInitMaxDuration     CmisDurationsTime,
                  cmmCmisModuleNpDeInitMaxDuration   CmisDurationsTime,
                  cmmCmisModuleNpTurnOnMaxDuration   CmisDurationsTime,
                  cmmCmisModuleNpTurnOffMaxDuration  CmisDurationsTime
                }

    cmmCmisModuleModSelWaitTime  OBJECT-TYPE
      SYNTAX          INTEGER
      UNITS           "us"
      MAX-ACCESS      read-only
      STATUS          current
      DESCRIPTION
      "Cmis Module mod sel wait time in micro seconds.
      '-100002' indicates not-applicable."
      ::= { cmmCmisModuleAdvertisementDurationsTableEntry 1 }

    cmmCmisModuleDpInitMaxDuration  OBJECT-TYPE
      SYNTAX      CmisDurationsTime
      MAX-ACCESS      read-only
      STATUS          current
      DESCRIPTION
      "Cmis Module dp init maximum time"
      ::= { cmmCmisModuleAdvertisementDurationsTableEntry 2 }

    cmmCmisModuleDpDeInitMaxDuration  OBJECT-TYPE
      SYNTAX      CmisDurationsTime
      MAX-ACCESS      read-only
      STATUS          current
      DESCRIPTION
      "Cmis Module dp de-init maximum time"
      ::= { cmmCmisModuleAdvertisementDurationsTableEntry 3 }

    cmmCmisModuleDpTurnOnMaxDuration  OBJECT-TYPE
      SYNTAX      CmisDurationsTime
      MAX-ACCESS      read-only
      STATUS          current
      DESCRIPTION
      "Cmis Module dp turn on maximum time"
      ::= { cmmCmisModuleAdvertisementDurationsTableEntry 4 }

    cmmCmisModuleDpTurnOffMaxDuration  OBJECT-TYPE
      SYNTAX      CmisDurationsTime
      MAX-ACCESS      read-only
      STATUS          current
      DESCRIPTION
      "Cmis Module dp turn off maximum time"
      ::= { cmmCmisModuleAdvertisementDurationsTableEntry 5 }

    cmmCmisModulePowerUpMaxDuration  OBJECT-TYPE
      SYNTAX      CmisDurationsTime
      MAX-ACCESS      read-only
      STATUS          current
      DESCRIPTION
      "Cmis Module power up maximum time"
      ::= { cmmCmisModuleAdvertisementDurationsTableEntry 6 }

    cmmCmisModulePowerDownMaxDuration  OBJECT-TYPE
      SYNTAX      CmisDurationsTime
      MAX-ACCESS      read-only
      STATUS          current
      DESCRIPTION
      "Cmis Module power down maximum time"
      ::= { cmmCmisModuleAdvertisementDurationsTableEntry 7 }

    cmmCmisModuleNpInitMaxDuration  OBJECT-TYPE
      SYNTAX      CmisDurationsTime
      MAX-ACCESS      read-only
      STATUS          current
      DESCRIPTION
      "Cmis Module np init maximum time.
      '-100002' indicates not-applicable."
      ::= { cmmCmisModuleAdvertisementDurationsTableEntry 8 }

    cmmCmisModuleNpDeInitMaxDuration  OBJECT-TYPE
      SYNTAX      CmisDurationsTime
      MAX-ACCESS      read-only
      STATUS          current
      DESCRIPTION
      "Cmis Module np de-init maximum time.
      '-100002' indicates not-applicable."
      ::= { cmmCmisModuleAdvertisementDurationsTableEntry 9 }

    cmmCmisModuleNpTurnOnMaxDuration  OBJECT-TYPE
      SYNTAX      CmisDurationsTime
      MAX-ACCESS      read-only
      STATUS          current
      DESCRIPTION
      "Cmis Module np turn-on maximum time.
      '-100002' indicates not-applicable."
      ::= { cmmCmisModuleAdvertisementDurationsTableEntry 10 }

    cmmCmisModuleNpTurnOffMaxDuration  OBJECT-TYPE
      SYNTAX      CmisDurationsTime
      MAX-ACCESS      read-only
      STATUS          current
      DESCRIPTION
      "Cmis Module np turn-on maximum time.
      '-100002' indicates not-applicable."
      ::= { cmmCmisModuleAdvertisementDurationsTableEntry 11 }


    cmmCmisModuleAdvertisementLaserTable OBJECT-TYPE
      SYNTAX            SEQUENCE OF CmmCmisModuleAdvertisementLaserTableEntry
      MAX-ACCESS        not-accessible
      STATUS            current
      DESCRIPTION
      "A list of entries containing Cmis advertisement laser details."
      ::= { cmmCmisModuleObjects 20 }

    cmmCmisModuleAdvertisementLaserTableEntry OBJECT-TYPE
      SYNTAX            CmmCmisModuleAdvertisementLaserTableEntry
      MAX-ACCESS        not-accessible
      STATUS            current
      DESCRIPTION
      "A list of table entries containing Cmis advertisement laser information."
      INDEX    { cmmStackUnitIndex, cmmCmisModuleType,
          cmmCmisModulePortNumber }
      ::= { cmmCmisModuleAdvertisementLaserTable 1 }

    CmmCmisModuleAdvertisementLaserTableEntry   ::=
      SEQUENCE  {
                  cmmCmisModuleSupportedGrids           BITS,
                  cmmCmisModuleFineTuningSupport        TruthValue,
                  cmmCmisModuleFineTuningResolution     INTEGER,
                  cmmCmisModuleFineTuningLowOfsset      INTEGER,
                  cmmCmisModuleFineTuningHighOffset     INTEGER,
                  cmmCmisModulePerLaneProgramOutputPwr  TruthValue,
                  cmmCmisModuleMinProgrammableOutputPwr INTEGER,
                  cmmCmisModuleMaxProgrammableOutputPwr INTEGER
                }


    cmmCmisModuleSupportedGrids  OBJECT-TYPE
      SYNTAX  BITS   {
                       lasergrid3p125ghz(0),
                       lasergrid6p25ghz(1),
                       lasergrid12p5ghz(2),
                       lasergrid25ghz(3),
                       lasergrid50ghz(4),
                       lasergrid100ghz(5),
                       lasergrid33ghz(6),
                       lasergrid75ghz(7)
                     }
      MAX-ACCESS      read-only
      STATUS          current
      DESCRIPTION
      "Cmis Module supported laser grid value"
      ::= { cmmCmisModuleAdvertisementLaserTableEntry 1 }

    cmmCmisModuleFineTuningSupport  OBJECT-TYPE
      SYNTAX      TruthValue
      MAX-ACCESS      read-only
      STATUS          current
      DESCRIPTION
      "Cmis Module laser grid status,
      true(1) represents supported,
      false(2) represents not supported"
      ::= { cmmCmisModuleAdvertisementLaserTableEntry 2 }

    cmmCmisModuleFineTuningResolution  OBJECT-TYPE
      SYNTAX      INTEGER
      UNITS           "0.001 GHz"
      MAX-ACCESS      read-only
      STATUS          current
      DESCRIPTION
      "Cmis Module laser fine tuning resolution value"
      ::= { cmmCmisModuleAdvertisementLaserTableEntry 3 }

    cmmCmisModuleFineTuningLowOfsset  OBJECT-TYPE
      SYNTAX      INTEGER
      UNITS           "0.001 GHz"
      MAX-ACCESS      read-only
      STATUS          current
      DESCRIPTION
      "Cmis Module laser fine tuning low offset value"
      ::= { cmmCmisModuleAdvertisementLaserTableEntry 4 }

    cmmCmisModuleFineTuningHighOffset  OBJECT-TYPE
      SYNTAX      INTEGER
      UNITS           "0.001 GHz"
      MAX-ACCESS      read-only
      STATUS          current
      DESCRIPTION
      "Cmis Module laser fine tuning high offset value"
      ::= { cmmCmisModuleAdvertisementLaserTableEntry 5 }

    cmmCmisModulePerLaneProgramOutputPwr  OBJECT-TYPE
      SYNTAX      TruthValue
      MAX-ACCESS      read-only
      STATUS          current
      DESCRIPTION
      "Cmis Module laser grid status,
      true(1) represents supported,
      false(2) represents not supported"
      ::= { cmmCmisModuleAdvertisementLaserTableEntry 6 }

    cmmCmisModuleMinProgrammableOutputPwr  OBJECT-TYPE
      SYNTAX      INTEGER
      UNITS           "0.001 dBm"
      MAX-ACCESS      read-only
      STATUS          current
      DESCRIPTION
      "Cmis Module laser minimum programmable output power value"
      ::= { cmmCmisModuleAdvertisementLaserTableEntry 7 }

    cmmCmisModuleMaxProgrammableOutputPwr  OBJECT-TYPE
      SYNTAX      INTEGER
      UNITS           "0.001 dBm"
      MAX-ACCESS      read-only
      STATUS          current
      DESCRIPTION
      "Cmis Module laser maximum programmable output power value"
      ::= { cmmCmisModuleAdvertisementLaserTableEntry 8 }

    cmmCmisModuleAdvertisementLaserGridsSpacingTable OBJECT-TYPE
      SYNTAX            SEQUENCE OF CmmCmisModuleAdvertisementLaserGridsSpacingTableEntry
      MAX-ACCESS        not-accessible
      STATUS            current
      DESCRIPTION
      "A list of entries containing Cmis advertisement laser grids spacing details."
      ::= { cmmCmisModuleObjects 21 }

    cmmCmisModuleAdvertisementLaserGridsSpacingTableEntry OBJECT-TYPE
      SYNTAX            CmmCmisModuleAdvertisementLaserGridsSpacingTableEntry
      MAX-ACCESS        not-accessible
      STATUS            current
      DESCRIPTION
      "A list of table entries containing Cmis advertisement laser grids
      spacing information."
      INDEX    { cmmStackUnitIndex, cmmCmisModuleType,
        cmmCmisModulePortNumber, cmmCmisModuleLaserGridSpacingType }
        ::= { cmmCmisModuleAdvertisementLaserGridsSpacingTable 1 }

    CmmCmisModuleAdvertisementLaserGridsSpacingTableEntry   ::=
        SEQUENCE  {
          cmmCmisModuleLaserGridSpacingType        INTEGER,
          cmmCmisModuleLaserGridSpacingSupported   TruthValue,
          cmmCmisModuleLowestChannelFreq           INTEGER,
          cmmCmisModuleHighestChannelFreq          INTEGER,
          cmmCmisModuleChannelCount                INTEGER
        }

    cmmCmisModuleLaserGridSpacingType  OBJECT-TYPE
      SYNTAX  INTEGER   {
                          lasergrid3p125ghz(1),
                          lasergrid6p25ghz(2),
                          lasergrid12p5ghz(3),
                          lasergrid25ghz(4),
                          lasergrid50ghz(5),
                          lasergrid100ghz(6),
                          lasergrid33ghz(7),
                          lasergrid75ghz(8)
                         }
      MAX-ACCESS      read-only
      STATUS          current
      DESCRIPTION
      "Cmis Module laser grid spacing type"
      ::= { cmmCmisModuleAdvertisementLaserGridsSpacingTableEntry 1 }

    cmmCmisModuleLaserGridSpacingSupported  OBJECT-TYPE
      SYNTAX          TruthValue
      MAX-ACCESS      read-only
      STATUS          current
      DESCRIPTION
      "Cmis Module laser grid spacing type supported value,
      true(1) represents supported,
      false(2) represents not supported"
      ::= { cmmCmisModuleAdvertisementLaserGridsSpacingTableEntry 2 }

    cmmCmisModuleLowestChannelFreq  OBJECT-TYPE
      SYNTAX          INTEGER
      UNITS           "0.001 THz"
      MAX-ACCESS      read-only
      STATUS          current
      DESCRIPTION
      "Cmis Module laser grid lowest channel frequency value.
      '-100002' indicates not-applicable."
      ::= { cmmCmisModuleAdvertisementLaserGridsSpacingTableEntry 3 }

    cmmCmisModuleHighestChannelFreq  OBJECT-TYPE
      SYNTAX          INTEGER
      UNITS           "0.001 THz"
      MAX-ACCESS      read-only
      STATUS          current
      DESCRIPTION
      "Cmis Module laser grid highest channel frequency value.
      '-100002' indicates not-applicable."
      ::= { cmmCmisModuleAdvertisementLaserGridsSpacingTableEntry 4 }

    cmmCmisModuleChannelCount  OBJECT-TYPE
      SYNTAX          INTEGER
      MAX-ACCESS      read-only
      STATUS          current
      DESCRIPTION
      "Cmis Module laser grid channel count value.
      '-100002' indicates not-applicable."
      ::= { cmmCmisModuleAdvertisementLaserGridsSpacingTableEntry 5 }

    cmmCmisModuleAdvertisementHostFlagsTable OBJECT-TYPE
      SYNTAX            SEQUENCE OF CmmCmisModuleAdvertisementHostFlagsTableEntry
      MAX-ACCESS        not-accessible
      STATUS            current
      DESCRIPTION
      "A list of entries containing Cmis advertisement host flags details."
      ::= { cmmCmisModuleObjects 22 }

    cmmCmisModuleAdvertisementHostFlagsTableEntry OBJECT-TYPE
      SYNTAX            CmmCmisModuleAdvertisementHostFlagsTableEntry
      MAX-ACCESS        not-accessible
      STATUS            current
      DESCRIPTION
      "A list of table entries containing Cmis advertisement host flags
      information."
      INDEX    { cmmStackUnitIndex, cmmCmisModuleType,
          cmmCmisModulePortNumber, cmmCmisAdvertisementModuleHostAttrFlagType }
      ::= { cmmCmisModuleAdvertisementHostFlagsTable 1 }

    CmmCmisModuleAdvertisementHostFlagsTableEntry   ::=
      SEQUENCE  {
                  cmmCmisAdvertisementModuleHostAttrFlagType     CmisHostAttrFlags,
                  cmmCmisAdvertisementModuleHostFlagsSupported   TruthValue
                }

    cmmCmisAdvertisementModuleHostAttrFlagType  OBJECT-TYPE
      SYNTAX          CmisHostAttrFlags
      MAX-ACCESS      read-only
      STATUS          current
      DESCRIPTION
      "Cmis Module advertisemnt host attr type information"
      ::= { cmmCmisModuleAdvertisementHostFlagsTableEntry 1 }

    cmmCmisAdvertisementModuleHostFlagsSupported   OBJECT-TYPE
      SYNTAX          TruthValue
      MAX-ACCESS      read-only
      STATUS          current
      DESCRIPTION
      "Cmis Module advertisement host attr supported information,
      true(1) represents supported,
      false(2) represents not supported"
      ::= { cmmCmisModuleAdvertisementHostFlagsTableEntry 2 }

    cmmCmisModuleAdvertisementHostMonitoringsTable OBJECT-TYPE
      SYNTAX            SEQUENCE OF CmmCmisModuleAdvertisementHostMonitoringsTableEntry
      MAX-ACCESS        not-accessible
      STATUS            current
      DESCRIPTION
      "A list of entries containing Cmis advertisement media monitorings
      details."
      ::= { cmmCmisModuleObjects 23 }

    cmmCmisModuleAdvertisementHostMonitoringsTableEntry OBJECT-TYPE
      SYNTAX            CmmCmisModuleAdvertisementHostMonitoringsTableEntry
      MAX-ACCESS        not-accessible
      STATUS            current
      DESCRIPTION
      "A list of table entries containing Cmis advertisement host monitorings
      information."
      INDEX    { cmmStackUnitIndex, cmmCmisModuleType,
      cmmCmisModulePortNumber, cmmCmisAdvertisementModuleHostMonitoringAttrType }
      ::= { cmmCmisModuleAdvertisementHostMonitoringsTable 1 }

    CmmCmisModuleAdvertisementHostMonitoringsTableEntry   ::=
        SEQUENCE  {
          cmmCmisAdvertisementModuleHostMonitoringAttrType   CmisHostAttrMonitorings,
          cmmCmisAdvertisementModuleHostMonitoringSupported  TruthValue,
          cmmCmisAdvertisementModuleHostLanesAssigned        CmisLanesAssigned
        }

    cmmCmisAdvertisementModuleHostMonitoringAttrType  OBJECT-TYPE
      SYNTAX          CmisHostAttrMonitorings
      MAX-ACCESS      read-only
      STATUS          current
      DESCRIPTION
      "Cmis Module advertisement host monitorings attr type information.
      '-100002' indicates not-applicable."
      ::= { cmmCmisModuleAdvertisementHostMonitoringsTableEntry 1 }

    cmmCmisAdvertisementModuleHostMonitoringSupported OBJECT-TYPE
      SYNTAX          TruthValue
      MAX-ACCESS      read-only
      STATUS          current
      DESCRIPTION
      "Cmis Module advertisement host monitorings supported information,
      true(1) represents supported,
      false(2) represents not supported"
      ::= { cmmCmisModuleAdvertisementHostMonitoringsTableEntry 2 }

   cmmCmisAdvertisementModuleHostLanesAssigned  OBJECT-TYPE
      SYNTAX          CmisLanesAssigned
      MAX-ACCESS      read-only
      STATUS          current
      DESCRIPTION
      "Bitmap of Cmis Module Host lane assigned value"
      ::= { cmmCmisModuleAdvertisementHostMonitoringsTableEntry 3 }

    cmmCmisModuleAdvertisementMediaFlagsTable OBJECT-TYPE
      SYNTAX            SEQUENCE OF CmmCmisModuleAdvertisementMediaFlagsTableEntry
      MAX-ACCESS        not-accessible
      STATUS            current
      DESCRIPTION
      "A list of entries containing Cmis advertisement media flags details."
      ::= { cmmCmisModuleObjects 24 }

    cmmCmisModuleAdvertisementMediaFlagsTableEntry OBJECT-TYPE
      SYNTAX            CmmCmisModuleAdvertisementMediaFlagsTableEntry
      MAX-ACCESS        not-accessible
      STATUS            current
      DESCRIPTION
      "A list of table entries containing Cmis advertisement media flags
      information."
      INDEX    { cmmStackUnitIndex, cmmCmisModuleType,
          cmmCmisModulePortNumber, cmmCmisAdvertisementModuleMediaAttrFlagType }
      ::= { cmmCmisModuleAdvertisementMediaFlagsTable 1 }

    CmmCmisModuleAdvertisementMediaFlagsTableEntry   ::=
      SEQUENCE  {
                  cmmCmisAdvertisementModuleMediaAttrFlagType   CmisMediaAttrFlags,
                  cmmCmisAdvertisementModuleMediaFlagsSupported TruthValue
                }

    cmmCmisAdvertisementModuleMediaAttrFlagType  OBJECT-TYPE
      SYNTAX          CmisMediaAttrFlags
      MAX-ACCESS      read-only
      STATUS          current
      DESCRIPTION
      "Cmis Module advertisement media flags attr type information"
      ::= { cmmCmisModuleAdvertisementMediaFlagsTableEntry 1 }

    cmmCmisAdvertisementModuleMediaFlagsSupported OBJECT-TYPE
      SYNTAX          TruthValue
      MAX-ACCESS      read-only
      STATUS          current
      DESCRIPTION
      "Cmis Module advertisement media flags supported information,
      true(1) represents supported,
       false(2) represents not supported"
      ::= { cmmCmisModuleAdvertisementMediaFlagsTableEntry 2 }

    cmmCmisModuleAdvertisementMediaMonitoringsTable OBJECT-TYPE
      SYNTAX            SEQUENCE OF CmmCmisModuleAdvertisementMediaMonitoringsTableEntry
      MAX-ACCESS        not-accessible
      STATUS            current
      DESCRIPTION
      "A list of entries containing Cmis advertisement media monitorings
      details."
      ::= { cmmCmisModuleObjects 25 }

    cmmCmisModuleAdvertisementMediaMonitoringsTableEntry OBJECT-TYPE
      SYNTAX            CmmCmisModuleAdvertisementMediaMonitoringsTableEntry
      MAX-ACCESS        not-accessible
      STATUS            current
      DESCRIPTION
      "A list of table entries containing Cmis advertisement media monitorings
      information."
      INDEX    { cmmStackUnitIndex, cmmCmisModuleType,
        cmmCmisModulePortNumber, cmmCmisAdvertisementModuleMediaMonitoringAttrType }
        ::= { cmmCmisModuleAdvertisementMediaMonitoringsTable 1 }

   CmmCmisModuleAdvertisementMediaMonitoringsTableEntry   ::=
     SEQUENCE  {
       cmmCmisAdvertisementModuleMediaMonitoringAttrType   CmisMediaAttrMonitorings,
       cmmCmisAdvertisementModuleMediaMonitoringSupported  TruthValue,
       cmmCmisAdvertisementModuleMediaLanesAssigned        CmisLanesAssigned
     }

   cmmCmisAdvertisementModuleMediaMonitoringAttrType  OBJECT-TYPE
     SYNTAX          CmisMediaAttrMonitorings
     MAX-ACCESS      read-only
     STATUS          current
     DESCRIPTION
     "Cmis Module advertisement media monitorings attr type information"
     ::= { cmmCmisModuleAdvertisementMediaMonitoringsTableEntry 1 }

   cmmCmisAdvertisementModuleMediaMonitoringSupported OBJECT-TYPE
     SYNTAX          TruthValue
     MAX-ACCESS      read-only
     STATUS          current
     DESCRIPTION
     "Cmis Module advertisement media monitorings supported information,
     true(1) represents supported,
     false(2) represents not supported"
     ::= { cmmCmisModuleAdvertisementMediaMonitoringsTableEntry 2 }

   cmmCmisAdvertisementModuleMediaLanesAssigned  OBJECT-TYPE
     SYNTAX          CmisLanesAssigned
     MAX-ACCESS      read-only
     STATUS          current
     DESCRIPTION
     "Bitmap of Cmis Module Media lane assigned value"
     ::= { cmmCmisModuleAdvertisementMediaMonitoringsTableEntry 3 }

     -- for cmmCmisModuleAdvertisementModuleFlagsTable ,
     -- cmmCmisModuleObjects: 26 is reserved

    cmmCmisModuleAdvertisementModuleMonitoringsTable OBJECT-TYPE
      SYNTAX            SEQUENCE OF CmmCmisModuleAdvertisementModuleMonitoringsTableEntry
      MAX-ACCESS        not-accessible
      STATUS            current
      DESCRIPTION
      "A list of entries containing Cmis advertisement module monitoring details."
      ::= { cmmCmisModuleObjects 27 }

    cmmCmisModuleAdvertisementModuleMonitoringsTableEntry OBJECT-TYPE
      SYNTAX            CmmCmisModuleAdvertisementModuleMonitoringsTableEntry
      MAX-ACCESS        not-accessible
      STATUS            current
      DESCRIPTION
      "A list of table entries containing Cmis advertisement module monitoring
      information."
      INDEX    { cmmStackUnitIndex, cmmCmisModuleType,
          cmmCmisModulePortNumber, cmmCmisAdvertisementModuleMonitoringAttrType }
      ::= { cmmCmisModuleAdvertisementModuleMonitoringsTable 1 }

    CmmCmisModuleAdvertisementModuleMonitoringsTableEntry   ::=
      SEQUENCE  {
                  cmmCmisAdvertisementModuleMonitoringAttrType   CmisModuleAttrMonitorings,
                  cmmCmisAdvertisementModuleAttrSupported        TruthValue
                }

    cmmCmisAdvertisementModuleMonitoringAttrType  OBJECT-TYPE
      SYNTAX       CmisModuleAttrMonitorings
      MAX-ACCESS   read-only
      STATUS       current
      DESCRIPTION
      "Cmis Module Advertising monitor module attr type value"
      ::= { cmmCmisModuleAdvertisementModuleMonitoringsTableEntry 1 }

    cmmCmisAdvertisementModuleAttrSupported  OBJECT-TYPE
      SYNTAX      TruthValue
      MAX-ACCESS      read-only
      STATUS          current
      DESCRIPTION
      "Cmis Module advertising monitor attr supported,
      true(1) represents supported,
      false(2) represents not supported"
      ::= { cmmCmisModuleAdvertisementModuleMonitoringsTableEntry 2 }

    cmmCmisModuleAdvertisementPagesTable OBJECT-TYPE
      SYNTAX            SEQUENCE OF CmmCmisModuleAdvertisementPagesTableEntry
      MAX-ACCESS        not-accessible
      STATUS            current
      DESCRIPTION
      "A list of entries containing Cmis module advertisement pages details."
      ::= { cmmCmisModuleObjects 28 }

    cmmCmisModuleAdvertisementPagesTableEntry OBJECT-TYPE
      SYNTAX            CmmCmisModuleAdvertisementPagesTableEntry
      MAX-ACCESS        not-accessible
      STATUS            current
      DESCRIPTION
      "A list of table entries containing Cmis module advertisement pages
      information."
      INDEX    { cmmStackUnitIndex, cmmCmisModuleType,
      cmmCmisModulePortNumber }
      ::= { cmmCmisModuleAdvertisementPagesTable 1 }

    CmmCmisModuleAdvertisementPagesTableEntry   ::=
      SEQUENCE  {
                  cmmCmisModuleNetworkPathPagesSupported    TruthValue,
                  cmmCmisModuleVdmPagesSupported            TruthValue,
                  cmmCmisModuleVdmGroups                    INTEGER,
                  cmmCmisModuleDiagnosticsPagesSupported    TruthValue,
                  cmmCmisModuleUserPagesSupported           TruthValue,
                  cmmCmisModuleBanksPerPage                 INTEGER
                }

    cmmCmisModuleNetworkPathPagesSupported  OBJECT-TYPE
      SYNTAX          TruthValue
      MAX-ACCESS      read-only
      STATUS          current
      DESCRIPTION
      "Cmis Module advertisement network path pages information,
      true(1) represents supported,
      false(2) represents not supported"
      ::= { cmmCmisModuleAdvertisementPagesTableEntry 1 }

    cmmCmisModuleVdmPagesSupported  OBJECT-TYPE
      SYNTAX          TruthValue
      MAX-ACCESS      read-only
      STATUS          current
      DESCRIPTION
      "Cmis Module advertisement vdm pages information,
      true(1) represents supported,
      false(2) represents not supported"
      ::= { cmmCmisModuleAdvertisementPagesTableEntry 2 }

    cmmCmisModuleVdmGroups  OBJECT-TYPE
      SYNTAX  INTEGER   {
                          group-1(1),
                          group-1-and-2(2),
                          group-1-to-3(3),
                          group-1-to-4(4)
                        }
      MAX-ACCESS      read-only
      STATUS          current
      DESCRIPTION
      "Cmis Module advertisemnt vdm groups supported informtaion.
      '-100002' indicates not-applicable."
      ::= { cmmCmisModuleAdvertisementPagesTableEntry 3 }

    cmmCmisModuleDiagnosticsPagesSupported  OBJECT-TYPE
      SYNTAX          TruthValue
      MAX-ACCESS      read-only
      STATUS          current
      DESCRIPTION
      "Cmis Module advertisement diagnostics pages information,
      true(1) represents supported,
      false(2) represents not supported"
      ::= { cmmCmisModuleAdvertisementPagesTableEntry 4 }

    cmmCmisModuleUserPagesSupported  OBJECT-TYPE
      SYNTAX          TruthValue
      MAX-ACCESS      read-only
      STATUS          current
      DESCRIPTION
      "Cmis Module advertisement user pages information,
      true(1) represents supported,
      false(2) represents not supported"
      ::= { cmmCmisModuleAdvertisementPagesTableEntry 5 }

    cmmCmisModuleBanksPerPage  OBJECT-TYPE
      SYNTAX  INTEGER   {
                           bank-0(1),
                           bank-0-and-1(2),
                           bank-0-to-3(3),
                           reserved(4)
                        }
      MAX-ACCESS      read-only
      STATUS          current
      DESCRIPTION
      "Cmis Module advertisemnt banks per page information."
      ::= { cmmCmisModuleAdvertisementPagesTableEntry 6 }

    cmmCmisModuleAdvertisementSITable OBJECT-TYPE
      SYNTAX            SEQUENCE OF CmmCmisModuleAdvertisementSITableEntry
      MAX-ACCESS        not-accessible
      STATUS            current
      DESCRIPTION
      "A list of entries containing Cmis module advertisement signal integrity
      details."
      ::= { cmmCmisModuleObjects 29 }

    cmmCmisModuleAdvertisementSITableEntry OBJECT-TYPE
      SYNTAX            CmmCmisModuleAdvertisementSITableEntry
      MAX-ACCESS        not-accessible
      STATUS            current
      DESCRIPTION
      "A list of table entries containing Cmis module advertisement signal integrity
      details."
      INDEX    { cmmStackUnitIndex, cmmCmisModuleType,
      cmmCmisModulePortNumber }
      ::= { cmmCmisModuleAdvertisementSITable 1 }

    CmmCmisModuleAdvertisementSITableEntry   ::=
      SEQUENCE  {
                  cmmCmisModuleTxInputManualEqSupported         TruthValue,
                  cmmCmisModuleTxInputEqMax                     INTEGER,
                  cmmCmisModuleRxOutputEqPreCursorSupported     TruthValue,
                  cmmCmisModuleRxOutputEqPreCursorMax           INTEGER,
                  cmmCmisModuleRxOutputEqPostCursorSupported    TruthValue,
                  cmmCmisModuleRxOutputEqPostCursorMax          INTEGER,
                  cmmCmisModuleRxOutpuAmpSupported              TruthValue,
                  cmmCmisModuleRxOutpuAmpCodes                  BITS,
                  cmmCmisModuleTxCdrSupported                   TruthValue,
                  cmmCmisModuleTxCdrBypassSupported             TruthValue,
                  cmmCmisModuleRxCdrSupported                   TruthValue,
                  cmmCmisModuleRxCdrBypassSupported             TruthValue
                }

    cmmCmisModuleTxInputManualEqSupported  OBJECT-TYPE
      SYNTAX          TruthValue
      MAX-ACCESS      read-only
      STATUS          current
      DESCRIPTION
      "Cmis Module advertisement tx input manual equalization support information.
      true(1) represents supported,
      false(2) represents not supported"
      ::= { cmmCmisModuleAdvertisementSITableEntry 1 }

    cmmCmisModuleTxInputEqMax  OBJECT-TYPE
      SYNTAX  INTEGER   {
                          no-equalization(1),
                          code-1(2),
                          code-2(3),
                          code-3(4),
                          code-4(5),
                          code-5(6),
                          code-6(7),
                          code-7(8),
                          code-8(9),
                          code-9(10),
                          code-10(11),
                          code-11(12),
                          code-12(13),
                          custom1(14),
                          custom2(15),
                          custom3(16)
                        }
      MAX-ACCESS      read-only
      STATUS          current
      DESCRIPTION
      "Cmis Module advertisemnt signal integrity tx input maximum equalization details.
      '-100002' indicates not-applicable."
      ::= { cmmCmisModuleAdvertisementSITableEntry 2 }

    cmmCmisModuleRxOutputEqPreCursorSupported  OBJECT-TYPE
      SYNTAX          TruthValue
      MAX-ACCESS      read-only
      STATUS          current
      DESCRIPTION
      "Cmis Module advertisement rx output equalization pre-cursor support information.
      true(1) represents supported,
      false(2) represents not supported"
      ::= { cmmCmisModuleAdvertisementSITableEntry 3 }

    cmmCmisModuleRxOutputEqPreCursorMax  OBJECT-TYPE
      SYNTAX  INTEGER   {
                            no-equalization(1),
                            code-1(2),
                            code-2(3),
                            code-3(4),
                            code-4(5),
                            code-5(6),
                            code-6(7),
                            code-7(8),
                            reserved1(9),
                            reserved2(10),
                            reserved3(11),
                            custom1(12),
                            custom2(13),
                            custom3(14),
                            custom4(15),
                            custom5(16)
                        }
      MAX-ACCESS      read-only
      STATUS          current
      DESCRIPTION
      "Cmis Module advertisemnt signal integrity rx output pre-cursor maximum
      equalization details.
      '-100002' indicates not-applicable."
      ::= { cmmCmisModuleAdvertisementSITableEntry 4 }

    cmmCmisModuleRxOutputEqPostCursorSupported  OBJECT-TYPE
      SYNTAX          TruthValue
      MAX-ACCESS      read-only
      STATUS          current
      DESCRIPTION
      "Cmis Module advertisement rx output equalization post-cursor support
      information.
      true(1) represents supported,
      false(2) represents not supported"
      ::= { cmmCmisModuleAdvertisementSITableEntry 5 }

    cmmCmisModuleRxOutputEqPostCursorMax  OBJECT-TYPE
      SYNTAX  INTEGER   {
                           no-equalization(1),
                           code-1(2),
                           code-2(3),
                           code-3(4),
                           code-4(5),
                           code-5(6),
                           code-6(7),
                           code-7(8),
                           reserved1(9),
                           reserved2(10),
                           reserved3(11),
                           custom1(12),
                           custom2(13),
                           custom3(14),
                           custom4(15),
                           custom5(16)
                       }
    MAX-ACCESS      read-only
    STATUS          current
    DESCRIPTION
    "Cmis Module advertisemnt signal integrity rx output post-cursor maximum
    equalization details.
    '-100002' indicates not-applicable."
    ::= { cmmCmisModuleAdvertisementSITableEntry 6 }

    cmmCmisModuleRxOutpuAmpSupported  OBJECT-TYPE
      SYNTAX          TruthValue
      MAX-ACCESS      read-only
      STATUS          current
      DESCRIPTION
      "Cmis Module advertisement rx output amplitude support information.
      true(1) represents supported,
      false(2) represents not supported"
      ::= { cmmCmisModuleAdvertisementSITableEntry 7 }

    cmmCmisModuleRxOutpuAmpCodes  OBJECT-TYPE
      SYNTAX  BITS   {
                       code-0(0),
                       code-1(1),
                       code-2(2),
                       code-3(3)
                     }
      MAX-ACCESS      read-only
      STATUS          current
      DESCRIPTION
      "Cmis Module advertisemnt signal integrity rx output
      amplitude codes details."
      ::= { cmmCmisModuleAdvertisementSITableEntry 8 }

    cmmCmisModuleTxCdrSupported  OBJECT-TYPE
      SYNTAX          TruthValue
      MAX-ACCESS      read-only
      STATUS          current
      DESCRIPTION
      "Cmis Module advertisement tx cdr support information.
      true(1) represents supported,
      false(2) represents not supported"
      ::= { cmmCmisModuleAdvertisementSITableEntry 9 }

    cmmCmisModuleTxCdrBypassSupported  OBJECT-TYPE
      SYNTAX          TruthValue
      MAX-ACCESS      read-only
      STATUS          current
      DESCRIPTION
      "Cmis Module advertisement tx cdr bypass support information.
      true(1) represents supported,
      false(2) represents not supported"
      ::= { cmmCmisModuleAdvertisementSITableEntry 10 }

    cmmCmisModuleRxCdrSupported  OBJECT-TYPE
      SYNTAX          TruthValue
      MAX-ACCESS      read-only
      STATUS          current
      DESCRIPTION
      "Cmis Module advertisement rx cdr support information.
      true(1) represents supported,
      false(2) represents not supported"
      ::= { cmmCmisModuleAdvertisementSITableEntry 11 }

    cmmCmisModuleRxCdrBypassSupported  OBJECT-TYPE
      SYNTAX          TruthValue
      MAX-ACCESS      read-only
      STATUS          current
      DESCRIPTION
      "Cmis Module advertisement rx cdr bypass support information.
      true(1) represents supported,
      false(2) represents not supported"
      ::= { cmmCmisModuleAdvertisementSITableEntry 12 }


    cmmCmisModuleAdvertisementHostCustomApplicationTable OBJECT-TYPE
      SYNTAX            SEQUENCE OF CmmCmisModuleAdvertisementHostCustomApplicationTableEntry
      MAX-ACCESS        not-accessible
      STATUS            current
      DESCRIPTION
      "A list of entries containing Cmis module host lane advertisement for custom application."
      ::= { cmmCmisModuleObjects 30 }

    cmmCmisModuleAdvertisementHostCustomApplicationTableEntry OBJECT-TYPE
      SYNTAX            CmmCmisModuleAdvertisementHostCustomApplicationTableEntry
      MAX-ACCESS        not-accessible
      STATUS            current
      DESCRIPTION
      "A list of table entries containing Cmis module host lane advertisement
       for custom application."
      INDEX    { cmmStackUnitIndex, cmmCmisModuleType,
          cmmCmisModulePortNumber, cmmCmisModuleCustomAppHostID }
         ::= { cmmCmisModuleAdvertisementHostCustomApplicationTable 1 }

    CmmCmisModuleAdvertisementHostCustomApplicationTableEntry   ::=
      SEQUENCE  {
                  cmmCmisModuleCustomAppHostID                INTEGER,
                  cmmCmisModuleCustomHostApplicationSelector  INTEGER,
                  cmmCmisModuleCustomHostInterfaceType        CmisInterfaceType,
                  cmmCmisModuleCustomHostApplicationBitrate   CmisBitRate,
                  cmmCmisModuleCustomHostLaneCount            INTEGER,
                  cmmCmisModuleCustomHostSignalBitrate        CmisBitRate,
                  cmmCmisModuleCustomHostModulationFormat     CmisModulationFormat,
                  cmmCmisModuleCustomHostBitsPerUnitInterval  INTEGER,
                  cmmCmisModuleCustomHostLaneAssigned         CmisLanesAssigned,
                  cmmCmisModuleCustomHostConfig               DisplayString
                }

    cmmCmisModuleCustomAppHostID  OBJECT-TYPE
      SYNTAX          INTEGER (1..32)
      MAX-ACCESS      not-accessible
      STATUS          current
      DESCRIPTION
      "The unique Cmis module custom advertising application number"
      ::= { cmmCmisModuleAdvertisementHostCustomApplicationTableEntry 1 }

    cmmCmisModuleCustomHostApplicationSelector   OBJECT-TYPE
      SYNTAX          INTEGER (1..15)
      MAX-ACCESS      read-only
      STATUS          current
      DESCRIPTION
      "The unique Cmis module custom application selection number"
      ::= { cmmCmisModuleAdvertisementHostCustomApplicationTableEntry 2 }

    cmmCmisModuleCustomHostInterfaceType  OBJECT-TYPE
      SYNTAX      CmisInterfaceType
      MAX-ACCESS      read-only
      STATUS          current
      DESCRIPTION
      "Cmis Module Host interface type for custom application.
      '-100002' indicates not-applicable."
      ::= { cmmCmisModuleAdvertisementHostCustomApplicationTableEntry 3 }

    cmmCmisModuleCustomHostApplicationBitrate  OBJECT-TYPE
      SYNTAX      CmisBitRate
      MAX-ACCESS  read-only
      STATUS      current
      DESCRIPTION
      "Cmis Module Host application bit rate value for custom application"
      ::= { cmmCmisModuleAdvertisementHostCustomApplicationTableEntry 4 }

    cmmCmisModuleCustomHostLaneCount  OBJECT-TYPE
      SYNTAX      INTEGER
      MAX-ACCESS  read-only
      STATUS      current
      DESCRIPTION
      "Cmis Module Host lane count for custom application"
      ::= { cmmCmisModuleAdvertisementHostCustomApplicationTableEntry 5 }

    cmmCmisModuleCustomHostSignalBitrate  OBJECT-TYPE
      SYNTAX      CmisBitRate
      MAX-ACCESS  read-only
      STATUS      current
      DESCRIPTION
      "Cmis Module Host signal bit rate value for custom application"
      ::= { cmmCmisModuleAdvertisementHostCustomApplicationTableEntry 6 }

    cmmCmisModuleCustomHostModulationFormat  OBJECT-TYPE
      SYNTAX      CmisModulationFormat
      MAX-ACCESS  read-only
      STATUS      current
      DESCRIPTION
      "Cmis Module Host modulation format for custom application.
      '-100002' indicates not-applicable."
      ::= { cmmCmisModuleAdvertisementHostCustomApplicationTableEntry 7 }

    cmmCmisModuleCustomHostBitsPerUnitInterval  OBJECT-TYPE
      SYNTAX      INTEGER
      UNITS       "0.01 unit"
      MAX-ACCESS  read-only
      STATUS      current
      DESCRIPTION
      "Cmis Module Host bits per unit interval value for custom application"
      ::= { cmmCmisModuleAdvertisementHostCustomApplicationTableEntry 8 }

    cmmCmisModuleCustomHostLaneAssigned  OBJECT-TYPE
      SYNTAX          CmisLanesAssigned
      MAX-ACCESS  read-only
      STATUS      current
      DESCRIPTION
      "Bitmap of Cmis Module Host lane assigned value for custom application"
      ::= { cmmCmisModuleAdvertisementHostCustomApplicationTableEntry 9 }

    cmmCmisModuleCustomHostConfig  OBJECT-TYPE
      SYNTAX      DisplayString
      MAX-ACCESS  read-only
      STATUS      current
      DESCRIPTION
      "Cmis Module Host configured breakout mode and lane speed for custom
      application"
      ::= { cmmCmisModuleAdvertisementHostCustomApplicationTableEntry 10 }


    cmmCmisModuleAdvertisementMediaCustomApplicationTable OBJECT-TYPE
      SYNTAX            SEQUENCE OF CmmCmisModuleAdvertisementMediaCustomApplicationTableEntry
      MAX-ACCESS        not-accessible
      STATUS            current
      DESCRIPTION
      "A list of entries containing Cmis module media lane advertisement for custom
      application details."
      ::= { cmmCmisModuleObjects 31 }

    cmmCmisModuleAdvertisementMediaCustomApplicationTableEntry OBJECT-TYPE
      SYNTAX            CmmCmisModuleAdvertisementMediaCustomApplicationTableEntry
      MAX-ACCESS        not-accessible
      STATUS            current
      DESCRIPTION
      "A list of table entries containing Cmis module media lane advertisement
      for custom application."
      INDEX    { cmmStackUnitIndex, cmmCmisModuleType,
          cmmCmisModulePortNumber, cmmCmisModuleCustomAppMediaID }
      ::= { cmmCmisModuleAdvertisementMediaCustomApplicationTable 1 }

    CmmCmisModuleAdvertisementMediaCustomApplicationTableEntry   ::=
      SEQUENCE  {
                  cmmCmisModuleCustomAppMediaID                INTEGER,
                  cmmCmisModuleCustomMediaApplicationSelector  INTEGER,
                  cmmCmisModuleCustomMediaInterfaceType        CmisInterfaceType,
                  cmmCmisModuleCustomMediaApplicationBitrate   CmisBitRate,
                  cmmCmisModuleCustomMediaLaneCount            INTEGER,
                  cmmCmisModuleCustomMediaSignalBitrate        CmisBitRate,
                  cmmCmisModuleCustomMediaModulationFormat     CmisModulationFormat,
                  cmmCmisModuleCustomMediaBitsPerUnitInterval  INTEGER,
                  cmmCmisModuleCustomMediaLaneAssigned         CmisLanesAssigned
                }

    cmmCmisModuleCustomAppMediaID  OBJECT-TYPE
      SYNTAX          INTEGER (1..32)
      MAX-ACCESS      not-accessible
      STATUS          current
      DESCRIPTION
      "The unique Cmis module custom advertising application number"
      ::= { cmmCmisModuleAdvertisementMediaCustomApplicationTableEntry 1 }

    cmmCmisModuleCustomMediaApplicationSelector   OBJECT-TYPE
      SYNTAX          INTEGER (1..15)
      MAX-ACCESS      read-only
      STATUS          current
      DESCRIPTION
      "The unique Cmis module custom application selection number"
      ::= { cmmCmisModuleAdvertisementMediaCustomApplicationTableEntry 2 }

    cmmCmisModuleCustomMediaInterfaceType  OBJECT-TYPE
      SYNTAX      CmisInterfaceType
      MAX-ACCESS      read-only
      STATUS          current
      DESCRIPTION
      "Cmis Module Media interface type for custom application.
      '-100002' indicates not-applicable."
      ::= { cmmCmisModuleAdvertisementMediaCustomApplicationTableEntry 3 }

    cmmCmisModuleCustomMediaApplicationBitrate  OBJECT-TYPE
      SYNTAX      CmisBitRate
      MAX-ACCESS  read-only
      STATUS      current
      DESCRIPTION
      "Cmis Module Media for custom application bit rate value"
      ::= { cmmCmisModuleAdvertisementMediaCustomApplicationTableEntry 4 }

    cmmCmisModuleCustomMediaLaneCount  OBJECT-TYPE
      SYNTAX      INTEGER
      MAX-ACCESS  read-only
      STATUS      current
      DESCRIPTION
      "Cmis Module Media for custom application lane count"
      ::= { cmmCmisModuleAdvertisementMediaCustomApplicationTableEntry 5 }

    cmmCmisModuleCustomMediaSignalBitrate  OBJECT-TYPE
      SYNTAX      CmisBitRate
      MAX-ACCESS  read-only
      STATUS      current
      DESCRIPTION
      "Cmis Module Media for custom application signal bit rate value"
      ::= { cmmCmisModuleAdvertisementMediaCustomApplicationTableEntry 6 }

    cmmCmisModuleCustomMediaModulationFormat  OBJECT-TYPE
      SYNTAX      CmisModulationFormat
      MAX-ACCESS  read-only
      STATUS      current
      DESCRIPTION
      "Cmis Module Media modulation format for custom application.
      '-100002' indicates not-applicable."
      ::= { cmmCmisModuleAdvertisementMediaCustomApplicationTableEntry 7 }

    cmmCmisModuleCustomMediaBitsPerUnitInterval  OBJECT-TYPE
      SYNTAX      INTEGER
      UNITS       "0.01 unit"
      MAX-ACCESS  read-only
      STATUS      current
      DESCRIPTION
      "Cmis Module Media bits per unit interval value for custom application"
      ::= { cmmCmisModuleAdvertisementMediaCustomApplicationTableEntry 8 }

    cmmCmisModuleCustomMediaLaneAssigned  OBJECT-TYPE
      SYNTAX      CmisLanesAssigned
      MAX-ACCESS  read-only
      STATUS      current
      DESCRIPTION
      "Bitmap of Cmis Module Media lane assigned value for custom application"
      ::= { cmmCmisModuleAdvertisementMediaCustomApplicationTableEntry 9 }


    cmmCmisModuleApplicationStateTable OBJECT-TYPE
      SYNTAX            SEQUENCE OF CmmCmisModuleApplicationStateTableEntry
      MAX-ACCESS        not-accessible
      STATUS            current
      DESCRIPTION
      "Table to display Cmis module application state information."
      ::= { cmmCmisModuleObjects 32 }

    cmmCmisModuleApplicationStateTableEntry OBJECT-TYPE
      SYNTAX            CmmCmisModuleApplicationStateTableEntry
      MAX-ACCESS        not-accessible
      STATUS            current
      DESCRIPTION
      "A table to display Cmis module application state information."
      INDEX    { cmmStackUnitIndex, cmmCmisModuleType,
          cmmCmisModulePortNumber }
      ::= { cmmCmisModuleApplicationStateTable 1 }

    CmmCmisModuleApplicationStateTableEntry   ::=
      SEQUENCE  {
                  cmmCmisModuleConfiguredApplicationID   INTEGER,
                  cmmCmisModuleCustomApplicationHostID   INTEGER,
                  cmmCmisModuleCustomApplicationMediaID  INTEGER
      }

    cmmCmisModuleConfiguredApplicationID  OBJECT-TYPE
      SYNTAX          INTEGER (1..32)
      MAX-ACCESS      read-only
      STATUS          current
      DESCRIPTION
      "The unique Cmis module application id configured in h/w"
      ::= { cmmCmisModuleApplicationStateTableEntry 1 }

    cmmCmisModuleCustomApplicationHostID  OBJECT-TYPE
      SYNTAX          INTEGER (1..32)
      MAX-ACCESS      read-only
      STATUS          current
      DESCRIPTION
      "The unique Cmis module custom application host id configured in h/w"
      ::= { cmmCmisModuleApplicationStateTableEntry 2 }

    cmmCmisModuleCustomApplicationMediaID  OBJECT-TYPE
      SYNTAX          INTEGER (1..32)
      MAX-ACCESS      read-only
      STATUS          current
      DESCRIPTION
      "The unique Cmis module custom application media id configured in h/w"
      ::= { cmmCmisModuleApplicationStateTableEntry 3 }


    cmmCmisModuleAdvertisementTxOutputFilterTable OBJECT-TYPE
      SYNTAX            SEQUENCE OF CmmCmisModuleAdvertisementTxOutputFilterTableEntry
      MAX-ACCESS        not-accessible
      STATUS            current
      DESCRIPTION
      "Table to display Cmis module tx output filter advertisement information."
      ::= { cmmCmisModuleObjects 33 }

    cmmCmisModuleAdvertisementTxOutputFilterTableEntry OBJECT-TYPE
      SYNTAX            CmmCmisModuleAdvertisementTxOutputFilterTableEntry
      MAX-ACCESS        not-accessible
      STATUS            current
      DESCRIPTION
      "A table to display Cmis module tx output filter advertisement information."
      INDEX    { cmmStackUnitIndex, cmmCmisModuleType,
                 cmmCmisModulePortNumber }
        ::= { cmmCmisModuleAdvertisementTxOutputFilterTable 1 }

    CmmCmisModuleAdvertisementTxOutputFilterTableEntry  ::=
        SEQUENCE  {
          cmmCmisModuleInsertionofLFonLDDetection   TruthValue,
          cmmCmisModuleTxTransmitShapeControl       TruthValue
        }

    cmmCmisModuleInsertionofLFonLDDetection  OBJECT-TYPE
      SYNTAX          TruthValue
      MAX-ACCESS      read-only
      STATUS          current
      DESCRIPTION
      "The Cmis module provides status of insertion of LF on LD detection"
        ::= { cmmCmisModuleAdvertisementTxOutputFilterTableEntry 1 }

    cmmCmisModuleTxTransmitShapeControl  OBJECT-TYPE
      SYNTAX          TruthValue
      MAX-ACCESS      read-only
      STATUS          current
      DESCRIPTION
      "The Cmis module provides status of tx transmit shape control"
        ::= { cmmCmisModuleAdvertisementTxOutputFilterTableEntry 2 }


    cmmCmisModuleTxOutputFilterStatusTable OBJECT-TYPE
      SYNTAX            SEQUENCE OF CmmCmisModuleTxOutputFilterStatusTableEntry
      MAX-ACCESS        not-accessible
      STATUS            current
      DESCRIPTION
      "Table to display Cmis module tx output filter status information."
        ::= { cmmCmisModuleObjects 34 }

    cmmCmisModuleTxOutputFilterStatusTableEntry OBJECT-TYPE
      SYNTAX            CmmCmisModuleTxOutputFilterStatusTableEntry
      MAX-ACCESS        not-accessible
      STATUS            current
      DESCRIPTION
      "A table to display Cmis module tx output filter status information."
      INDEX    { cmmStackUnitIndex, cmmCmisModuleType,
                 cmmCmisModulePortNumber, cmmCmisModuleLaneNumber }
        ::= { cmmCmisModuleTxOutputFilterStatusTable 1 }

    CmmCmisModuleTxOutputFilterStatusTableEntry  ::=
      SEQUENCE  {
                  cmmCmisModuleTxFilterType       CmisModuleTxFilterTypes,
                  cmmCmisModuleTxFilterRollOfFactor  INTEGER
                }

    cmmCmisModuleTxFilterType  OBJECT-TYPE
      SYNTAX          CmisModuleTxFilterTypes
      MAX-ACCESS      read-only
      STATUS          current
      DESCRIPTION
        "Cmis Module Media lane tx filter configured type"
        ::= { cmmCmisModuleTxOutputFilterStatusTableEntry 1 }

    cmmCmisModuleTxFilterRollOfFactor  OBJECT-TYPE
      SYNTAX          INTEGER
      UNITS           "0.001 unit"
      MAX-ACCESS      read-only
      STATUS          current
      DESCRIPTION
      "The Cmis module provides media lane tx filter hardware configured value"
        ::= { cmmCmisModuleTxOutputFilterStatusTableEntry 2 }


    cmmCmisModuleMappingInfoTable     OBJECT-TYPE
      SYNTAX            SEQUENCE OF CmmCmisModuleMappingInfoTableEntry
      MAX-ACCESS        not-accessible
      STATUS            deprecated
      DESCRIPTION
      "A list of entries containing Cmis module interface mapping information."
        ::= { cmmCmisModuleObjects 35 }

    cmmCmisModuleMappingInfoTableEntry OBJECT-TYPE
      SYNTAX         CmmCmisModuleMappingInfoTableEntry
      MAX-ACCESS        not-accessible
      STATUS            deprecated
      DESCRIPTION
      "A list of table entries containing Cmis module interface mapping information."
      INDEX    { cmmStackUnitIndex, cmmCmisModulePortNumber }
        ::= { cmmCmisModuleMappingInfoTable 1 }

    CmmCmisModuleMappingInfoTableEntry   ::=
      SEQUENCE {
            cmmCmisFPPort               DisplayString,
            cmmCmisFPPortType           CmisModuleFPPortTypes,
            cmmCmisFPPortModuleType     CmisModuleFPPortModuleTypes,
            cmmCmisFPPortInterface      DisplayString
          }

    cmmCmisFPPort  OBJECT-TYPE
      SYNTAX          DisplayString
      MAX-ACCESS      read-only
      STATUS          deprecated
      DESCRIPTION
      "Cmis module transceiver front panel port."
      ::= { cmmCmisModuleMappingInfoTableEntry 1 }

    cmmCmisFPPortType  OBJECT-TYPE
      SYNTAX          CmisModuleFPPortTypes
      MAX-ACCESS      read-only
      STATUS          deprecated
      DESCRIPTION
      "Cmis module transceiver front panel port types."
      ::= { cmmCmisModuleMappingInfoTableEntry 2 }

    cmmCmisFPPortModuleType OBJECT-TYPE
      SYNTAX          CmisModuleFPPortModuleTypes
      MAX-ACCESS      read-only
      STATUS          deprecated
      DESCRIPTION
      "Cmis module transceiver front panel port module types."
      ::= { cmmCmisModuleMappingInfoTableEntry 3 }

    cmmCmisFPPortInterface OBJECT-TYPE
      SYNTAX          DisplayString
      MAX-ACCESS      read-only
      STATUS          deprecated
      DESCRIPTION
      "Cmis module transceiver front panel port interface name."
      ::= { cmmCmisModuleMappingInfoTableEntry 4 }


    --
    -- ## Notifications
    --

    cmmCmisModuleMonitorAlarmSeverity              OBJECT IDENTIFIER ::= { cmmCmisModuleMonitorObjects 1 }
    cmmCmisModuleMonitorNotifications              OBJECT IDENTIFIER ::= { cmmCmisModuleMonitorObjects 2 }
    cmmCmisModuleMediaLaneMonitorNotifications     OBJECT IDENTIFIER ::= { cmmCmisModuleMonitorObjects 3 }
    cmmCmisModuleHostLaneMonitorNotifications      OBJECT IDENTIFIER ::= { cmmCmisModuleMonitorObjects 4 }

   cmmCmisModuleAlarmSeverity  OBJECT-TYPE
      SYNTAX       INTEGER {
                             alertmax(1),
                             alertmin(2),
                             criticalmax(3),
                             criticalmin(4)
                           }

      MAX-ACCESS   accessible-for-notify
      STATUS       current
      DESCRIPTION
      "A generic threshold alarm type information"
      ::= { cmmCmisModuleMonitorAlarmSeverity 1 }

   cmmCmisModuleNotifyAlarm   NOTIFICATION-TYPE
      OBJECTS     {
                    cmmStackUnitIndex,
                    cmmCmisModuleType,
                    cmmCmisModulePortNumber,
                    cmmCmisModuleAlarmSeverity,
                    cmmCmisModuleMonitoringAttrType,
                    cmmCmisModuleAttrValue,
                    cmmCmisModuleAttrThreshAlertMax,
                    cmmCmisModuleAttrThreshAlertMin
                  }
        STATUS       current
        DESCRIPTION
            "Set when cmis module event type exceeds threshold value"
        ::= { cmmCmisModuleMonitorNotifications 1 }

   cmmCmisModuleNotifyAlarmRecovery   NOTIFICATION-TYPE
      OBJECTS     {
                    cmmStackUnitIndex,
                    cmmCmisModuleType,
                    cmmCmisModulePortNumber,
                    cmmCmisModuleMonitoringAttrType,
                    cmmCmisModuleAttrValue,
                    cmmCmisModuleAttrThreshCriticalMax,
                    cmmCmisModuleAttrThreshCriticalMin
                  }
        STATUS       current
        DESCRIPTION
            "Set when cmis module event type recovers from alarm"
        ::= { cmmCmisModuleMonitorNotifications 2 }

    cmmCmisModuleMediaNotifyAlarm   NOTIFICATION-TYPE
      OBJECTS     {
                    cmmStackUnitIndex,
                    cmmCmisModuleType,
                    cmmCmisModulePortNumber,
                    cmmCmisModuleLaneNumber,
                    cmmCmisModuleAlarmSeverity,
                    cmmCmisModuleMediaMonitoringAttrType,
                    cmmCmisModuleMediaAttrValue,
                    cmmCmisModuleMediaAttrThreshAlertMax,
                    cmmCmisModuleMediaAttrThreshAlertMin
                  }
        STATUS       current
        DESCRIPTION
        "Set when cmis module media lane exceeds alarm value"
        ::= { cmmCmisModuleMediaLaneMonitorNotifications 1 }

    cmmCmisModuleMediaNotifyAlarmRecovery   NOTIFICATION-TYPE
      OBJECTS     {
                    cmmStackUnitIndex,
                    cmmCmisModuleType,
                    cmmCmisModulePortNumber,
                    cmmCmisModuleLaneNumber,
                    cmmCmisModuleMediaMonitoringAttrType,
                    cmmCmisModuleMediaAttrValue,
                    cmmCmisModuleMediaAttrThreshCriticalMax,
                    cmmCmisModuleMediaAttrThreshCriticalMin
                  }
        STATUS       current
        DESCRIPTION
        "Set when cmis module media lane recovers alarm value"
        ::= { cmmCmisModuleMediaLaneMonitorNotifications 2 }

    cmmCmisModuleMediaFlagsNotifyAlarm    NOTIFICATION-TYPE
      OBJECTS     {
                    cmmStackUnitIndex,
                    cmmCmisModuleType,
                    cmmCmisModulePortNumber,
                    cmmCmisModuleLaneNumber,
                    cmmCmisModuleMediaLaneAttrFlagType
                  }
        STATUS       current
        DESCRIPTION
        "When cmis module media lane descrete attributes flags are set"
        ::= { cmmCmisModuleMediaLaneMonitorNotifications 3 }

    cmmCmisModuleMediaFlagsNotifyAlarmRecovery    NOTIFICATION-TYPE
      OBJECTS     {
                    cmmStackUnitIndex,
                    cmmCmisModuleType,
                    cmmCmisModulePortNumber,
                    cmmCmisModuleLaneNumber,
                    cmmCmisModuleMediaLaneAttrFlagType
                  }
        STATUS       current
        DESCRIPTION
        "When cmis module media lane descrete attributes flags are recovered"
        ::= { cmmCmisModuleMediaLaneMonitorNotifications 4 }

    cmmCmisModuleHostNotifyAlarm    NOTIFICATION-TYPE
      OBJECTS     {
                    cmmStackUnitIndex,
                    cmmCmisModuleType,
                    cmmCmisModulePortNumber,
                    cmmCmisModuleLaneNumber,
                    cmmCmisModuleAlarmSeverity,
                    cmmCmisModuleHostLaneMonitoringAttrType,
                    cmmCmisModuleHostLaneAttrValue,
                    cmmCmisModuleHostLaneAttrThreshAlertMax,
                    cmmCmisModuleHostLaneAttrThreshAlertMin
                  }
        STATUS       current
        DESCRIPTION
        "Set when cmis module host lane exceeds alarm value"
        ::= { cmmCmisModuleHostLaneMonitorNotifications 1 }

    cmmCmisModuleHostNotifyAlarmRecovery    NOTIFICATION-TYPE
      OBJECTS     {
                    cmmStackUnitIndex,
                    cmmCmisModuleType,
                    cmmCmisModulePortNumber,
                    cmmCmisModuleLaneNumber,
                    cmmCmisModuleHostLaneMonitoringAttrType,
                    cmmCmisModuleHostLaneAttrValue,
                    cmmCmisModuleHostLaneAttrThreshCriticalMax,
                    cmmCmisModuleHostLaneAttrThreshCriticalMin
                  }
        STATUS       current
        DESCRIPTION
        "Set when cmis module host lane recovers alarm value"
        ::= { cmmCmisModuleHostLaneMonitorNotifications 2 }


    cmmCmisModuleHostFlagsNotifyAlarm    NOTIFICATION-TYPE
      OBJECTS     {
                    cmmStackUnitIndex,
                    cmmCmisModuleType,
                    cmmCmisModulePortNumber,
                    cmmCmisModuleLaneNumber,
                    cmmCmisModuleHostLaneAttrFlagType
                  }
        STATUS       current
        DESCRIPTION
        "When cmis module host lane descrete attributes flags are set"
        ::= { cmmCmisModuleHostLaneMonitorNotifications 3 }

    cmmCmisModuleHostFlagsNotifyAlarmRecovery    NOTIFICATION-TYPE
      OBJECTS     {
                    cmmStackUnitIndex,
                    cmmCmisModuleType,
                    cmmCmisModulePortNumber,
                    cmmCmisModuleLaneNumber,
                    cmmCmisModuleHostLaneAttrFlagType
                  }
        STATUS       current
        DESCRIPTION
        "When cmis module host lane descrete attributes flags are recovered"
        ::= { cmmCmisModuleHostLaneMonitorNotifications 4 }

END
