IPI-PREFIX-LIST-MIB DEFINITIONS ::= BEGIN

IMPORTS
      OBJECT-TYPE, MODULE-IDENTITY,
      Gauge32, Counter32, Integer32, Unsigned32,
      IpAddress, Counter64,
      TimeTicks, NOTIFICATION-TYPE
          FROM SNMPv2-SMI
      DateAndTime, DisplayString,
      PhysAddress, RowStatus, TEXTUAL-CONVENTION
          FROM SNMPv2-TC
      MODULE-COMPLIANCE, OBJECT-GROUP, NOTIFICATION-GROUP
          FROM SNMPv2-CONF
      snmpTraps
          FROM SNMPv2-MIB
      enterprises, OBJECT-IDENTITY
          FROM SNMPv2-SMI
      Ipv6Address
          FROM IPV6-TC
      ipi  FROM IPI-MODULE-MIB;

ipi-prefix-list MODULE-IDENTITY
   LAST-UPDATED "202012150000Z"
   ORGANIZATION "IP Infusion Inc."
   CONTACT-INFO 
       "postal: 3965 Freedom Circle, Suite 200, Santa Clara, CA 95054

        email: support@ipinfusion.com

        telephone: +1 408-400-1900
        website: http://www.ipinfusion.com/"
   DESCRIPTION 
      "This MIB module is for managing None"

   REVISION      "202012150000Z"
   DESCRIPTION 
      "Change to have data-types in lower case instead of camel case"

   REVISION      "202006240000Z"
   DESCRIPTION 
      "Initial Version"
   ::= { ipi  101 } 


ipiPrefixListPrefixTable OBJECT-TYPE 
	SYNTAX SEQUENCE OF IpiPrefixListPrefixEntry
	MAX-ACCESS not-accessible
	STATUS current
	DESCRIPTION 
		"This table provides information for IPV4 prefix-list configurations"
	::= { ipi-prefix-list 1 }

ipiPrefixListPrefixEntry OBJECT-TYPE
	SYNTAX IpiPrefixListPrefixEntry
	MAX-ACCESS not-accessible
	STATUS current
	DESCRIPTION 
		"An entry containing information for IPV4 prefix-list configurations"
	INDEX { ipiPrefixListPrefixListType,ipiPrefixListPrefixListName }
	::= { ipiPrefixListPrefixTable 1 }

IpiPrefixListPrefixEntry::= SEQUENCE {
	ipiPrefixListPrefixListName OCTET STRING,
	ipiPrefixListPrefixListType INTEGER,
	ipiPrefixListDescription OCTET STRING	}

ipiPrefixListPrefixListName OBJECT-TYPE
	SYNTAX OCTET STRING 
	MAX-ACCESS read-write
	STATUS current 
	DESCRIPTION 
		"Name of the prefix list"
	::= { ipiPrefixListPrefixEntry 1 }

ipiPrefixListPrefixListType OBJECT-TYPE
	SYNTAX INTEGER {ip(1), ipv6(2)} 
	MAX-ACCESS read-write
	STATUS current 
	DESCRIPTION 
		"prefix-list type"
	::= { ipiPrefixListPrefixEntry 2 }

ipiPrefixListDescription OBJECT-TYPE
	SYNTAX OCTET STRING 
	MAX-ACCESS read-write
	STATUS current 
	DESCRIPTION 
		"Up to 80 characters describing this prefix-list"
	::= { ipiPrefixListPrefixEntry 3 }


ipiPrefixListPrefixEntryTable OBJECT-TYPE 
	SYNTAX SEQUENCE OF IpiPrefixListPrefixEntryEntry
	MAX-ACCESS not-accessible
	STATUS current
	DESCRIPTION 
		"This table provides information for List of sequences"
	::= { ipi-prefix-list 2 }

ipiPrefixListPrefixEntryEntry OBJECT-TYPE
	SYNTAX IpiPrefixListPrefixEntryEntry
	MAX-ACCESS not-accessible
	STATUS current
	DESCRIPTION 
		"An entry containing information for List of sequences"
	INDEX { ipiPrefixListPrefixListType,ipiPrefixListPrefixListName,ipiPrefixListSequenceId }
	::= { ipiPrefixListPrefixEntryTable 1 }

IpiPrefixListPrefixEntryEntry::= SEQUENCE {
	ipiPrefixListSequenceId Unsigned32	}

ipiPrefixListSequenceId OBJECT-TYPE
	SYNTAX Unsigned32(1..4294967295) 
	MAX-ACCESS read-write
	STATUS current 
	DESCRIPTION 
		"Sequence number of the prefix list"
	::= { ipiPrefixListPrefixEntryEntry 1 }


ipiPrefixListEntryTable OBJECT-TYPE 
	SYNTAX SEQUENCE OF IpiPrefixListEntryEntry
	MAX-ACCESS not-accessible
	STATUS current
	DESCRIPTION 
		"This table provides information for prefix-list network information"
	::= { ipi-prefix-list 3 }

ipiPrefixListEntryEntry OBJECT-TYPE
	SYNTAX IpiPrefixListEntryEntry
	MAX-ACCESS not-accessible
	STATUS current
	DESCRIPTION 
		"An entry containing information for prefix-list network information"
	INDEX { ipiPrefixListPrefixListType,ipiPrefixListPrefixListName,ipiPrefixListSequenceId,ipiPrefixListPrefixAddr,ipiPrefixListAction }
	::= { ipiPrefixListEntryTable 1 }

IpiPrefixListEntryEntry::= SEQUENCE {
	ipiPrefixListAction INTEGER,
	ipiPrefixListMinimumPrefixLengthMatch Unsigned32,
	ipiPrefixListMaximumPrefixLengthMatch Unsigned32,
	ipiPrefixListPrefixAddr OCTET STRING,
	ipiPrefixListExactPrefixLengthMatch Unsigned32	}

ipiPrefixListAction OBJECT-TYPE
	SYNTAX INTEGER {deny(1), permit(2)} 
	MAX-ACCESS read-write
	STATUS current 
	DESCRIPTION 
		"Router starts to match prefixes from the top of the prefix list, and stops whenever a match or deny occurs. To promote efficiency, use the seq parameter and place common matches or denials towards the top of the list. The sequence values are generated in the sequence of 5. The parameters ge and le specify the range of the prefix length to be matched"
	::= { ipiPrefixListEntryEntry 1 }

ipiPrefixListMinimumPrefixLengthMatch OBJECT-TYPE
	SYNTAX Unsigned32(0..32) 
	MAX-ACCESS read-write
	STATUS current 
	DESCRIPTION 
		"Minimum prefix length match"
	::= { ipiPrefixListEntryEntry 2 }

ipiPrefixListMaximumPrefixLengthMatch OBJECT-TYPE
	SYNTAX Unsigned32(0..32) 
	MAX-ACCESS read-write
	STATUS current 
	DESCRIPTION 
		"Maximum prefix length match"
	::= { ipiPrefixListEntryEntry 3 }

ipiPrefixListPrefixAddr OBJECT-TYPE
	SYNTAX OCTET STRING 
	MAX-ACCESS read-write
	STATUS current 
	DESCRIPTION 
		"Either IP address mask and length of the prefix list mask or Take all packets of any length. This parameter is the same as using 0.0.0.0/0 le 32 for A.B.C.D/M."
	::= { ipiPrefixListEntryEntry 4 }

ipiPrefixListExactPrefixLengthMatch OBJECT-TYPE
	SYNTAX Unsigned32(0..32) 
	MAX-ACCESS read-write
	STATUS current 
	DESCRIPTION 
		"Exact prefix length match"
	::= { ipiPrefixListEntryEntry 5 }


END
