CERAGON-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

ceragon MODULE-IDENTITY
    LAST-UPDATED "202507100000Z"
    ORGANIZATION "Ceragon Networks Ltd."
    CONTACT-INFO
        "http://www.ceragon.com"
    DESCRIPTION
        "The Ceragon Networks Ltd. enterprise Module Identity."

    REVISION "202507100000Z"
        DESCRIPTION "Initial revision."

    ::= { cmmStackUnitModelName 2281 }

ceragonOIDS OBJECT IDENTIFIER ::= { ceragon 1 }
ceragonProducts OBJECT IDENTIFIER ::= { ceragon 2 }
ceragonIP50FX OBJECT IDENTIFIER ::= { ceragonProducts 1 }

END
