HFCL-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

hfcl MODULE-IDENTITY
    LAST-UPDATED "202507100000Z"
    ORGANIZATION "Himachal Futuristic Communications Limited"
    CONTACT-INFO
        "http://www.hfcl.com"
    DESCRIPTION
        "The Himachal Futuristic Communications Limited enterprise Module Identity."

    REVISION "202507100000Z"
        DESCRIPTION "Initial revision."

    ::= { cmmStackUnitModelName 3577 }

hfclOIDS OBJECT IDENTIFIER ::= { hfcl 1 }
hfclProducts OBJECT IDENTIFIER ::= { hfcl 2 }
hfclAR OBJECT IDENTIFIER ::= { hfclProducts 1 }
hfclARPORTWELL OBJECT IDENTIFIER ::= { hfclProducts 2 }
hfclDUAR OBJECT IDENTIFIER ::= { hfclProducts 3 }
hfclDUARPORTWELL OBJECT IDENTIFIER ::= { hfclProducts 4 }
hfclCUAR OBJECT IDENTIFIER ::= { hfclProducts 5 }
hfclCUARPORTWELL OBJECT IDENTIFIER ::= { hfclProducts 6 }

END
