ZYXEL-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

zyxel MODULE-IDENTITY
    LAST-UPDATED "202507100000Z"
    ORGANIZATION "ZyXEL Communications Corp."
    CONTACT-INFO
        "http://www.zyxel.com"
    DESCRIPTION
        "The ZyXEL Communications Corp. enterprise Module Identity."

    REVISION "202507100000Z"
        DESCRIPTION "Initial revision."

    ::= { vendorModelInfo 890 }

zyxelOIDS OBJECT IDENTIFIER ::= { zyxel 1 }
zyxelProducts OBJECT IDENTIFIER ::= { zyxel 2 }
zyxelSDA3016SS OBJECT IDENTIFIER ::= { zyxelProducts 1 }

END
