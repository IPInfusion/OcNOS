OCNOS-LICENSE-MIB DEFINITIONS ::= BEGIN

IMPORTS
      OBJECT-TYPE, MODULE-IDENTITY,
      Gauge32, Counter32, Integer32, Unsigned32,
      IpAddress, Counter64,
      TimeTicks, NOTIFICATION-TYPE
          FROM SNMPv2-SMI
      DateAndTime, DisplayString,
      PhysAddress, RowStatus, TEXTUAL-CONVENTION
          FROM SNMPv2-TC
      MODULE-COMPLIANCE, OBJECT-GROUP, NOTIFICATION-GROUP
          FROM SNMPv2-CONF
      snmpTraps
          FROM SNMPv2-MIB
      enterprises, OBJECT-IDENTITY
          FROM SNMPv2-SMI
      Ipv6Address
          FROM IPV6-TC
      ipi  FROM OCNOS-IPI-MODULE-MIB;

license MODULE-IDENTITY
   LAST-UPDATED "201806210000Z"
   ORGANIZATION "IP Infusion Inc."
   CONTACT-INFO 
       "postal: 3965 Freedom Circle, Suite 200, Santa Clara, CA 95054

        email: support@ipinfusion.com

        telephone: +1 408-400-1900
        website: http://www.ipinfusion.com/"
   DESCRIPTION 
      "This MIB module is for managing license configurations"

   REVISION      "201806210000Z"
   DESCRIPTION 
      "Initial Version"
   ::= { ipi  78 } 

licenseSlotCount OBJECT-TYPE
	SYNTAX Unsigned32 
	MAX-ACCESS read-only
	STATUS current 
	DESCRIPTION 
		"license slot count"
	::= { license 1 }

licenseLicenseStatus OBJECT-TYPE
	SYNTAX OCTET STRING 
	MAX-ACCESS read-only
	STATUS current 
	DESCRIPTION 
		"license log message for all clients"
	::= { license 2 }

licenseLicenseMsg OBJECT-TYPE
	SYNTAX OCTET STRING 
	MAX-ACCESS read-only
	STATUS current 
	DESCRIPTION 
		"license log message for all clients"
	::= { license 3 }

licenseServiceEndDate OBJECT-TYPE
	SYNTAX OCTET STRING 
	MAX-ACCESS read-only
	STATUS current 
	DESCRIPTION 
		"service end date"
	::= { license 4 }

licenseRemainingDays OBJECT-TYPE
	SYNTAX Integer32 
	MAX-ACCESS read-only
	STATUS current 
	DESCRIPTION 
		"remaining days to license expiry or remaining lease"
	::= { license 5 }

licenseDeviceSoftware OBJECT-TYPE
	SYNTAX OCTET STRING 
	MAX-ACCESS read-only
	STATUS current 
	DESCRIPTION 
		"Device software"
	::= { license 6 }

licenseNodeIdentifier OBJECT-TYPE
	SYNTAX OCTET STRING 
	MAX-ACCESS read-only
	STATUS current 
	DESCRIPTION 
		"Node id"
	::= { license 7 }

licenseValidity OBJECT-TYPE
	SYNTAX OCTET STRING 
	MAX-ACCESS read-only
	STATUS current 
	DESCRIPTION 
		"Validity of license"
	::= { license 8 }

licenseType OBJECT-TYPE
	SYNTAX OCTET STRING 
	MAX-ACCESS read-only
	STATUS current 
	DESCRIPTION 
		"License Type"
	::= { license 9 }


--
-- Notifications
--

licenseNotificationsPrefix OBJECT IDENTIFIER ::=
        { license 0 }

licensemessage NOTIFICATION-TYPE
   OBJECTS { licenseLicenseMsg }
   STATUS  current
   DESCRIPTION
           "license messages to all northbound"
   ::= { licenseNotificationsPrefix 1 }

licensestatus NOTIFICATION-TYPE
   OBJECTS { licenseLicenseStatus }
   STATUS  current
   DESCRIPTION
           "license success or failure"
   ::= { licenseNotificationsPrefix 2 }

licenseremainingdays NOTIFICATION-TYPE
   OBJECTS { licenseRemainingDays }
   STATUS  current
   DESCRIPTION
           "license remaining days"
   ::= { licenseNotificationsPrefix 3 }
END
