WISTRON-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

wistron MODULE-IDENTITY
    LAST-UPDATED "202507100000Z"
    ORGANIZATION "Wistron NeWeb Corporation"
    CONTACT-INFO
        "http://www.wistron.com"
    DESCRIPTION
        "The Wistron NeWeb Corporation enterprise Module Identity."

    REVISION "202507100000Z"
        DESCRIPTION "Initial revision."

    ::= { cmmStackUnitModelName 15756 }

wistronOIDS OBJECT IDENTIFIER ::= { wistron 1 }
wistronProducts OBJECT IDENTIFIER ::= { wistron 2 }
wistronPLOOMTECH OBJECT IDENTIFIER ::= { wistronProducts 1 }

END
