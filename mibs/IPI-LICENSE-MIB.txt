IPI-LICENSE-MIB DEFINITIONS ::= BEGIN

IMPORTS
      OBJECT-TYPE, MODULE-IDENTITY,
      Gauge32, Counter32, Integer32, Unsigned32,
      IpAddress, Counter64,
      TimeTicks, NOTIFICATION-TYPE
          FROM SNMPv2-SMI
      DateAndTime, DisplayString,
      PhysAddress, RowStatus, TEXTUAL-CONVENTION
          FROM SNMPv2-TC
      MODULE-COMPLIANCE, OBJECT-GROUP, NOTIFICATION-GROUP
          FROM SNMPv2-CONF
      snmpTraps
          FROM SNMPv2-MIB
      enterprises, OBJECT-IDENTITY
          FROM SNMPv2-SMI
      Ipv6Address
          FROM IPV6-TC
      ipi  FROM IPI-MODULE-MIB;

ipi-license MODULE-IDENTITY
   LAST-UPDATED "202409180000Z"

ORGANIZATION "IP Infusion"
CONTACT-INFO "support@ipinfusion.com"
   DESCRIPTION 
      "This MIB module is for managing license module allows use to manage license configurations in the device"

   REVISION      "202409180000Z"
   DESCRIPTION 
      "Support to add confirmation for license release command"

   REVISION      "202405310000Z"
   DESCRIPTION 
      "Support user VRF for license pool"

   REVISION      "202307180000Z"
   DESCRIPTION 
      "Removed ZR/ZR+ license support DM"

   REVISION      "202303020000Z"
   DESCRIPTION 
      "ZR/ZR+ license support"

   REVISION      "202209300000Z"
   DESCRIPTION 
      "Import cml-data-types used by notifications"

   REVISION      "202206010000Z"
   DESCRIPTION 
      "Updated the yang file with feature"

   REVISION      "202108230000Z"
   DESCRIPTION 
      "Using Epoch value for service-end-date attribute"

   REVISION      "202107300000Z"
   DESCRIPTION 
      "Module attributes Restructured"

   REVISION      "201806210000Z"
   DESCRIPTION 
      "Initial Version"
   ::= { ipi  78 } 

ipiLicenseSlotCount OBJECT-TYPE
	SYNTAX Unsigned32 
	MAX-ACCESS read-only
	STATUS current 
	DESCRIPTION 
		"license slot count"
	::= { ipi-license 1 }

ipiLicenseStatus OBJECT-TYPE
	SYNTAX INTEGER {success(0), failure(1)} 
	MAX-ACCESS read-only
	STATUS current 
	DESCRIPTION 
		"license status"
	::= { ipi-license 2 }

ipiLicenseMsg OBJECT-TYPE
	SYNTAX OCTET STRING 
	MAX-ACCESS read-only
	STATUS current 
	DESCRIPTION 
		"license log message for all clients"
	::= { ipi-license 3 }

ipiLicenseServiceEndDate OBJECT-TYPE
	SYNTAX TimeTicks 
	MAX-ACCESS read-only
	STATUS current 
	DESCRIPTION 
		"The Unix Epoch value. It represents the license end date. Zero if it does not expire"
	::= { ipi-license 4 }

ipiLicenseRemainingDays OBJECT-TYPE
	SYNTAX Integer32 
	MAX-ACCESS read-only
	STATUS current 
	DESCRIPTION 
		"remaining days to license expiry or remaining lease"
	::= { ipi-license 5 }

ipiLicenseDeviceSoftware OBJECT-TYPE
	SYNTAX OCTET STRING 
	MAX-ACCESS read-only
	STATUS current 
	DESCRIPTION 
		"Device software"
	::= { ipi-license 6 }

ipiLicenseNodeId OBJECT-TYPE
	SYNTAX OCTET STRING 
	MAX-ACCESS read-only
	STATUS current 
	DESCRIPTION 
		"Node id"
	::= { ipi-license 7 }

ipiLicenseValidity OBJECT-TYPE
	SYNTAX INTEGER {notapplicable(0), permanent(1), expired(2)} 
	MAX-ACCESS read-only
	STATUS current 
	DESCRIPTION 
		"Validity of license"
	::= { ipi-license 8 }

ipiLicenseType OBJECT-TYPE
	SYNTAX INTEGER {evaluationlimitededition(0), devicelockedfulledition(1), trialedition(2), leasefulledition(3)} 
	MAX-ACCESS read-only
	STATUS current 
	DESCRIPTION 
		"License Type"
	::= { ipi-license 9 }


--
-- Notifications
--

ipiCMLSEPlicenseNotificationsPrefix OBJECT IDENTIFIER ::=
        { ipi-license 0 }

licenselogmessage NOTIFICATION-TYPE
   OBJECTS { ipiLicenseMsg }
   STATUS  current
   DESCRIPTION
           "license messages to all northbound"
   ::= { ipiCMLSEPlicenseNotificationsPrefix 1 }

licensestatus NOTIFICATION-TYPE
   OBJECTS { ipiLicenseStatus }
   STATUS  current
   DESCRIPTION
           "license success or failure"
   ::= { ipiCMLSEPlicenseNotificationsPrefix 2 }

licenseremainingdays NOTIFICATION-TYPE
   OBJECTS { ipiLicenseRemainingDays }
   STATUS  current
   DESCRIPTION
           "license remaining days"
   ::= { ipiCMLSEPlicenseNotificationsPrefix 3 }
END
