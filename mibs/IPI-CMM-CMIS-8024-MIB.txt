IPI-CMM-CMIS-8024-MIB DEFINITIONS ::= BEGIN

    --  This module provides authoritative definitions for
    --    8024 specific information.
    --
    --  This module will be extended, as needed.
    --

    IMPORTS
      OBJECT-TYPE, MODULE-IDENTITY,
      Gauge32, Counter32, Unsigned32,
      TimeTicks, NOTIFICATION-TYPE
        FROM SNMPv2-SMI
      DateAndTime, DisplayString,
      MacAddress, RowStatus, TEXTUAL-CONVENTION
        FROM SNMPv2-TC
      MODULE-COMPLIANCE, OBJECT-GROUP, NOTIFICATION-GROUP
        FROM SNMPv2-CONF
      enterprises,OBJECT-IDENTITY
        FROM SNMPv2-SMI
      ipi FROM IPI-MODULE-MIB;

   cmm  MODULE-IDENTITY
   LAST-UPDATED "202206230000Z"   -- 2022 Jun 23, 12:00:00 GMT
   ORGANIZATION "IP Infusion"
   CONTACT-INFO "support@ipinfusion.com"

    DESCRIPTION
     "The Structure of CMM CMIS 8024 specific information."
   REVISION "202206230000Z"
   DESCRIPTION
     "Complying to level 3 of SMILINT"
   ::= { ipi 100 }


   -- ### Textual Convention
   ConnectorType ::= TEXTUAL-CONVENTION
      STATUS      current
      DESCRIPTION
        "classifies the connector type"
      SYNTAX  INTEGER {
        unknown(1),
        subscriber-connector(2),
        fibre-channel-style-1-copper-connector(3),
        fibre-channel-style-2-copper-connector(4),
        bayonet-threaded-neill-concelman(5),
        fibre-channel-coax-headers(6),
        fiber-jack(7),
        lucent-connector(8),
        mechanical-transfer-registered-jack(9),
        multiple-optical(10),
        sg(11),
        optical-pigtail(12),
        multifiber-parallel-optic-1x12(13),
        multifiber-parallel-optic-2x16(14)
      }

   MediaInterfaceTechEncodings ::= TEXTUAL-CONVENTION
      STATUS      current
      DESCRIPTION
        "classifies the media interface device or cable technology."
      SYNTAX  INTEGER {
          vcsel-850nm(1),
          vcsel-1310nm(2),
          vcsel-1550nm(3),
          fp-1310nm(4),
          dfb-1310nm(5),
          dfb-1550nm(6),
          eml-1310nm(7),
          eml-1550nm(8),
          others(9),
          dfb-1490nm(10),
          copper-cable-unequalized(11),
          copper-cable-passive-equalized(12),
          copper-cable-near-and-far-end-limiting-active-equalizers(13),
          copper-cable-far-end-limiting-active-equalizers(14),
          copper-cable-near-end-limiting-active-equalizers(15),
          copper-cable-linear-active-equalizers(16),
          c-band-tunable-laser(17),
          l-band-tunable-laser(18),
          reserved(19)
        }

  END
