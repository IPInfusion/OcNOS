NXP-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

nxp MODULE-IDENTITY
    LAST-UPDATED "202507100000Z"
    ORGANIZATION "NXP Semiconductors B.V."
    CONTACT-INFO
        "http://www.nxp.com"
    DESCRIPTION
        "The NXP Semiconductors B.V. enterprise Module Identity."

    REVISION "202507100000Z"
        DESCRIPTION "Initial revision."

    ::= { cmmStackUnitModelName 28137 }

nxpOIDS OBJECT IDENTIFIER ::= { nxp 1 }
nxpProducts OBJECT IDENTIFIER ::= { nxp 2 }
nxpNAIES4 OBJECT IDENTIFIER ::= { nxpProducts 1 }

END
