PEGATRON-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

pegatron MODULE-IDENTITY
    LAST-UPDATED "202507100000Z"
    ORGANIZATION "Pegatron Computer Inc."
    CONTACT-INFO
        "http://www.pegatroncorp.com"
    DESCRIPTION
        "The Pegatron Computer Inc. enterprise Module Identity."

    REVISION "202507100000Z"
        DESCRIPTION "Initial revision."

    ::= { cmmStackUnitModelName 32022 }

pegatronOIDS OBJECT IDENTIFIER ::= { pegatron 1 }
pegatronProducts OBJECT IDENTIFIER ::= { pegatron 2 }
pegatronDM2118B OBJECT IDENTIFIER ::= { pegatronProducts 1 }
pegatronDM6214B OBJECT IDENTIFIER ::= { pegatronProducts 2 }

END
