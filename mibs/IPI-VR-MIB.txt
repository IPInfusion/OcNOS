IPI-VR-MIB DEFINITIONS ::= BEGIN

IMPORTS
      OBJECT-TYPE, MODULE-IDENTITY,
      Gauge32, Counter32, Integer32, Unsigned32,
      IpAddress, Counter64,
      TimeTicks, NOTIFICATION-TYPE
          FROM SNMPv2-SMI
      DateAndTime, DisplayString,
      PhysAddress, RowStatus, TEXTUAL-CONVENTION
          FROM SNMPv2-TC
      MODULE-COMPLIANCE, OBJECT-GROUP, NOTIFICATION-GROUP
          FROM SNMPv2-CONF
      snmpTraps
          FROM SNMPv2-MIB
      enterprises, OBJECT-IDENTITY
          FROM SNMPv2-SMI
      Ipv6Address
          FROM IPV6-TC
      ipi  FROM IPI-MODULE-MIB;

vr MODULE-IDENTITY
   LAST-UPDATED "202206010000Z"
   ORGANIZATION "IP Infusion Inc."
   CONTACT-INFO 
       "postal: 3965 Freedom Circle, Suite 200, Santa Clara, CA 95054

        email: support@ipinfusion.com

        telephone: +1 408-400-1900
        website: http://www.ipinfusion.com/"
   DESCRIPTION 
      "This MIB module is for managing Virtual router"

   REVISION      "202206010000Z"
   DESCRIPTION 
      "Updated the yang file with feature"

   REVISION      "201806210000Z"
   DESCRIPTION 
      "Initial Version"
   ::= { ipi  2 } 


vrVrTable OBJECT-TYPE 
	SYNTAX SEQUENCE OF VrVrEntry
	MAX-ACCESS not-accessible
	STATUS current
	DESCRIPTION 
		"This table provides information for Virtual router object"
	::= { vr 1 }

vrVrEntry OBJECT-TYPE
	SYNTAX VrVrEntry
	MAX-ACCESS not-accessible
	STATUS current
	DESCRIPTION 
		"An entry containing information for Virtual router object"
	INDEX { vrVrId }
	::= { vrVrTable 1 }

VrVrEntry::= SEQUENCE {
	vrVrId Unsigned32,
	vrName OCTET STRING	}

vrVrId OBJECT-TYPE
	SYNTAX Unsigned32(0..255) 
	MAX-ACCESS read-only
	STATUS current 
	DESCRIPTION 
		"Virtual router id"
	DEFVAL 	{ 0 } 
	::= { vrVrEntry 1 }

vrName OBJECT-TYPE
	SYNTAX OCTET STRING 
	MAX-ACCESS read-only
	STATUS current 
	DESCRIPTION 
		"name"
	::= { vrVrEntry 2 }


END
