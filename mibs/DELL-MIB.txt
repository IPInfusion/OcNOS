DELL-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

dell MODULE-IDENTITY
    LAST-UPDATED "202507100000Z"
    ORGANIZATION "Dell Inc."
    CONTACT-INFO
        "http://www.dell.com"
    DESCRIPTION
        "The Dell Inc. enterprise Module Identity."

    REVISION "202507100000Z"
        DESCRIPTION "Initial revision."

    ::= { cmmStackUnitModelName 674 }

dellOIDS OBJECT IDENTIFIER ::= { dell 1 }
dellProducts OBJECT IDENTIFIER ::= { dell 2 }
dellS4048 OBJECT IDENTIFIER ::= { dellProducts 1 }
dellS4048T OBJECT IDENTIFIER ::= { dellProducts 2 }
dellS4248 OBJECT IDENTIFIER ::= { dellProducts 3 }
dellS5296F OBJECT IDENTIFIER ::= { dellProducts 4 }
dellS6000 OBJECT IDENTIFIER ::= { dellProducts 5 }
dellS6010 OBJECT IDENTIFIER ::= { dellProducts 6 }
dellZ9100 OBJECT IDENTIFIER ::= { dellProducts 7 }

END
