OCNOS-VXLAN-MIB DEFINITIONS ::= BEGIN

IMPORTS
      OBJECT-TYPE, MODULE-IDENTITY,
      Gauge32, Counter32, Integer32, Unsigned32,
      IpAddress, Counter64,
      TimeTicks, NOTIFICATION-TYPE
          FROM SNMPv2-SMI
      DateAndTime, DisplayString,
      PhysAddress, RowStatus, TEXTUAL-CONVENTION
          FROM SNMPv2-TC
      MODULE-COMPLIANCE, OBJECT-GROUP, NOTIFICATION-GROUP
          FROM SNMPv2-CONF
      snmpTraps
          FROM SNMPv2-MIB
      enterprises, OBJECT-IDENTITY
          FROM SNMPv2-SMI
      Ipv6Address
          FROM IPV6-TC
      ipi  FROM OCNOS-IPI-MODULE-MIB
        vrVrId
                FROM OCNOS-VR-MIB;

vxlan MODULE-IDENTITY
   LAST-UPDATED "201708090000Z"
   ORGANIZATION "IP Infusion Inc."
   CONTACT-INFO 
       "postal: 3965 Freedom Circle, Suite 200, Santa Clara, CA 95054

        email: support@ipinfusion.com

        telephone: +1 408-400-1900
        website: http://www.ipinfusion.com/"
   DESCRIPTION 
      "This MIB module is for managing Network Virtualization Overlay functionality"

   REVISION      "201708090000Z"
   DESCRIPTION 
      "Initial Version"
   ::= { ipi  87 } 


vxlanNvoTunnelStatsTable OBJECT-TYPE 
	SYNTAX SEQUENCE OF VxlanNvoTunnelStatsEntry
	MAX-ACCESS not-accessible
	STATUS current
	DESCRIPTION 
		"This table provides information for Tunnel Stats"
	::= { vxlan 1 }

vxlanNvoTunnelStatsEntry OBJECT-TYPE
	SYNTAX VxlanNvoTunnelStatsEntry
	MAX-ACCESS not-accessible
	STATUS current
	DESCRIPTION 
		"An entry containing information for Tunnel Stats"
	INDEX { vrVrId,vxlanDestIp }
	::= { vxlanNvoTunnelStatsTable 1 }

VxlanNvoTunnelStatsEntry::= SEQUENCE {
	vxlanDestIp IpAddress,
	vxlanSourceIp IpAddress,
	vxlanOutbytes Counter64,
	vxlanOutpackets Counter64,
	vxlanInbytes Counter64,
	vxlanInpackets Counter64,
	vxlanUpdatetime TimeTicks,
	vxlanUpdowntime TimeTicks,
	vxlanTunnelStatus INTEGER,
	vxlanTxArpDiscardPackets Counter64,
	vxlanTxNdDiscardPackets Counter64,
	vxlanTxArpRequestPackets Counter64,
	vxlanTxArpReplyPackets Counter64,
	vxlanTxNeighborSolicitationPackets Counter64,
	vxlanTxNeighborAdvertisementPackets Counter64,
	vxlanTxGarpPackets Counter64,
	vxlanTxGnaPackets Counter64	}

vxlanDestIp OBJECT-TYPE
	SYNTAX IpAddress 
	MAX-ACCESS read-only
	STATUS current 
	DESCRIPTION 
		"Tunnel destination IP"
	::= { vxlanNvoTunnelStatsEntry 1 }

vxlanSourceIp OBJECT-TYPE
	SYNTAX IpAddress 
	MAX-ACCESS read-only
	STATUS current 
	DESCRIPTION 
		"Tunnel source IP"
	::= { vxlanNvoTunnelStatsEntry 2 }

vxlanOutbytes OBJECT-TYPE
	SYNTAX Counter64 
	MAX-ACCESS read-only
	STATUS current 
	DESCRIPTION 
		"This indicates total number of bytes sent out from tunnel interface"
	::= { vxlanNvoTunnelStatsEntry 3 }

vxlanOutpackets OBJECT-TYPE
	SYNTAX Counter64 
	MAX-ACCESS read-only
	STATUS current 
	DESCRIPTION 
		"This indicates total number of packets sent out from tunnel interface"
	::= { vxlanNvoTunnelStatsEntry 4 }

vxlanInbytes OBJECT-TYPE
	SYNTAX Counter64 
	MAX-ACCESS read-only
	STATUS current 
	DESCRIPTION 
		"This indicates total number of bytes received on tunnel interface"
	::= { vxlanNvoTunnelStatsEntry 5 }

vxlanInpackets OBJECT-TYPE
	SYNTAX Counter64 
	MAX-ACCESS read-only
	STATUS current 
	DESCRIPTION 
		"This indicates total number of packets received on tunnel interface"
	::= { vxlanNvoTunnelStatsEntry 6 }

vxlanUpdatetime OBJECT-TYPE
	SYNTAX TimeTicks 
	MAX-ACCESS read-only
	STATUS current 
	DESCRIPTION 
		"This indicates the last updated time of a tunnel nexthop"
	::= { vxlanNvoTunnelStatsEntry 7 }

vxlanUpdowntime OBJECT-TYPE
	SYNTAX TimeTicks 
	MAX-ACCESS read-only
	STATUS current 
	DESCRIPTION 
		"This indicates tunnel up/down time"
	::= { vxlanNvoTunnelStatsEntry 8 }

vxlanTunnelStatus OBJECT-TYPE
	SYNTAX INTEGER {deleted(0), unresolved(1), resolved(2), installed(3)} 
	MAX-ACCESS read-only
	STATUS current 
	DESCRIPTION 
		"Status of tunnel"
	::= { vxlanNvoTunnelStatsEntry 9 }

vxlanTxArpDiscardPackets OBJECT-TYPE
	SYNTAX Counter64 
	MAX-ACCESS read-only
	STATUS current 
	DESCRIPTION 
		"This Object describes Arp Discarded Packets"
	::= { vxlanNvoTunnelStatsEntry 10 }

vxlanTxNdDiscardPackets OBJECT-TYPE
	SYNTAX Counter64 
	MAX-ACCESS read-only
	STATUS current 
	DESCRIPTION 
		"This Object describes Nd Discarded Packets"
	::= { vxlanNvoTunnelStatsEntry 11 }

vxlanTxArpRequestPackets OBJECT-TYPE
	SYNTAX Counter64 
	MAX-ACCESS read-only
	STATUS current 
	DESCRIPTION 
		"This Object describes Arp request Transmitted Packets"
	::= { vxlanNvoTunnelStatsEntry 12 }

vxlanTxArpReplyPackets OBJECT-TYPE
	SYNTAX Counter64 
	MAX-ACCESS read-only
	STATUS current 
	DESCRIPTION 
		"This Object describes Arp reply Transmitted Packets"
	::= { vxlanNvoTunnelStatsEntry 13 }

vxlanTxNeighborSolicitationPackets OBJECT-TYPE
	SYNTAX Counter64 
	MAX-ACCESS read-only
	STATUS current 
	DESCRIPTION 
		"This Object describes Neighbour Solicitation Transmitted Packets"
	::= { vxlanNvoTunnelStatsEntry 14 }

vxlanTxNeighborAdvertisementPackets OBJECT-TYPE
	SYNTAX Counter64 
	MAX-ACCESS read-only
	STATUS current 
	DESCRIPTION 
		"This Object describes Neighbour Advertisement Transmitted Packets"
	::= { vxlanNvoTunnelStatsEntry 15 }

vxlanTxGarpPackets OBJECT-TYPE
	SYNTAX Counter64 
	MAX-ACCESS read-only
	STATUS current 
	DESCRIPTION 
		"This Object describes Garp Transmitted Packets"
	::= { vxlanNvoTunnelStatsEntry 16 }

vxlanTxGnaPackets OBJECT-TYPE
	SYNTAX Counter64 
	MAX-ACCESS read-only
	STATUS current 
	DESCRIPTION 
		"This Object describes Gna Transmitted Packets"
	::= { vxlanNvoTunnelStatsEntry 17 }


--
-- Notifications
--

vxlanNotificationsPrefix OBJECT IDENTIFIER ::=
        { vxlan 0 }

vxlantunnelstatuschangenotification NOTIFICATION-TYPE
   OBJECTS { vxlanDestIp, vrVrId, vxlanTunnelStatus }
   STATUS  current
   DESCRIPTION
           "The nvoTunnelStatus trap is generated when there is any status change in Tunnel Severity level is INFO for tunnel status going to Unresolved/Deleted status and MINOR for Resolved status."
   ::= { vxlanNotificationsPrefix 1 }
END
