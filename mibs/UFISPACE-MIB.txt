UFISPACE-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

ufiSpace MODULE-IDENTITY
    LAST-UPDATED "202507100000Z"
    ORGANIZATION "Ufi Space Co., Ltd."
    CONTACT-INFO
        "http://www.ufispace.com"
    DESCRIPTION
        "The Ufi Space Co., Ltd. enterprise Module Identity."

    REVISION "202507100000Z"
        DESCRIPTION "Initial revision."

    ::= { cmmStackUnitModelName 52257 }

ufiSpaceOIDS OBJECT IDENTIFIER ::= { ufiSpace 1 }
ufiSpaceProducts OBJECT IDENTIFIER ::= { ufiSpace 2 }
ufiSpace310030XC OBJECT IDENTIFIER ::= { ufiSpaceProducts 1 }
ufiSpace630156ST OBJECT IDENTIFIER ::= { ufiSpaceProducts 2 }
ufiSpace780154XS OBJECT IDENTIFIER ::= { ufiSpaceProducts 3 }
ufiSpace890154XC OBJECT IDENTIFIER ::= { ufiSpaceProducts 4 }
ufiSpace911032X OBJECT IDENTIFIER ::= { ufiSpaceProducts 5 }
ufiSpace930032D OBJECT IDENTIFIER ::= { ufiSpaceProducts 6 }
ufiSpace930132D OBJECT IDENTIFIER ::= { ufiSpaceProducts 7 }
ufiSpace932164E OBJECT IDENTIFIER ::= { ufiSpaceProducts 8 }
ufiSpace950012XST OBJECT IDENTIFIER ::= { ufiSpaceProducts 9 }
ufiSpace950022XST OBJECT IDENTIFIER ::= { ufiSpaceProducts 10 }
ufiSpace950030XS OBJECT IDENTIFIER ::= { ufiSpaceProducts 11 }
ufiSpace950118SMT OBJECT IDENTIFIER ::= { ufiSpaceProducts 12 }
ufiSpace950128SMT OBJECT IDENTIFIER ::= { ufiSpaceProducts 13 }
ufiSpace950212SM OBJECT IDENTIFIER ::= { ufiSpaceProducts 14 }
ufiSpace950216SMT OBJECT IDENTIFIER ::= { ufiSpaceProducts 15 }
ufiSpace951028DC OBJECT IDENTIFIER ::= { ufiSpaceProducts 16 }
ufiSpace951030XC OBJECT IDENTIFIER ::= { ufiSpaceProducts 17 }
ufiSpace960028DX OBJECT IDENTIFIER ::= { ufiSpaceProducts 18 }
ufiSpace960032X OBJECT IDENTIFIER ::= { ufiSpaceProducts 19 }
ufiSpace960056DX OBJECT IDENTIFIER ::= { ufiSpaceProducts 20 }
ufiSpace960064X OBJECT IDENTIFIER ::= { ufiSpaceProducts 21 }
ufiSpace960072XC OBJECT IDENTIFIER ::= { ufiSpaceProducts 22 }
ufiSpace961036D OBJECT IDENTIFIER ::= { ufiSpaceProducts 23 }
ufiSpace961046DX OBJECT IDENTIFIER ::= { ufiSpaceProducts 24 }
ufiSpace961048DX OBJECT IDENTIFIER ::= { ufiSpaceProducts 25 }

END
