EDGECORE-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

edgeCore MODULE-IDENTITY
    LAST-UPDATED "202507100000Z"
    ORGANIZATION "Edgecore Networks Corporation"
    CONTACT-INFO
        "http://www.edge-core.com"
    DESCRIPTION
        "The Edgecore Networks Corporation enterprise Module Identity."

    REVISION "202507100000Z"
        DESCRIPTION "Initial revision."

    ::= { cmmStackUnitModelName 52587 }

edgeCoreOIDS OBJECT IDENTIFIER ::= { edgeCore 1 }
edgeCoreProducts OBJECT IDENTIFIER ::= { edgeCore 2 }
edgeCoreAS462554T OBJECT IDENTIFIER ::= { edgeCoreProducts 1 }
edgeCoreAS581254T OBJECT IDENTIFIER ::= { edgeCoreProducts 2 }
edgeCoreAS581254X OBJECT IDENTIFIER ::= { edgeCoreProducts 3 }
edgeCoreAS583554T OBJECT IDENTIFIER ::= { edgeCoreProducts 4 }
edgeCoreAS583554X OBJECT IDENTIFIER ::= { edgeCoreProducts 5 }
edgeCoreAS591254X OBJECT IDENTIFIER ::= { edgeCoreProducts 6 }
edgeCoreAS591516X OBJECT IDENTIFIER ::= { edgeCoreProducts 7 }
edgeCoreAS591518X OBJECT IDENTIFIER ::= { edgeCoreProducts 8 }
edgeCoreAS591626XB OBJECT IDENTIFIER ::= { edgeCoreProducts 9 }
edgeCoreAS591654X OBJECT IDENTIFIER ::= { edgeCoreProducts 10 }
edgeCoreAS591654XKS OBJECT IDENTIFIER ::= { edgeCoreProducts 11 }
edgeCoreAS591654XM OBJECT IDENTIFIER ::= { edgeCoreProducts 12 }
edgeCoreAS731527XB OBJECT IDENTIFIER ::= { edgeCoreProducts 13 }
edgeCoreAS731530X OBJECT IDENTIFIER ::= { edgeCoreProducts 14 }
edgeCoreAS731626XB OBJECT IDENTIFIER ::= { edgeCoreProducts 15 }
edgeCoreAS732656X OBJECT IDENTIFIER ::= { edgeCoreProducts 16 }
edgeCoreAS751524X OBJECT IDENTIFIER ::= { edgeCoreProducts 17 }
edgeCoreAS753528XB OBJECT IDENTIFIER ::= { edgeCoreProducts 18 }
edgeCoreAS771232X OBJECT IDENTIFIER ::= { edgeCoreProducts 19 }
edgeCoreAS771624SC OBJECT IDENTIFIER ::= { edgeCoreProducts 20 }
edgeCoreAS771632X OBJECT IDENTIFIER ::= { edgeCoreProducts 21 }
edgeCoreAS772632X OBJECT IDENTIFIER ::= { edgeCoreProducts 22 }
edgeCoreAS781664X OBJECT IDENTIFIER ::= { edgeCoreProducts 23 }
edgeCoreAS794630XB OBJECT IDENTIFIER ::= { edgeCoreProducts 24 }
edgeCoreAS794674XKB OBJECT IDENTIFIER ::= { edgeCoreProducts 25 }
edgeCoreAS971632D OBJECT IDENTIFIER ::= { edgeCoreProducts 26 }
edgeCoreAS972632D OBJECT IDENTIFIER ::= { edgeCoreProducts 27 }
edgeCoreAS973664D OBJECT IDENTIFIER ::= { edgeCoreProducts 28 }
edgeCoreAS981764D OBJECT IDENTIFIER ::= { edgeCoreProducts 29 }
edgeCoreAS994736XKB OBJECT IDENTIFIER ::= { edgeCoreProducts 30 }
edgeCoreASXVOLT16 OBJECT IDENTIFIER ::= { edgeCoreProducts 31 }

END
