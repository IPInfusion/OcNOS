ALPHANW-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

alphaNetworks MODULE-IDENTITY
    LAST-UPDATED "202507100000Z"
    ORGANIZATION "Alpha Networks Inc."
    CONTACT-INFO
        "http://www.alphanetworks.com"
    DESCRIPTION
        "The Alpha Networks Inc. enterprise Module Identity."

    REVISION "202507100000Z"
        DESCRIPTION "Initial revision."

    ::= { cmmStackUnitModelName 31874 }

alphaNetworksOIDS OBJECT IDENTIFIER ::= { alphaNetworks 1 }
alphaNetworksProducts OBJECT IDENTIFIER ::= { alphaNetworks 2 }
alphaNetworksSPX70D0168F OBJECT IDENTIFIER ::= { alphaNetworksProducts 1 }
alphaNetworksSTX60D0062F OBJECT IDENTIFIER ::= { alphaNetworksProducts 2 }

END
