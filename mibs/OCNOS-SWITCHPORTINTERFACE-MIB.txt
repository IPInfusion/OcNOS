OCNOS-SWITCHPORTINTERFACE-MIB DEFINITIONS ::= BEGIN

IMPORTS
      OBJECT-TYPE, MODULE-IDENTITY,
      Gauge32, Counter32, Integer32, Unsigned32,
      IpAddress, Counter64,
      TimeTicks, NOTIFICATION-TYPE
          FROM SNMPv2-SMI
      DateAndTime, DisplayString,
      PhysAddress, RowStatus, TEXTUAL-CONVENTION
          FROM SNMPv2-TC
      MODULE-COMPLIANCE, OBJECT-GROUP, NOTIFICATION-GROUP
          FROM SNMPv2-CONF
      snmpTraps
          FROM SNMPv2-MIB
      enterprises, OBJECT-IDENTITY
          FROM SNMPv2-SMI
      Ipv6Address
          FROM IPV6-TC
      ipi  FROM OCNOS-IPI-MODULE-MIB
      ifName  FROM IF-MIB
        vrVrId
                FROM OCNOS-VR-MIB;

switchportinterface MODULE-IDENTITY
   LAST-UPDATED "201806210000Z"
   ORGANIZATION "IP Infusion Inc."
   CONTACT-INFO 
       "postal: 3965 Freedom Circle, Suite 200, Santa Clara, CA 95054

        email: support@ipinfusion.com

        telephone: +1 408-400-1900
        website: http://www.ipinfusion.com/"
   DESCRIPTION 
      "This MIB module is for managing switchport configuration"

   REVISION      "201806210000Z"
   DESCRIPTION 
      "Initial Version"
   ::= { ipi  888 } 


switchportinterfacePortSecurityTable OBJECT-TYPE 
	SYNTAX SEQUENCE OF SwitchportinterfacePortSecurityEntry
	MAX-ACCESS not-accessible
	STATUS current
	DESCRIPTION 
		"This table provides information for portSecurity"
	::= { switchportinterface 1 }

switchportinterfacePortSecurityEntry OBJECT-TYPE
	SYNTAX SwitchportinterfacePortSecurityEntry
	MAX-ACCESS not-accessible
	STATUS current
	DESCRIPTION 
		"An entry containing information for portSecurity"
	INDEX { vrVrId,ifName }
	::= { switchportinterfacePortSecurityTable 1 }

SwitchportinterfacePortSecurityEntry::= SEQUENCE {
	switchportinterfacePortSecurityMode INTEGER,
	switchportinterfacePortSecurityLogging INTEGER,
	switchportinterfacePortSecurityMaxLimit Unsigned32	}

switchportinterfacePortSecurityMode OBJECT-TYPE
	SYNTAX INTEGER {static(1), default(2)} 
	MAX-ACCESS read-write
	STATUS current 
	DESCRIPTION 
		"port security type"
	::= { switchportinterfacePortSecurityEntry 1 }

switchportinterfacePortSecurityLogging OBJECT-TYPE
	SYNTAX INTEGER {enable(1), disable(0)} 
	MAX-ACCESS read-write
	STATUS current 
	DESCRIPTION 
		"port security type"
	::= { switchportinterfacePortSecurityEntry 2 }

switchportinterfacePortSecurityMaxLimit OBJECT-TYPE
	SYNTAX Unsigned32(1..1000) 
	MAX-ACCESS read-write
	STATUS current 
	DESCRIPTION 
		"port-security"
	DEFVAL 	{ 1 } 
	::= { switchportinterfacePortSecurityEntry 3 }


--
-- Notifications
--

switchportinterfaceNotificationsPrefix OBJECT IDENTIFIER ::=
        { switchportinterface 0 }
END
