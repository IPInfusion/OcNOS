DELTA-MIB DEFINITIONS ::= BEGIN

IMPORTS
    MODULE-IDENTITY, OBJECT-IDENTITY, OBJECT-TYPE,
    Gauge32, Counter32, Integer32, Unsigned32,
    IpAddress, Counter64, TimeTicks, NOTIFICATION-TYPE,
    enterprises
        FROM SNMPv2-SMI
    DateAndTime, DisplayString, PhysAddress, RowStatus, TEXTUAL-CONVENTION
        FROM SNMPv2-TC
    MODULE-COMPLIANCE, OBJECT-GROUP, NOTIFICATION-GROUP
        FROM SNMPv2-CONF
    snmpTraps
        FROM SNMPv2-MIB
    cmmStackUnitModelName
        FROM IPI-CMM-CHASSIS-MIB;

delta MODULE-IDENTITY
    LAST-UPDATED "202507100000Z"
    ORGANIZATION "Delta Electronics Inc."
    CONTACT-INFO
        "http://www.deltaww.com"
    DESCRIPTION
        "The Delta Electronics Inc. enterprise Module Identity."

    REVISION "202507100000Z"
        DESCRIPTION "Initial revision."

    ::= { cmmStackUnitModelName 6785 }

deltaOIDS OBJECT IDENTIFIER ::= { delta 1 }
deltaProducts OBJECT IDENTIFIER ::= { delta 2 }
deltaAG7648 OBJECT IDENTIFIER ::= { deltaProducts 1 }
deltaAGC7648 OBJECT IDENTIFIER ::= { deltaProducts 2 }
deltaAGC7008S OBJECT IDENTIFIER ::= { deltaProducts 3 }
deltaAG8032 OBJECT IDENTIFIER ::= { deltaProducts 4 }
deltaAG9032V1 OBJECT IDENTIFIER ::= { deltaProducts 5 }
deltaAG9032V2 OBJECT IDENTIFIER ::= { deltaProducts 6 }

END
